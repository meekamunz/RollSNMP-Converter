-- MIB file created 20-Feb-2005 03:57:28, by
--   SMICng version 2.2.11-beta(PRO)(Solaris), January 20, 2001. Enterprise key cisco.com

CISCO-ITP-TC-MIB DEFINITIONS ::= BEGIN

-- From file: "CISCO-ITP-TC-MIB.my"
-- Compile options "4 7 F H N O W 03 06 0B 0G 0N 0T"

IMPORTS
    ciscoMgmt
            FROM CISCO-SMI
    Gauge
            FROM RFC1155-SMI;

ciscoItpTextualConventions OBJECT IDENTIFIER ::= { ciscoMgmt 231 }
-- MODULE-IDENTITY
--  LastUpdated
--    200308030000Z
--  OrgName
--    Cisco Systems, Inc.
--  ContactInfo
--           Cisco Systems, Inc
--            Customer Service
--    
--    Postal: 170 W. Tasman Drive
--            San Jose, CA  95134
--            USA
--    
--       Tel: +1 800 553-NETS
--    
--    E-mail: cs-ss7@cisco.com
--  Descr
--    The defines textual conventions used by to manage
--     devices related to the SS7 network.  The
--     relevant ITU documents describing this technology is
--     the ITU Q series, including ITU Q.700: Introduction to
--     CCITT Signalling System No. 7 and ITU Q.701 Functional
--     description of the message transfer part (MTP) of
--     Signalling System No. 7.
--    
--    Abbreviations:
--    CDPA  - Called Party Point Code
--    CGPA  - Calling Party Point Code
--    CLLI  - Common Language Location Codes
--    CR    - Connection Request message
--    CREF  - Connection Refusal message
--    DPC   - Destination Point Code
--    ERR   - Error message
--    GTA   - Global Title Address 
--    GTI   - Global Title Indicator
--    GTT   - Global Title Translation
--    LUDT  - long unitdata message
--    LUDTS - long unitdata service message
--    M2PA  - MTP2 Peer-to-Peer Adaptation Layer
--    M3UA  - MTP3-User Adaptation 
--    MAP   - Mated Application Table
--    MSU   - Message Signal Unit 
--    MTP   - Message Transport Protocol
--    MTP2  - Layer 2 of Message Transport Protocol
--    MTP3  - Layer 3 of Message Transport Protocol
--    NAI   - Nature of Address Indicator
--    NP    - Numbering Plan         
--    NTT   - The Japanese Nippon Telephone & Telegraph 
--    OPC   - Originating Point Code
--    PC    - Point Code
--    RTN   - Route Table Name
--    RSR   - Reset Request message
--    SCCP  - Signalling Connection Control Part
--    SCTP  - Stream Transmission Protocol(RFC 2960)
--    SI    - Signalling Indicator
--    SP    - Signalling Point
--    SLC   - Signalling Link Code
--    SLS   - Signalling Link Selector
--    SSN   - Subsystem Number
--    SUA   - SCCP-User Adaptation 
--    TFR   - Transfer Restricted messages  
--    TT    - Title Translation
--    TTC   - The Japanese Telecommunications Technology 
--       Committee 
--    UDT   - unitdata message
--    UDTS  - unitdata service message
--    XUDT  - extended unitdata message
--    XUDTS - extended unitdata service message
--  RevDate
--    200308030000Z
--  RevDescr
--    Updated CItpTcPointCode textual convention to 
--     include descriptions for Japanese NTT and TTC
--     variants.
--  RevDate
--    200301290000Z
--  RevDescr
--    Added textual convention used to support the 
--     ability to define multiple instances of the 
--     signalling points.  The following textual conventions
--     were added.                                         
--        CItpTcNetworkName
--        CItpTcInstanceNumber
--        CItpTcSls
--    
--     Also deprecated CItpTcGtaAddr and CItpTcGtaDisplayZB.
--     Added CItpTcGtaLongAddr and CItpTcGtaLongDisplay.
--     
--     Added new enumerated value to CItpTcLinkType object
--     for virtual link used to connect signalling points
--     acting as gateways.
--  RevDate
--    200112110000Z
--  RevDescr
--    Added new enumerated value to CItpTcLinkType object
--     for high speed link support. Add new enumerated
--     value to the CItpTcSs7Variant object to support
--     China national variant. A new textual convention has
--     been added to address 0..15 range for Global Title
--     addresses.
--  RevDate
--    200110010000Z
--  RevDescr
--    Initial version of this MIB module.

CItpTcAclId ::= Gauge(0|2700..2999)
-- TEXTUAL-CONVENTION
--  Status
--    mandatory
--  Descr
--    An numeric Identifier used to specify an access list 
--     used to permit and deny packets based on MTP3 
--     information. Either the value 0 or the value of access list
--     identifier. A value of zero indicates that an access list
--     is not specified.

CItpTcCLLI ::= OCTET STRING(SIZE(0..11))
-- TEXTUAL-CONVENTION
--  Status
--    mandatory
--  Descr
--    Common Language Location Codes (CLLI Codes). 
--     An 11-character standardized geographic identifier
--     that uniquely identifies the geographic location of
--     telecommunication equipment.
--     
--     The CLLI code is supported as octet string containing
--     administrative information in human-readable form.
--    
--     The use of control codes should be avoided.
--     
--     The use of newline should be avoided.
--    
--     The use of leading or trailing white space should
--     be avoided.
--  Refer
--    Complete listings of geographical and geopolitical 
--     codes can be found in the BR 751-401-xxx series and
--     BR 751-100-055, respectively.

CItpTcDisplayPC ::= OCTET STRING(SIZE(1..12))
-- TEXTUAL-CONVENTION
--  Status
--    mandatory
--  Descr
--    The Point Code in formatted based on the variant
--     and the customer defined parameters.

CItpTcEncodingSchemeValue ::= INTEGER(0..15)
-- TEXTUAL-CONVENTION
--  Status
--    mandatory
--  Descr
--    The encoding scheme value.

CItpTcGlobalTitleSelector ::= INTEGER {
        nai(1),
        tt(2),
        ttNpEs(3),
        ttNpNaiEs(4)
        }
-- TEXTUAL-CONVENTION
--  Status
--    mandatory
--  Descr
--    Global Title Selector.
--     'nai'       : Global title translation based on
--                   nature of address indicator.
--                   
--     'tt'        : Global title translation based on
--                   translation type.
--                   
--     'ttNpEs'    : Global title translation based on
--                   translation type, numbering plan 
--                   value and Encoding Scheme Value.
--         
--     'ttNpNaiEs' : Global title translation based on
--                   translation type, numbering plan,
--                   value, nature of address indicator
--                   and encoding scheme value.

CItpTcGlobalTitleSelectorName ::= OCTET STRING(SIZE(1..9))
-- TEXTUAL-CONVENTION
--  Status
--    mandatory
--  Descr
--    The configured name associated with SCCP GTT
--     Selector.
--    
--     An octet string specified by an administrator that
--     must be in human-readable form.  The names must
--     conform to the allowed characters that can be 
--     specified via Command Line Interface(CLI).  The 
--     names cannot contain control character and should 
--     not contain leading or trailing white space.

CItpTcGtaAddr ::= OCTET STRING(SIZE(8))
-- TEXTUAL-CONVENTION
--  Status
--    deprecated
--  Descr
--    The configured digits in the SCCP GTT
--     Global Title Address.
--     
--     An octet string specified by an administrator
--     must be in human-readable form.  The names must
--     conform to the allowed characters that can be 
--     specified via Command Line Interface(CLI).  The 
--     names cannot contain control character and should 
--     not contain leading or trailing white space.

CItpTcGtaLongAddr ::= OCTET STRING(SIZE(0..64))
-- TEXTUAL-CONVENTION
--  Status
--    mandatory
--  Descr
--    The configured hexadecimal digits in the SCCP GTT
--     Global Title Address.

CItpTcGtaDisplay ::= OCTET STRING(SIZE(1..15))
-- TEXTUAL-CONVENTION
--  Status
--    deprecated
--  Descr
--    The configured digits in the SCCP GTT
--     Global Title Address. It consists of ASCII
--     representation of GTA hex digits.
--    
--     This textual convention has been deprecated and
--     replaced by CItpTcGtaDisplayZB.

CItpTcGtaDisplayZB ::= OCTET STRING(SIZE(0..15))
-- TEXTUAL-CONVENTION
--  Status
--    deprecated
--  Descr
--    The configured digits in the SCCP GTT
--     Global Title Address. It consists of ASCII
--     representation of GTA hex digits.

CItpTcGtaLongDisplay ::= OCTET STRING(SIZE(0..64))
-- TEXTUAL-CONVENTION
--  Status
--    mandatory
--  Descr
--    The configured digits in the SCCP GTT
--     Global Title Address. It consists of ASCII
--     representation of GTA hex digits.

CItpTcGtaDisplayLen ::= Gauge(1..15)
-- TEXTUAL-CONVENTION
--  Status
--    mandatory
--  Descr
--    The SCCP GTT Global Title Address length.

CItpTcGtaLongDisplayLen ::= Gauge(0..64)
-- TEXTUAL-CONVENTION
--  Status
--    mandatory
--  Descr
--    The SCCP GTT Global Title Address length.

CItpTcNetworkName ::= OCTET STRING(SIZE(0..19))
-- TEXTUAL-CONVENTION
--  Status
--    mandatory
--  Descr
--    The network name is used to indicate the network
--     in which this signalling point is participating.
--     One or more instances of signalling points can 
--     exist in the same physical device.  This identifier
--     will be used to correlate instances of signalling 
--     points by network.
--     
--     When multiple instance support is not enable the 
--     network name will default to the null string.
--      
--     An octet string specified by an administrator that
--     must be in human-readable form.  The names must conform
--     to the allowed characters that can be specified via 
--     Command Line Interface(CLI).  The names cannot contain
--     control character and should not contain leading or 
--     trailing white space.

CItpTcInstanceNumber ::= Gauge(0..255)
-- TEXTUAL-CONVENTION
--  Status
--    mandatory
--  Descr
--    The instance number used to select a particular
--     Signalling point.

CItpTcLinksetId ::= OCTET STRING(SIZE(1..19))
-- TEXTUAL-CONVENTION
--  Status
--    mandatory
--  Descr
--    The configured name associated with an Signalling
--     Point Linkset.
--         
--     An octet string specified by an administrator that must
--     be in human-readable form.  The names must conform to 
--     the allowed characters that can be specified via 
--     Command Line Interface(CLI).  The names cannot contain
--     control character and should not contain leading or 
--     trailing white space.

CItpTcLinkSLC ::= Gauge(0..15)
-- TEXTUAL-CONVENTION
--  Status
--    mandatory
--  Descr
--    The Signalling Link Code. This is the link identifier
--     within a linkset.

CItpTcLinkType ::= INTEGER {
        other(1),
        serial(2),
        sctpIp(3),
        hsl(4),
        virtual(5)
        }
-- TEXTUAL-CONVENTION
--  Status
--    mandatory
--  Descr
--    The link types.
--     'other'  : This link is of some type not listed below.
--     'serial' : This link is a serial link transporting
--                  SS7 traffic.
--     'sctpIp' : This a SCTP/IP link transporting 
--                  SS7 traffic.
--     'hsl'    : This link is a high speed link using the ATM 
--                protocol for transporting SS7 traffic.
--     'virtual': This link is virtual link used to connect to 
--                instance of signalling point running on the 
--                same physical device.  The link will be used to 
--                send and manage traffic between two signalling
--                acting as a gateway.

CItpTcNAI ::= INTEGER(0..255)
-- TEXTUAL-CONVENTION
--  Status
--    mandatory
--  Descr
--    The SCCP GTT Network Address Indicator (NAI).
--     The following values are generally used:
--       Unknown Nature of Address (0),
--       Subscriber Number (1),
--       Reserved for national use (2),
--       National Significant Number (3),
--       International Number (4),
--       Maximum NAI (127),
--       Invalid NAI (253),
--       Wild    NAI (254).

CItpTcNetworkIndicator ::= INTEGER {
        --?? enum value of zero may cause problems
        international(0),
        internationatSpare(1),
        national(2),
        nationalSpare(3)
        }
-- TEXTUAL-CONVENTION
--  Status
--    mandatory
--  Descr
--    Network Indicator:
--      international - International network
--      national      - National network
--      reserved      - Reserved for national use
--      spare         - Spare (for international use only)
--     'international'      : International network
--     'internationalSpare' : International network spare
--     'national'           : National network
--     'nationalSpare'      : National network Spare

CItpTcNumberingPlan ::= INTEGER(0..255)
-- TEXTUAL-CONVENTION
--  Status
--    mandatory
--  Descr
--    The SCCP GTT Numbering Plan (NP).
--     The following values are generally used:
--       Unknown NP (0),
--       ISDN/Telephony NP (1),
--       Spare    (2),
--       Data  NP (3),
--       Telex NP (4),
--       Maritime Mobile NP (5),
--       Land Mobile     NP (6),
--       ISDN/Mobile     NP (7),
--       Private NP (8).
--       Max     NP (15),
--       Invalid NP (253),
--       Wild    NP (254).

CItpTcPointCode ::= Gauge(0..16777216)
-- TEXTUAL-CONVENTION
--  Status
--    mandatory
--  Descr
--    The SS7 network node address as specified in the
--     following references.  The format of the Point
--     code depends on the variant defined in the 
--     CgspSS7Variant object as follows.
--     
--            33222222222211111111110000000000
--            10987654321098765432109876543210
--     ANSI:          nnnnnnnn                 - Network
--                            cccccccc         - Cluster
--                                    mmmmmmmm - Member
--     ITU:                     zzz            - Zone
--                                 aaaaaaaa    - Area/Network
--                                         iii - Identifier
--     NTT:                   zzzzz            - Zone         
--                                 aaaa        - Area/Network 
--                                     iiiiiii - Identifier   
--     TTC:                   zzzzz            - Zone         
--                                 aaaa        - Area/Network 
--                                     iiiiiii - Identifier   
--     
--     Note: The China variant has the same format as ANSI.
--                                         
--     This form of the point-code is not intended for
--     for presentation.
--  Refer
--    The SS7 network node address as specified in the
--     International Telecommunication Union standard Q.708:
--     Specifications of Signalling System No. 7 - Numbering
--     of International Signalling Point Codes, and by ANSI
--     T1.111.8 Numbering of Signalling Point Codes.
--    
--     GF 001-9001 - Technical Specifications of Signalling
--     System No. 7 for National Telephone Network of China.

CItpTcPointCodeMask ::= Gauge(0..16777216)
-- TEXTUAL-CONVENTION
--  Status
--    mandatory
--  Descr
--    A mask used to perform different operations on
--     pointcodes.
--  Refer
--    The SS7 network node address as specified in the
--     International Telecommunication Union standard Q.708:
--     Specifications of Signalling System No. 7 - Numbering
--     of International Signalling Point Codes, and by ANSI
--     T1.111.8 Numbering of Signalling Point Codes.

CItpTcPointCodeType ::= INTEGER {
        primary(1),
        additional(2),
        capability(3)
        }
-- TEXTUAL-CONVENTION
--  Status
--    mandatory
--  Descr
--    List of the possible Point Code types.
--      'primary'     : The primary point used to communicate
--                      information on the Signalling point.
--      'additional'  : Additional point codes.

CItpTcQos ::= Gauge(0..7|255)
-- TEXTUAL-CONVENTION
--  Status
--    mandatory
--  Descr
--    The quality of service classification to be assigned 
--     to the IP packets used to transport the SS7 messages.
--     The value can be from one to seven when selecting
--     a Qos class or 255 to indicate the packet will not
--     be assigned a Qos class. This value will be set to
--     zero when cItpSpLinkType indicates that 
--     Quality of Service does not apply to this link.

CItpTcRouteTableName ::= OCTET STRING(SIZE(1..19))
-- TEXTUAL-CONVENTION
--  Status
--    mandatory
--  Descr
--    The configured name associated with an SP Route
--     Table.
--         
--     An octet string specified by an administrator that must
--     be in human-readable form.  The names must conform to 
--     the allowed characters that can be specified via 
--     Command Line Interface(CLI).  The names cannot contain
--     control character and should not contain leading or 
--     trailing white space.

CItpTcServiceIndicator ::= INTEGER {
        --?? enum value of zero may cause problems
        snmm(0),
        sntm(1),
        spare2(2),
        sccp(3),
        tup(4),
        isup(5),
        dupc(6),
        dupf(7),
        mtup(8),
        bisup(9),
        sisup(10),
        spare11(11),
        spare12(12),
        spare13(13),
        spare14(14),
        spare15(15)
        }
-- TEXTUAL-CONVENTION
--  Status
--    mandatory
--  Descr
--    The list of possible Service Indicator values. This
--     identifies the type of SS7 packet.
--    
--     The service indicator codes for the international
--     Signalling network are allocated as follows:
--    
--     'SNMM'        : Signalling network management 
--                     messages (SNMM)
--     'SNTM'        : Signalling network testing and 
--                     maintenance messages (SNTM)
--     'Spare2'      : Spare 2
--     'SCCP'        : SCCP
--     'TUP'         : Telephone User Part (TUP)
--     'ISUP'        : ISDN User Part      (ISUP)
--     'DUPC'        : Data User Part, call and circuit-related 
--                     messages (DUPC)
--     'DUPF'        : Data User Part, facility registration and
--                     cancellation messages (DUPF)
--     'MTUP'        : Reserved for MTP Testing User Part (MTUP)
--     'BISUP'       : Broadband ISDN User Part  (BISUP)
--     'SISUP'       : Satellite ISDN User Part (SISUP)
--     'Spare11'     : Spare 11
--     'Spare12'     : Spare 12
--     'Spare13'     : Spare 13
--     'Spare14'     : Spare 14
--     'Spare15'     : Spare 15
--  Refer
--    ITU Q.704 Signalling network functions and messages section
--     14.2.1 Service indicator.

CItpTcSls ::= Gauge(0..255)
-- TEXTUAL-CONVENTION
--  Status
--    mandatory
--  Descr
--    The Signalling Link Selector is a numeric value that
--     contains the MTP3 packets to allow load balancing of
--     traffic across a link within a linkset or combined linkset.
--     Each linkset provides one or more tables used to map
--     Signalling Link Selectors to Signalling Link Codes.  The
--     number of Signalling Link Selectors is 16 for ITU and 256
--     for ANSI.

CItpTcSs7Variant ::= INTEGER {
        ansi(1),
        itu(2),
        china(3)
        }
-- TEXTUAL-CONVENTION
--  Status
--    mandatory
--  Descr
--    The list of SS7 variants.
--    'ANSI'    : The ANSI variant of the SS7 specification.
--    'ITU'     : The ITU variant of the SS7 specification.
--    'China'   : The China national variant. This variant
--                is a combination of ITU and ANSI. The 
--                protocol matches ITU except where the 
--                point-code has been expanded to ANSI format.
--  Refer
--    GF 001-9001 - Technical Specifications of Signalling
--     System No. 7 for National Telephone Network of China.

CItpTcSubSystemNumber ::= Gauge(0|2..255)
-- TEXTUAL-CONVENTION
--  Status
--    mandatory
--  Descr
--    The SCCP Subsystem Number .  A  value of zero 
--     indicates that a subsystem is not specified.

CItpTcSubSystemNumberMask ::= Gauge(2..255)
-- TEXTUAL-CONVENTION
--  Status
--    mandatory
--  Descr
--    The SCCP Subsystem Number Mask.

CItpTcTableLoadStatus ::= INTEGER {
        loadNotRequested(1),
        loadInProgress(2),
        loadComplete(3),
        loadCompleteWithErrors(4),
        loadFailed(5)
        }
-- TEXTUAL-CONVENTION
--  Status
--    mandatory
--  Descr
--    The status of the current or prior load operation.
--     'loadNotRequested' : load operations have not been
--                          requested.
--    
--     'loadInProgress'  : load request is active.
--    
--     'loadComplete' : load request complete without errors.
--    
--     'loadCompleteWithErrors' : Load request completed with
--                                some type of errors that
--                                prevented the adding of one
--                                or more entries.
--    
--     'loadFailed' : Load request failed.

CItpTcTimerMtp2T01 ::= Gauge(5000..150000)
-- TEXTUAL-CONVENTION
--  Status
--    mandatory
--  Descr
--    Alignment ready timer. The default and valid range is
--     dependant on the value of variant. 
--     
--           Min      Max      Def 
--           ======   ======   ======  
--     ANSI   12500    16000    13000  
--     ITU    40000    50000    40000 
--     
--     The SYNTAX statement allows values for both
--     the ANSI, ITU variants and MTP2 Peer-to-Peer 
--     Adaptation Layer.
--  Refer
--    ITU Q.703 Signalling Link.
--     ANSI T1.111.3 Telecommunications - Signalling system
--     No. 7 (SS7)-Message Transfer Part (MTP).

CItpTcTimerMtp2T02 ::= Gauge(0|5000..150000)
-- TEXTUAL-CONVENTION
--  Status
--    mandatory
--  Descr
--    Not aligned timer. The default and valid range is
--     dependant on the value of variant.
--    
--     This timer is only applicable if cItpTcLinkType
--     is serial. A get on this object will return a
--     zero if the link is not serial.
--     
--           Min      Max      Def 
--           ======   ======   ======  
--     ANSI    5000    14000    11500  
--     ITU     5000   150000     5000 
--     
--     The SYNTAX statement allows values for both
--     the ANSI and ITU variants.
--  Refer
--    ITU Q.703 Signalling Link.
--     ANSI T1.111.3 Telecommunications - Signalling system
--     No. 7 (SS7)-Message Transfer Part (MTP).

CItpTcTimerMtp2T03 ::= Gauge(0|1000..14000)
-- TEXTUAL-CONVENTION
--  Status
--    mandatory
--  Descr
--    Aligned timer. The default and valid range is
--     dependant on the value of variant. 
--      
--     This timer is only applicable if cItpTcLinkType
--     is serial. A get on this object will return a
--     zero if the link is not serial.
--     
--           Min      Max      Def
--           ======   ======   ======  
--     ANSI    5000    14000    11500   
--     ITU     1000     2000     1500 
--     
--     The SYNTAX statement allows values for both
--     the ANSI and ITU variants. 
--  Refer
--    ITU Q.703 Signalling Link.
--     ANSI T1.111.3 Telecommunications - Signalling system
--     No. 7 (SS7)-Message Transfer Part (MTP).

CItpTcTimerMtp2T04E ::= Gauge(0|400..660)
-- TEXTUAL-CONVENTION
--  Status
--    mandatory
--  Descr
--    Proving period timer emergency timer. The default and
--     valid range is dependant on the value of 
--     variant.
--    
--     This timer is only applicable if cItpTcLinkType
--     is serial. A get on this object will return a
--     zero if the link is not serial.
--    
--           Min      Max      Def
--           ======   ======   ======  
--     ANSI     540      660      600    
--     ITU      400      600      500 
--     
--     The SYNTAX statement allows values for both
--     the ANSI and ITU variants. 
--  Refer
--    ITU Q.703 Signalling Link.
--    ANSI T1.111.3 Telecommunications - Signalling system
--    No. 7 (SS7)-Message Transfer Part (MTP).

CItpTcTimerMtp2T04N ::= Gauge(0|2007..9500)
-- TEXTUAL-CONVENTION
--  Status
--    mandatory
--  Descr
--    Proving period timer normal timer. The default and
--     valid range is dependant on the value of
--     variant.
--    
--     This timer is only applicable if cItpTcLinkType
--     is serial. A get on this object will return a
--     zero if the link is not serial.
--     
--           Min      Max      Def
--           ======   ======   ======  
--     ANSI    2007     2530     2300   
--     ITU     7500     9500     8200 
--     
--     The SYNTAX statement allows values for both
--     the ANSI and ITU variants. 
--  Refer
--    ITU Q.703 Signalling Link.
--     ANSI T1.111.3 Telecommunications - Signalling system
--     No. 7 (SS7)-Message Transfer Part (MTP).

CItpTcTimerMtp2T05 ::= Gauge(0|80..120)
-- TEXTUAL-CONVENTION
--  Status
--    mandatory
--  Descr
--    Sending SIB timer. The default and valid range is
--     dependant on the value of variant.
--    
--     This timer is only applicable if cItpTcLinkType
--     is serial. A get on this object will return a
--     zero if the link is not serial.
--    
--           Min      Max      Def
--           ======   ======   ======  
--     ANSI      80      120       80   
--     ITU       80      120      100 
--     
--     The SYNTAX statement allows values for both
--     the ANSI and ITU variants. 
--  Refer
--    ITU Q.703 Signalling Link.
--    ANSI T1.111.3 Telecommunications - Signalling system
--    No. 7 (SS7)-Message Transfer Part (MTP).

CItpTcTimerMtp2T06 ::= Gauge(1000..6000)
-- TEXTUAL-CONVENTION
--  Status
--    mandatory
--  Descr
--    Remote congestion timer. The default and valid range is
--     dependant on the value of variant.
--    
--           Min      Max      Def
--           ======   ======   ======  
--     ANSI    1000     6000     1000   
--     ITU     3000     6000     3000 
--     
--     The SYNTAX statement allows values for both
--     the ANSI, ITU variants and MTP2 Peer-to-Peer 
--     Adaptation Layer.
--  Refer
--    ITU Q.703 Signalling Link.
--    ANSI T1.111.3 Telecommunications - Signalling system
--    No. 7 (SS7)-Message Transfer Part (MTP).

CItpTcTimerMtp2T07 ::= Gauge(0|100..6000)
-- TEXTUAL-CONVENTION
--  Status
--    mandatory
--  Descr
--    Excessive delay of acknowledgement timer. The default
--     and valid range is dependant on the value of
--     variant().
--     
--     This timer is only applicable if cItpTcLinkType
--     is serial. A get on this object will return a
--     zero if the link is not serial.
--    
--          Min      Max      Def
--          ======   ======   ======  
--    ANSI     500     2000     1000    
--    ITU      500     2000     1000 
--    
--    The SYNTAX statement allows values for both
--    the ANSI and ITU variants.
--  Refer
--    ITU Q.703 Signalling Link.
--    ANSI T1.111.3 Telecommunications - Signalling system
--    No. 7 (SS7)-Message Transfer Part (MTP).

CItpTcTimerMtp3T01 ::= Gauge(500..1200)
-- TEXTUAL-CONVENTION
--  Status
--    mandatory
--  Descr
--    Delay to avoid message mis-sequencing on changeover.
--     Ranges by variant.
--     
--           Min      Max      Def
--           ======   ======   ======  
--     ANSI     500     1200      800   
--     ITU      500     1200      800   
--     
--     The SYNTAX statement allows values for both
--     the ANSI and ITU variants. 
--  Refer
--    ITU Q.704 Signalling network functions and messages.
--    ANSI T1.111 Telecommunications - Signalling system
--    No. 7 (SS7)-Message Transfer Part (MTP).

CItpTcTimerMtp3T02 ::= Gauge(700..2000)
-- TEXTUAL-CONVENTION
--  Status
--    mandatory
--  Descr
--    Waiting for changeover acknowledgement.
--     Ranges by variant.
--     
--           Min      Max      Def
--           ======   ======   ======  
--     ANSI     700     2000     1400      
--     ITU      700     2000     1400   
--     
--     The SYNTAX statement allows values for both
--     the ANSI and ITU variants. 
--  Refer
--    ITU Q.704 Signalling network functions and messages.
--    ANSI T1.111 Telecommunications - Signalling system
--    No. 7 (SS7)-Message Transfer Part (MTP).

CItpTcTimerMtp3T03 ::= Gauge(500..1200)
-- TEXTUAL-CONVENTION
--  Status
--    mandatory
--  Descr
--    Time controlled diversion-delay to avoid
--    mis-sequencing on change back.
--     Ranges by variant.
--     
--           Min      Max      Def
--           ======   ======   ======  
--     ANSI     500     1200      800      
--     ITU      500     1200      800   
--     
--     The SYNTAX statement allows values for both
--     the ANSI and ITU variants. 
--  Refer
--    ITU Q.704 Signalling network functions and messages.
--    ANSI T1.111 Telecommunications - Signalling system
--    No. 7 (SS7)-Message Transfer Part (MTP).

CItpTcTimerMtp3T04 ::= Gauge(500..1200)
-- TEXTUAL-CONVENTION
--  Status
--    mandatory
--  Descr
--    Waiting for change back acknowledgement (first
--    attempt).
--     Ranges by variant.
--     
--           Min      Max      Def
--           ======   ======   ======  
--     ANSI     500     1200      800      
--     ITU      500     1200      800   
--     
--     The SYNTAX statement allows values for both
--     the ANSI and ITU variants. 
--  Refer
--    ITU Q.704 Signalling network functions and messages.
--    ANSI T1.111 Telecommunications - Signalling system
--    No. 7 (SS7)-Message Transfer Part (MTP).

CItpTcTimerMtp3T05 ::= Gauge(500..1200)
-- TEXTUAL-CONVENTION
--  Status
--    mandatory
--  Descr
--    Waiting for change back acknowledgement (second
--     attempt).
--     Ranges by variant.
--     
--           Min      Max      Def
--           ======   ======   ======  
--     ANSI     500     1200      800      
--     ITU      500     1200      800   
--     
--     The SYNTAX statement allows values for both
--     the ANSI and ITU variants. 
--  Refer
--    ITU Q.704 Signalling network functions and messages.
--    ANSI T1.111 Telecommunications - Signalling system
--    No. 7 (SS7)-Message Transfer Part (MTP).

CItpTcTimerMtp3T06 ::= Gauge(500..1200)
-- TEXTUAL-CONVENTION
--  Status
--    mandatory
--  Descr
--    Delay to avoid message mis-sequencing on controlled
--     rerouting.
--     Ranges by variant.
--     
--           Min      Max      Def
--           ======   ======   ======  
--     ANSI     500     1200      800      
--     ITU      500     1200      800   
--     
--     The SYNTAX statement allows values for both
--     the ANSI and ITU variants. 
--  Refer
--    ITU Q.704 Signalling network functions and messages.
--    ANSI T1.111 Telecommunications - Signalling system
--    No. 7 (SS7)-Message Transfer Part (MTP).

CItpTcTimerMtp3T07 ::= Gauge(0|1000..2000)
-- TEXTUAL-CONVENTION
--  Status
--    mandatory
--  Descr
--    Waiting for Signalling data link connection
--     acknowledgement.
--     Ranges by variant.
--     
--           Min      Max      Def
--           ======   ======   ======  
--     ANSI    1000     2000     1500      
--     ITU     1000     2000     1500 
--     
--     The SYNTAX statement allows values for both
--     the ANSI and ITU variants. A value of zero 
--     indicates a value is not defined for a particular
--     variant or is not supported by the implementation.
--  Refer
--    ITU Q.704 Signalling network functions and messages.
--     ANSI T1.111 Telecommunications - Signalling system
--     No. 7 (SS7)-Message Transfer Part (MTP).

CItpTcTimerMtp3T08 ::= Gauge(800..1200)
-- TEXTUAL-CONVENTION
--  Status
--    mandatory
--  Descr
--    Transfer prohibited inhibition timer (transient
--     solution).
--     Ranges by variant.
--     
--           Min      Max      Def
--           ======   ======   ======  
--     ANSI     800     1200     1000    
--     ITU      800     1200     1000
--     
--     The SYNTAX statement allows values for both
--     the ANSI and ITU variants. 
--  Refer
--    ITU Q.704 Signalling network functions and messages.
--     ANSI T1.111 Telecommunications - Signalling system
--     No. 7 (SS7)-Message Transfer Part (MTP).

CItpTcTimerMtp3T10 ::= Gauge(30000..60000)
-- TEXTUAL-CONVENTION
--  Status
--    mandatory
--  Descr
--    Waiting to repeat Signalling routeset test message.
--     Ranges by variant.
--     
--           Min      Max      Def
--           ======   ======   ======  
--     ANSI   30000    60000    45000      
--     ITU    30000    60000    45000   
--     
--     The SYNTAX statement allows values for both
--     the ANSI and ITU variants. 
--  Refer
--    ITU Q.704 Signalling network functions and messages.
--     ANSI T1.111 Telecommunications - Signalling system
--     No. 7 (SS7)-Message Transfer Part (MTP).

CItpTcTimerMtp3T11 ::= Gauge(30000..90000)
-- TEXTUAL-CONVENTION
--  Status
--    mandatory
--  Descr
--    Transfer restricted timer. (This is one way of
--     implementing the function described in 13.4/Q.704 and
--     mainly intended to simplify SPs.).
--     Ranges by variant.
--     
--           Min      Max      Def
--           ======   ======   ======  
--     ANSI   30000    90000    60000      
--     ITU    30000    90000    60000   
--     
--     The SYNTAX statement allows values for both
--     the ANSI and ITU variants. 
--  Refer
--    ITU Q.704 Signalling network functions and messages.
--     ANSI T1.111 Telecommunications - Signalling system
--     No. 7 (SS7)-Message Transfer Part (MTP).

CItpTcTimerMtp3T12 ::= Gauge(800..1500)
-- TEXTUAL-CONVENTION
--  Status
--    mandatory
--  Descr
--    Waiting for uninhibit acknowledgement.
--     Ranges by variant.
--     
--           Min      Max      Def
--           ======   ======   ======  
--     ANSI     800     1500     1150      
--     ITU      800     1500     1150 
--     
--     The SYNTAX statement allows values for both
--     the ANSI and ITU variants. 
--  Refer
--    ITU Q.704 Signalling network functions and messages.
--     ANSI T1.111 Telecommunications - Signalling system
--     No. 7 (SS7)-Message Transfer Part (MTP).

CItpTcTimerMtp3T13 ::= Gauge(800..1500)
-- TEXTUAL-CONVENTION
--  Status
--    mandatory
--  Descr
--    Waiting for force uninhibit.
--     Ranges by variant.
--     
--           Min      Max      Def
--           ======   ======   ======  
--     ANSI     800     1500     1150    
--     ITU      800     1500     1150 
--     
--     The SYNTAX statement allows values for both
--     the ANSI and ITU variants. 
--  Refer
--    ITU Q.704 Signalling network functions and messages.
--     ANSI T1.111 Telecommunications - Signalling system
--    No. 7 (SS7)-Message Transfer Part (MTP).

CItpTcTimerMtp3T14 ::= Gauge(2000..3000)
-- TEXTUAL-CONVENTION
--  Status
--    mandatory
--  Descr
--    Waiting for inhibition acknowledgement.
--     Ranges by variant.
--     
--           Min      Max      Def
--           ======   ======   ======  
--     ANSI    2000     3000     2500      
--     ITU     2000     3000     2500   
--     
--     The SYNTAX statement allows values for both
--     the ANSI and ITU variants. 
--  Refer
--    ITU Q.704 Signalling network functions and messages.
--     ANSI T1.111 Telecommunications - Signalling system
--     No. 7 (SS7)-Message Transfer Part (MTP).

CItpTcTimerMtp3T15 ::= Gauge(2000..3000)
-- TEXTUAL-CONVENTION
--  Status
--    mandatory
--  Descr
--    Waiting to start Signalling routeset congestion
--     test. Ranges by variant.
--     
--           Min      Max      Def
--           ======   ======   ======  
--     ANSI    2000     3000     2500      
--     ITU     2000     3000     2500   
--     
--     The SYNTAX statement allows values for both
--     the ANSI and ITU variants. 
--  Refer
--    ITU Q.704 Signalling network functions and messages.
--     ANSI T1.111 Telecommunications - Signalling system
--     No. 7 (SS7)-Message Transfer Part (MTP).

CItpTcTimerMtp3T16 ::= Gauge(1400..2000)
-- TEXTUAL-CONVENTION
--  Status
--    mandatory
--  Descr
--    Waiting for routeset congestion status update.
--     Ranges by variant.
--     
--           Min      Max      Def
--           ======   ======   ======  
--     ANSI    1400     2000     1700      
--     ITU     1400     2000     1700   
--     
--     The SYNTAX statement allows values for both
--     the ANSI and ITU variants. 
--  Refer
--    ITU Q.704 Signalling network functions and messages.
--     ANSI T1.111 Telecommunications - Signalling system
--     No. 7 (SS7)-Message Transfer Part (MTP).

CItpTcTimerMtp3T17 ::= Gauge(800..1500)
-- TEXTUAL-CONVENTION
--  Status
--    mandatory
--  Descr
--    Delay to avoid oscillation of initial alignment
--     failure and link restart.
--     Ranges by variant.
--     
--           Min      Max      Def
--           ======   ======   ======  
--     ANSI     800     1500     1150       
--     ITU      800     1500     1150    
--     
--     The SYNTAX statement allows values for both
--     the ANSI and ITU variants. 
--  Refer
--    ITU Q.704 Signalling network functions and messages.
--     ANSI T1.111 Telecommunications - Signalling system
--     No. 7 (SS7)-Message Transfer Part (MTP).

CItpTcTimerMtp3T18 ::= Gauge(1000..31000)
-- TEXTUAL-CONVENTION
--  Status
--    mandatory
--  Descr
--    This timers servers different function based on the 
--     variant.
--     
--     ANSI: Repeat TFR once by response method
--     ITU:  MTP restart link supervision
--     
--           Min      Max      Def
--           ======   ======   ======  
--     ANSI    2000    20000    11000      
--     ITU     1000    31000    30000   
--     
--     The SYNTAX statement allows values for both
--     the ANSI and ITU variants. 
--  Refer
--    ITU Q.704 Signalling network functions and messages.
--     ANSI T1.111 Telecommunications - Signalling system
--     No. 7 (SS7)-Message Transfer Part (MTP).

CItpTcTimerMtp3T19 ::= Gauge(67000..600000)
-- TEXTUAL-CONVENTION
--  Status
--    mandatory
--  Descr
--    This timers servers different function based on the 
--     variant.
--     
--     ANSI: failed craft timer referral timer
--     ITU:  supervision timer during MTP restart
--     
--           Min      Max      Def
--           ======   ======   ======  
--     ANSI  480000   600000   540000      
--     ITU    67000    69000    68000   
--     
--     The SYNTAX statement allows values for both
--     the ANSI and ITU variants. 
--  Refer
--    ITU Q.704 Signalling network functions and messages.
--     ANSI T1.111 Telecommunications - Signalling system
--     No. 7 (SS7)-Message Transfer Part (MTP).

CItpTcTimerMtp3T20 ::= Gauge(1000..120000)
-- TEXTUAL-CONVENTION
--  Status
--    mandatory
--  Descr
--    This timers servers different function based on the 
--     variant.
--     
--     ANSI: waiting to repeat local inhibit test
--     ITU:  MTP restart timer at the Signalling point
--     
--           Min      Max      Def
--           ======   ======   ======  
--     ANSI   90000   120000   105000      
--     ITU     1000    61000    60000   
--     
--     The SYNTAX statement allows values for both
--     the ANSI and ITU variants. 
--  Refer
--    ITU Q.704 Signalling network functions and messages.
--     ANSI T1.111 Telecommunications - Signalling system
--     No. 7 (SS7)-Message Transfer Part (MTP).

CItpTcTimerMtp3T21 ::= Gauge(63000..120000)
-- TEXTUAL-CONVENTION
--  Status
--    mandatory
--  Descr
--    This timers servers different function based on the 
--     variant.
--     
--     ANSI: waiting to repeat remote inhibit test)       
--     ITU:  MTP restart timer at adjacent Signalling point
--     
--           Min      Max      Def
--           ======   ======   ======  
--     ANSI   90000   120000   105000      
--     ITU    63000    65000    64000   
--     
--     The SYNTAX statement allows values for both
--     the ANSI and ITU variants. 
--  Refer
--    ITU Q.704 Signalling network functions and messages.
--     ANSI T1.111 Telecommunications - Signalling system
--     No. 7 (SS7)-Message Transfer Part (MTP).

CItpTcTimerMtp3T22 ::= Gauge(36000..360000)
-- TEXTUAL-CONVENTION
--  Status
--    mandatory
--  Descr
--    This timers servers different function based on the 
--     variant.
--     
--     ANSI: restarting SP waiting for Signalling links avail
--     ITU:  local inhibit test timer 
--     
--           Min      Max      Def
--           ======   ======   ======  
--     ANSI   36000    60000    30000      
--     ITU    80000   360000   300000   
--     
--     The SYNTAX statement allows values for both
--     the ANSI and ITU variants. 
--  Refer
--    ITU Q.704 Signalling network functions and messages.
--     ANSI T1.111 Telecommunications - Signalling system
--     No. 7 (SS7)-Message Transfer Part (MTP).

CItpTcTimerMtp3T23 ::= Gauge(9000..360000)
-- TEXTUAL-CONVENTION
--  Status
--    mandatory
--  Descr
--    This timers servers different function based on the 
--     variant.
--     
--     ANSI: restarting SP waiting to receive all TRA msgs
--     ITU:  remote inhibit test timer
--     
--           Min      Max      Def
--           ======   ======   ======  
--     ANSI    9000    60000    30000      
--     ITU    80000   360000   300000   
--     
--     The SYNTAX statement allows values for both
--     the ANSI and ITU variants. 
--  Refer
--    ITU Q.704 Signalling network functions and messages.
--     ANSI T1.111 Telecommunications - Signalling system
--     No. 7 (SS7)-Message Transfer Part (MTP).

CItpTcTimerMtp3T24 ::= Gauge(500..60000)
-- TEXTUAL-CONVENTION
--  Status
--    mandatory
--  Descr
--    This timers servers different function based on the 
--     variant.
--     
--     ANSI: restarting SP waiting to broadcast all TRA msgs
--     ITU:  stabilizing timer after local processor outage
--     
--           Min      Max      Def
--           ======   ======   ======  
--     ANSI    9000    60000    30000    
--     ITU      500      500      500 
--     
--     The SYNTAX statement allows values for both
--     the ANSI and ITU variants. 
--  Refer
--    ITU Q.704 Signalling network functions and messages.
--     ANSI T1.111 Telecommunications - Signalling system
--     No. 7 (SS7)-Message Transfer Part (MTP).

CItpTcTimerMtp3T25 ::= Gauge(0|30000..35000)
-- TEXTUAL-CONVENTION
--  Status
--    mandatory
--  Descr
--    Timer at Signalling Point (SP) adjacent to restarting
--     SP, waiting for traffic restart allowed message.
--      Ranges by variant.
--      
--            Min      Max      Def
--            ======   ======   ======  
--      ANSI   30000    35000    30000      
--      
--      This timer is not used when the variant is ITU.
--      A value of zero indicates a value is not defined 
--      for a particular variant or is not supported by the
--      implementation.
--  Refer
--    ANSI T1.111 Telecommunications - Signalling system
--     No. 7 (SS7)-Message Transfer Part (MTP)

CItpTcTimerMtp3T26 ::= Gauge(0|12000..15000)
-- TEXTUAL-CONVENTION
--  Status
--    mandatory
--  Descr
--    Timer at restarting SP waiting to repeat traffic
--     restart waiting message.
--      Ranges by variant.
--      
--            Min      Max      Def
--            ======   ======   ======  
--      ANSI   12000    15000    12000     
--      
--      This timer is not used when the variant is ITU.
--      A value of zero indicates a value is not defined 
--      for a particular variant or is not supported by
--      the implementation.
--  Refer
--    ANSI T1.111 Telecommunications - Signalling system
--     No. 7 (SS7)-Message Transfer Part (MTP)

CItpTcTimerMtp3T27 ::= Gauge(0|2000..50000)
-- TEXTUAL-CONVENTION
--  Status
--    mandatory
--  Descr
--    Minimum duration of unavailability for full restart.
--     Ranges by variant.
--     
--           Min      Max      Def
--           ======   ======   ======  
--     ANSI    2000    50000     4000     
--     
--     This timer is not used when the variant is ITU.
--     A value of zero indicates a value is not defined 
--     for a particular variant or is not supported by
--     the implementation.
--  Refer
--    ANSI T1.111 Telecommunications - Signalling system
--     No. 7 (SS7)-Message Transfer Part (MTP)

CItpTcTimerMtp3T28 ::= Gauge(0|3000..35000)
-- TEXTUAL-CONVENTION
--  Status
--    mandatory
--  Descr
--    Timer at SP adjacent to restarting SP waiting for
--    traffic restart waiting message.
--     Ranges by variant.
--     
--           Min      Max      Def
--           ======   ======   ======  
--     ANSI    3000    35000    30000    
--     
--     This timer is not used when the variant is ITU.
--     A value of zero indicates a value is not defined 
--     for a particular variant or is not supported by
--     the implementation.
--  Refer
--    ANSI T1.111 Telecommunications - Signalling system
--     No. 7 (SS7)-Message Transfer Part (MTP)

CItpTcTimerMtp3T29 ::= Gauge(0|60000..65000)
-- TEXTUAL-CONVENTION
--  Status
--    mandatory
--  Descr
--    Timer started when TRA sent in response to unexpected
--     TRA or TRW.
--     Ranges by variant.
--     
--           Min      Max      Def
--           ======   ======   ======  
--     ANSI   60000    65000    63000      
--     
--     This timer is not used when the variant is ITU.
--     A value of zero indicates a value is not defined 
--     for a particular variant or is not supported by
--     the implementation.
--  Refer
--    ANSI T1.111 Telecommunications - Signalling system
--     No. 7 (SS7)-Message Transfer Part (MTP)

CItpTcTimerMtp3T30 ::= Gauge(0|30000..35000)
-- TEXTUAL-CONVENTION
--  Status
--    mandatory
--  Descr
--    Timer to limit sending of TFPs and TFRs in response
--     to unexpected TRA or TRW.
--     Ranges by variant.
--     
--           Min      Max      Def
--           ======   ======   ======  
--     ANSI   30000    35000    33000      
--     
--     This timer is not used when the variant is ITU.
--     A value of zero indicates a value is not defined 
--     for a particular variant or is not supported by
--     the implementation.
--  Refer
--    ANSI T1.111 Telecommunications - Signalling system
--     No. 7 (SS7)-Message Transfer Part (MTP)

CItpTcTimerMtp3T31 ::= Gauge(0|10000..120000)
-- TEXTUAL-CONVENTION
--  Status
--    mandatory
--  Descr
--    False link congestion detection timer.
--     Ranges by variant.
--     
--           Min      Max      Def
--           ======   ======   ======  
--     ANSI   10000   120000    60000     
--     
--     This timer is not used when the variant is ITU.
--     A value of zero indicates a value is not defined 
--     for a particular variant or is not supported by
--     the implementation.
--  Refer
--    ANSI T1.111 Telecommunications - Signalling system
--     No. 7 (SS7)-Message Transfer Part (MTP)

CItpTcTimerMtp3T32 ::= Gauge(0|5000..120000)
-- TEXTUAL-CONVENTION
--  Status
--    mandatory
--  Descr
--    Link oscillation timer - Procedure A.
--     Ranges by variant.
--     
--           Min      Max      Def
--           ======   ======   ======  
--     ANSI    5000   120000    60000      
--     
--     This timer is not used when the variant is ITU.
--     A value of zero indicates a value is not defined 
--     for a particular variant or is not supported by
--     the implementation.
--  Refer
--    ANSI T1.111 Telecommunications - Signalling system
--     No. 7 (SS7)-Message Transfer Part (MTP)

CItpTcTimerMtp3T33 ::= Gauge(0|60000..600000)
-- TEXTUAL-CONVENTION
--  Status
--    mandatory
--  Descr
--    Probation timer for link oscillation - Procedure B.
--     Ranges by variant.
--     
--           Min      Max      Def
--           ======   ======   ======  
--     ANSI   60000   600000   300000      
--     
--     This timer is not used when the variant is ITU.
--     A value of zero indicates a value is not defined 
--     for a particular variant or is not supported by
--     the implementation.
--  Refer
--    ANSI T1.111 Telecommunications - Signalling system
--     No. 7 (SS7)-Message Transfer Part (MTP)

CItpTcTimerMtp3T34 ::= Gauge(0|5000..120000)
-- TEXTUAL-CONVENTION
--  Status
--    mandatory
--  Descr
--    Suspension timer for link oscillation - Procedure B.
--     Ranges by variant.
--     
--           Min      Max      Def
--           ======   ======   ======  
--     ANSI    5000   120000    60000      
--     
--     This timer is not used when the variant is ITU.
--     A value of zero indicates a value is not defined 
--     for a particular variant or is not supported by
--     the implementation.
--  Refer
--    ANSI T1.111 Telecommunications - Signalling system
--    No. 7 (SS7)-Message Transfer Part (MTP)

CItpTcTimerLinkTest ::= Gauge(0|4000..12000)
-- TEXTUAL-CONVENTION
--  Status
--    mandatory
--  Descr
--    Signalling Link test acknowledgement timer.
--     
--            Min      Max      Def
--           ======   ======   ======  
--     ANSI    4000    12000     8000      
--     
--     This timer is not used when the variant is ITU.
--     A value of zero indicates a value is not defined 
--     for a particular variant or is not supported by
--     the implementation.
--  Refer
--    ITU Q.704 Signalling network functions and messages.
--     ANSI T1.111 Telecommunications - Signalling system
--     No. 7 (SS7)-Message Transfer Part (MTP).

CItpTcTimerLinkMessage ::= Gauge(0|30000..90000)
-- TEXTUAL-CONVENTION
--  Status
--    mandatory
--  Descr
--    Interval timer for sending test messages.
--     
--           Min      Max      Def
--           ======   ======   ======  
--     ANSI   30000    90000    60000      
--     
--     This timer is not used when the variant is ITU.
--     A value of zero indicates a value is not defined 
--     for a particular variant or is not supported by
--     the implementation.
--  Refer
--    ITU Q.704 Signalling network functions and messages.
--     ANSI T1.111 Telecommunications - Signalling system
--     No. 7 (SS7)-Message Transfer Part (MTP).

CItpTcTimerLinkActRetry ::= Gauge(0|60000..90000)
-- TEXTUAL-CONVENTION
--  Status
--    mandatory
--  Descr
--    Link activation retry timer.
--     
--           Min      Max      Def
--           ======   ======   ======  
--     ANSI   60000    90000    60000      
--     
--     This timer is not used when the variant is ITU.
--     A value of zero indicates a value is not defined 
--     for a particular variant or is not supported by
--     the implementation.
--  Refer
--    ITU Q.704 Signalling network functions and messages.
--     ANSI T1.111 Telecommunications - Signalling system
--     No. 7 (SS7)-Message Transfer Part (MTP).

CItpTcTranslationType ::= INTEGER {
        tt(1),
        ssn(2)
        }
-- TEXTUAL-CONVENTION
--  Status
--    mandatory
--  Descr
--    The Translation Type for SCCP GTT GTA specifies Title 
--     Translation or Subsystem Number (SSN)
--    'tt'  : The GTT GTA has specified Title Translation
--    'ssn' : The GTT GTA has specified Subsystem Number.

CItpTcURL ::= OCTET STRING(SIZE(0..255))
-- TEXTUAL-CONVENTION
--  Status
--    mandatory
--  Descr
--    The URL used to load a configuration file.
--         
--     An octet string specified by an administrator that must
--     be in human-readable form.  The names must conform to 
--     the allowed characters that can be specified via 
--     Command Line Interface(CLI).  The names cannot contain
--     control character and should not contain leading or 
--     trailing white space.

CItpTcXuaName ::= OCTET STRING(SIZE(0..12))
-- TEXTUAL-CONVENTION
--  Status
--    mandatory
--  Descr
--    The configured name associated with M3UA/SUA
--     ASP or AS name.
--     
--     An octet string specified by an administrator that
--     must be in human-readable form.  The names must
--     conform to the allowed characters that can be 
--     specified via Command Line Interface(CLI).  The 
--     names cannot contain control character and should 
--     not contain leading or trailing white space.


END
