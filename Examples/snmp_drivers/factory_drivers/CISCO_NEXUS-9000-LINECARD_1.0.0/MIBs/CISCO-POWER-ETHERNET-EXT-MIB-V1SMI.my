-- MIB file created 28-Aug-2007 15:15:46, by
--   SMICng version 2.2.11-beta(PRO)(Solaris), January 20, 2001. Enterprise key cisco.com

CISCO-POWER-ETHERNET-EXT-MIB DEFINITIONS ::= BEGIN

-- From file: "CISCO-POWER-ETHERNET-EXT-MIB.my"
-- Compile options "4 7 F H N O W 03 06 0B 0G 0N 0T"

IMPORTS
    TruthValue
            FROM SNMPv2-TC-v1
    pethPsePortGroupIndex, pethPsePortIndex, pethMainPseGroupIndex
            FROM POWER-ETHERNET-MIB
    ciscoMgmt
            FROM CISCO-SMI
    EntPhysicalIndexOrZero
            FROM CISCO-TC
    SnmpAdminString
            FROM SNMP-FRAMEWORK-MIB
    Gauge
            FROM RFC1155-SMI
    OBJECT-TYPE
            FROM RFC-1212;

ciscoPowerEthernetExtMIB OBJECT IDENTIFIER ::= { ciscoMgmt 402 }
-- MODULE-IDENTITY
--  LastUpdated
--    200612190000Z
--  OrgName
--    Cisco Systems, Inc.
--  ContactInfo
--    Cisco Systems
--    Customer Service
--    
--    Postal: 170 W Tasman Drive
--    San Jose, CA 95134
--    USA
--    
--    Tel: +1 800 553-NETS
--    
--    E-mail: cs-lan-switch-snmp@cisco.com
--  Descr
--    A MIB module for extending the POWER-ETHERNET-MIB
--    (RFC3621) to add objects which provide additional
--    management information about Power Sourcing Equipment
--    (PSE) not available in POWER-ETHERNET-MIB.
--    
--    Glossary
--    
--    Power Sourcing Equipment (PSE)
--        These are devices supplying electrical power to
--        other equipment. They are, for example, inline power
--        switches, inline power daughterboards and power patch
--        panels.
--    
--    Powered Device (PD)
--        These are devices receiving their electrical power
--        supply from Power Sourcing Equipment. They are, for
--        example, IP telephones and wireless access points
--        or bridges.
--  RevDate
--    200612190000Z
--  RevDescr
--    Added cpeExtPsePortEntPhyIndex,
--    cpeExtPsePortPolicingCapable and 
--    cpeExtPsePortPolicingEnable to cpeExtPsePortTable.
--    Added cpeExtPdStatsTotalDevices and cpeExtPdStatsTable.
--  RevDate
--    200506100000Z
--  RevDescr
--    Added 'limit' to cpeExtPsePortEnable, 'overdraw' to
--    cpeExtPsePortAdditionalStatus and the groups
--    cpeExtPsePortPwrMonitorGroup and
--    cpeExtMainPseGroup.
--  RevDate
--    200404120000Z
--  RevDescr
--    Initial version of this MIB module.

cpeExtMIBNotifs OBJECT IDENTIFIER ::= { ciscoPowerEthernetExtMIB 0 }
cpeExtMIBObjects OBJECT IDENTIFIER ::= { ciscoPowerEthernetExtMIB 1 }
cpeExtMIBConformance OBJECT IDENTIFIER ::= { ciscoPowerEthernetExtMIB 2 }
cpeExtPdStatistics OBJECT IDENTIFIER ::= { cpeExtMIBObjects 4 }
cpeExtMIBCompliances OBJECT IDENTIFIER ::= { cpeExtMIBConformance 1 }
cpeExtMIBGroups OBJECT IDENTIFIER ::= { cpeExtMIBConformance 2 }

cpeExtDefaultAllocation OBJECT-TYPE
    SYNTAX Gauge
--  Units
--    milliwatts
    ACCESS read-write
    STATUS mandatory
    DESCRIPTION
        "This object indicates the default inline power allocation per
        port. This is a global configuration parameter that applies
        to all inline power capable ports in the system.
        
        The system must consider this object as well as the per port
        configuration object, cpeExtPsePortPwrMax, when determining
        how much power to allocate to a port. The system will use the
        lower of the two numbers."
    ::= { cpeExtMIBObjects 1 }

cpeExtPsePortTable OBJECT-TYPE
    SYNTAX SEQUENCE OF CpeExtPsePortEntry
    ACCESS not-accessible
    STATUS mandatory
    DESCRIPTION
        "This table extends the POWER-ETHERNET-MIB pethPsePortTable
        for power Ethernet ports on a Powered Sourcing Equipment
        (PSE) device."
    REFERENCE
        "RFC3621"
    ::= { cpeExtMIBObjects 2 }

cpeExtPsePortEntry OBJECT-TYPE
    SYNTAX CpeExtPsePortEntry
    ACCESS not-accessible
    STATUS mandatory
    DESCRIPTION
        "A cpeExtPsePortEntry extends a corresponding
        pethPsePortTable entry. This entry displays and
        controls more characteristics of a power Ethernet
        port on a PSE device."
    INDEX { pethPsePortGroupIndex, pethPsePortIndex }
-- Augments pethPsePortEntry FROM POWER-ETHERNET-MIB
    ::= { cpeExtPsePortTable 1 }

CpeExtPsePortEntry ::= SEQUENCE {
    cpeExtPsePortEnable INTEGER,
    cpeExtPsePortDiscoverMode INTEGER,
    cpeExtPsePortDeviceDetected TruthValue,
    cpeExtPsePortIeeePd TruthValue,
    cpeExtPsePortAdditionalStatus OCTET STRING,
    cpeExtPsePortPwrMax Gauge,
    cpeExtPsePortPwrAllocated Gauge,
    cpeExtPsePortPwrAvailable Gauge,
    cpeExtPsePortPwrConsumption Gauge,
    cpeExtPsePortMaxPwrDrawn Gauge,
    cpeExtPsePortEntPhyIndex EntPhysicalIndexOrZero,
    cpeExtPsePortPolicingCapable TruthValue,
    cpeExtPsePortPolicingEnable INTEGER
    }

cpeExtPsePortEnable OBJECT-TYPE
    SYNTAX INTEGER {
        auto(1),
        static(2),
        limit(3)
        }
    ACCESS read-write
    STATUS mandatory
    DESCRIPTION
        "This object is an extension of the pethPsePortAdminEnable
        object from RFC3621. It allows the user to be more specific
        when enabling the PSE functions. The states, 'auto', 'static'
        and 'limit' correspond to a value of 'true' for the
        pethPsePortAdminEnable object. However, if the value of
        pethPsePortAdminEnable is 'false', then the value of this
        object is irrelevant.
        
        Setting this value to 'auto' enables Powered Device discovery
        on the interface and the amount of power allocated depends on
        the Powered Device discovered. If pethPsePortAdminEnable was
        'false' prior to this set operation, then it will become
        'true'.
        
        Setting this value to 'static' will also enable Powered
        Device discovery. However, this is different from 'auto'
        in that the amount of power is pre-allocated based on the
        configuration on the Power Sourcing Equipment. If
        pethPsePortAdminEnable was 'false' prior to this set
        operation, then it will become 'true'.
        
        Setting this value to 'limit' enables Powered Device
        discovery on the interface. The amount of power allocated
        depends on the Powered Device discovered and the value
        of cpeExtPsePortPwrMax. The lower value will be used.
        If pethPsePortAdminEnable was 'false' prior to this set
        operation, then it will become 'true'.
        
        When setting the pethPsePortAdminEnable object to 'true'
        this object will adopt the value of 'auto'.
        
        If cpeExtPsePortPolicingCapable of the PSE port, or
        cpeExtMainPsePwrMonitorCapable of the PSE port's 
        main group, has the value of 'false', this object 
        can only be set to 'auto' or 'static'; Otherwise, 
        this object can be set to 'auto', 'static' or 'limit'."
    ::= { cpeExtPsePortEntry 1 }

cpeExtPsePortDiscoverMode OBJECT-TYPE
    SYNTAX INTEGER {
        unknown(1),
        off(2),
        ieee(3),
        cisco(4),
        ieeeAndCisco(5)
        }
    ACCESS read-only
    STATUS mandatory
    DESCRIPTION
        "This object indicates the discover mode used by the system to
        discover the PD.
        
        A value of 'unknown' indicates that the discover mode on the
        interface is unknown.
        
        A value of 'off' indicates that discovery is disabled on the
        interface.
        
        A value of 'ieee' indicates that the discover mode on the
        interface is IEEE based.
        
        A value of 'cisco' indicates that the discover mode on the
        interface is Cisco based.
        
        A value of 'ieeeAndCisco' indicates that the discover mode on
        the interface is both IEEE and Cisco based."
    ::= { cpeExtPsePortEntry 2 }

cpeExtPsePortDeviceDetected OBJECT-TYPE
    SYNTAX TruthValue
--    Rsyntax INTEGER {
--        true(1),
--        false(2)
--        }
    ACCESS read-only
    STATUS mandatory
    DESCRIPTION
        "This object indicates if a Powered Device (PD) has been
        detected on the interface.
        
        A value of 'true' indicates that a PD has been detected on
        the interface.
        
        A value of 'false' indicates that no PD has been detected on
        the interface."
    ::= { cpeExtPsePortEntry 3 }

cpeExtPsePortIeeePd OBJECT-TYPE
    SYNTAX TruthValue
--    Rsyntax INTEGER {
--        true(1),
--        false(2)
--        }
    ACCESS read-only
    STATUS mandatory
    DESCRIPTION
        "This object indicates whether the Powered Device attached
        to the interface is an IEEE compliant Powered Device or not.
        
        A value of 'true' indicates the attached Powered Device is
        an IEEE compliant Powered Device.
        
        A value of 'false' indicates the attached Powered Device
        is not an IEEE compliant Powered Device. This also means
        that the value of the corresponding object from the
        pethPsePortTable, pethPsePortPowerClassifications is
        irrelevant."
    ::= { cpeExtPsePortEntry 4 }

cpeExtPsePortAdditionalStatus OBJECT-TYPE
    SYNTAX OCTET STRING(SIZE(1..2))
        -- BITS are:
        --   deny(0)
        --   overdraw(1)
    ACCESS read-only
    STATUS mandatory
    DESCRIPTION
        "This object is an extension of the pethPsePortDetectionStatus
        object from RFC3621 and provides additional status
        information.
        
        deny: When set, the PD attached to the interface is being
              denied power due to insufficient power resources on
              the Power Sourcing Equipment.
        
        overdraw: When set, the PD attached to the interface is
                  being denied power because the PD is trying
                  to consume more power than it has been
                  configured to consume."
    ::= { cpeExtPsePortEntry 5 }

cpeExtPsePortPwrMax OBJECT-TYPE
    SYNTAX Gauge
--  Units
--    milliwatts
    ACCESS read-write
    STATUS mandatory
    DESCRIPTION
        "This indicates the maximum amount of power that the PSE will
        make available to the PD connected to this interface."
    ::= { cpeExtPsePortEntry 6 }

cpeExtPsePortPwrAllocated OBJECT-TYPE
    SYNTAX Gauge
--  Units
--    milliwatts
    ACCESS read-only
    STATUS mandatory
    DESCRIPTION
        "This object indicates the amount of power allocated from the
        PSE for the PD."
    ::= { cpeExtPsePortEntry 7 }

cpeExtPsePortPwrAvailable OBJECT-TYPE
    SYNTAX Gauge
--  Units
--    milliwatts
    ACCESS read-only
    STATUS mandatory
    DESCRIPTION
        "This object indicates the amount of power available for
        the PD to use. This value may differ from the value
        cpeExtPsePortPwrAllocated due to the efficiency issues
        of delivering the power from the PSE to the PD.
        
        When sufficient power is available to power a PD, this
        value should be equal to the lower of the two objects,
        cpeExtDefaultAllocation and cpeExtPsePortPwrMax."
    ::= { cpeExtPsePortEntry 8 }

cpeExtPsePortPwrConsumption OBJECT-TYPE
    SYNTAX Gauge
--  Units
--    milliwatts
    ACCESS read-only
    STATUS mandatory
    DESCRIPTION
        "This indicates the actual power consumption of the PD
        connected to this interface. It may not necessarily
        be equal to the value of cpeExtPsePortPwrAvailable."
    ::= { cpeExtPsePortEntry 9 }

cpeExtPsePortMaxPwrDrawn OBJECT-TYPE
    SYNTAX Gauge
--  Units
--    milliwatts
    ACCESS read-only
    STATUS mandatory
    DESCRIPTION
        "This indicates the maximum amount of power drawn by the PD
        connected to this interface, since it was powered on."
    ::= { cpeExtPsePortEntry 10 }

cpeExtPsePortEntPhyIndex OBJECT-TYPE
    SYNTAX EntPhysicalIndexOrZero
--    Rsyntax INTEGER(0..2147483647)
    ACCESS read-only
    STATUS mandatory
    DESCRIPTION
        "The entPhysicalIndex value that uniquely identifies the
        PSE port. If the PSE port does not have a corresponding 
        physical entry in entPhysicalTable or if the 
        entPhysicalTable is not supported by the management
        system, this object has the value of zero."
    REFERENCE
        "RFC 2737, entPhysicalIndex."
    ::= { cpeExtPsePortEntry 11 }

cpeExtPsePortPolicingCapable OBJECT-TYPE
    SYNTAX TruthValue
--    Rsyntax INTEGER {
--        true(1),
--        false(2)
--        }
    ACCESS read-only
    STATUS mandatory
    DESCRIPTION
        "This object indicates whether the PSE port hardware is
        capable of policing the port for proper power consumption 
        based on the allocated value."
    ::= { cpeExtPsePortEntry 12 }

cpeExtPsePortPolicingEnable OBJECT-TYPE
    SYNTAX INTEGER {
        on(1),
        off(2)
        }
    ACCESS read-write
    STATUS mandatory
    DESCRIPTION
        "This object allows the user to turn on or turn off the
        power policing of the PSE port. If the instance value of 
        cpeExtPsePortPolicingCapable is 'TRUE', the user is allowed
        to set this object to 'on' or 'off'. Otherwise, this
        object is read-only and always has the value of 'off'."
    ::= { cpeExtPsePortEntry 13 }

cpeExtMainPseTable OBJECT-TYPE
    SYNTAX SEQUENCE OF CpeExtMainPseEntry
    ACCESS not-accessible
    STATUS mandatory
    DESCRIPTION
        "This table contains the additional information for the
        main PSE group in pethMainPseTable."
    REFERENCE
        "RFC3621, pethMainPseTable"
    ::= { cpeExtMIBObjects 3 }

cpeExtMainPseEntry OBJECT-TYPE
    SYNTAX CpeExtMainPseEntry
    ACCESS not-accessible
    STATUS mandatory
    DESCRIPTION
        "A cpeExtMainPseEntry contains information about
        a particular pethMainPseGroupIndex. An entry is
        created by the agent when a main PSE group is added
        to the pethMainPseTable. An entry is deleted by the
        agent when a main PSE group is removed from the
        pethMainPseTable."
    REFERENCE
        "RFC3621, pethMainPseTable"
    INDEX { pethMainPseGroupIndex }
    ::= { cpeExtMainPseTable 1 }

CpeExtMainPseEntry ::= SEQUENCE {
    cpeExtMainPseEntPhyIndex EntPhysicalIndexOrZero,
    cpeExtMainPseDescr SnmpAdminString,
    cpeExtMainPsePwrMonitorCapable TruthValue
    }

cpeExtMainPseEntPhyIndex OBJECT-TYPE
    SYNTAX EntPhysicalIndexOrZero
--    Rsyntax INTEGER(0..2147483647)
    ACCESS read-only
    STATUS mandatory
    DESCRIPTION
        "The entPhysicalIndex value that uniquely identifies the
        main PSE group. If the main PSE group does not have a
        corresponding physical entry in entPhysicalTable or if
        the entPhysicalTable is not supported by the management
        system, then this object has the value of zero."
    REFERENCE
        "RFC 2737, entPhysicalIndex."
    ::= { cpeExtMainPseEntry 1 }

cpeExtMainPseDescr OBJECT-TYPE
    SYNTAX SnmpAdminString
--    Rsyntax OCTET STRING(SIZE(0..255))
    ACCESS read-only
    STATUS mandatory
    DESCRIPTION
        "A textual string containing information about the Power
        Source Equipment (PSE) group."
    ::= { cpeExtMainPseEntry 2 }

cpeExtMainPsePwrMonitorCapable OBJECT-TYPE
    SYNTAX TruthValue
--    Rsyntax INTEGER {
--        true(1),
--        false(2)
--        }
    ACCESS read-only
    STATUS mandatory
    DESCRIPTION
        "This object indicates if the given group is capable of
        monitoring the power consumption of the interfaces that
        belong to the group. The value 'true' means that the
        group is capable. The value 'false' means that the group
        in not capable."
    ::= { cpeExtMainPseEntry 3 }

cpeExtPdStatsTotalDevices OBJECT-TYPE
    SYNTAX Gauge
    ACCESS read-only
    STATUS mandatory
    DESCRIPTION
        "This object indicates the total number of the
        powered devices with any power classifications
        in the system.
        
        Classification is a way to tag different terminals
        on the Power over LAN network according to their
        power consumption. Devices such as IP telephones,
        WLAN access points and others, will be classified
        according to their power requirements."
    REFERENCE
        "IEEE Std 802.3af Section 30.9.1.1.6
         aPSEPowerClassification"
    ::= { cpeExtPdStatistics 1 }

cpeExtPdStatsTable OBJECT-TYPE
    SYNTAX SEQUENCE OF CpeExtPdStatsEntry
    ACCESS not-accessible
    STATUS mandatory
    DESCRIPTION
        "This table contains the statistics information
        of the powered devices fallen into different power
        classifications in the system."
    REFERENCE
        "IEEE Std 802.3af Section 30.9.1.1.6
               aPSEPowerClassification"
    ::= { cpeExtPdStatistics 2 }

cpeExtPdStatsEntry OBJECT-TYPE
    SYNTAX CpeExtPdStatsEntry
    ACCESS not-accessible
    STATUS mandatory
    DESCRIPTION
        "A cpeExtPdStatsEntry contains the statistics
        information about a particular power classification
        defined in cpeExtPdStatsIndex."
    INDEX { cpeExtPdStatsClass }
    ::= { cpeExtPdStatsTable 1 }

CpeExtPdStatsEntry ::= SEQUENCE {
    cpeExtPdStatsClass INTEGER,
    cpeExtPdStatsDeviceCount Gauge
    }

cpeExtPdStatsClass OBJECT-TYPE
    SYNTAX INTEGER {
        cisco(1),
        class0(2),
        class1(3),
        class2(4),
        class3(5)
        }
    ACCESS not-accessible
    STATUS mandatory
    DESCRIPTION
        "The power classification as the index for the
        statistics information for powered devices.
        
        A value of 'cisco' indicates that the powered
        devices are CISCO proprietary and their power 
        classification does not fall into any class
        in IEEE specifications.
        
        A value of 'class0' indicates that the power 
        classification of the powered devices falls into
        class 0 in IEEE specifications.
        
        A value of 'class1' indicates that the power
        classification of the powered devices falls into
        class 1 in IEEE specifications.
        
        A value of 'class2' indicates that the power
        classification of the powered devices falls into
        class 2 in IEEE specifications.
        
        A value of 'class3' indicates that the power
        classification of the powered devices falls into
        class 3 in IEEE specifications."
    REFERENCE
        "IEEE Std 802.3af Section 30.9.1.1.6
               aPSEPowerClassification"
    ::= { cpeExtPdStatsEntry 1 }

cpeExtPdStatsDeviceCount OBJECT-TYPE
    SYNTAX Gauge
    ACCESS read-only
    STATUS mandatory
    DESCRIPTION
        "This object indicates the count of the powered
        devices whose power classification falls into 
        a specific value of cpeExtPdStatsIndex."
    ::= { cpeExtPdStatsEntry 2 }

cpeExtPsePortGroup OBJECT IDENTIFIER ::= { cpeExtMIBGroups 1 }
-- OBJECT-GROUP
--  Status
--    mandatory
--  Descr
--    This group provides information and configuration objects
--    in addition to those provided in the POWER-ETHERNET-MIB
--    (RFC3621).
--  objects
--    cpeExtPsePortEnable, cpeExtPsePortDiscoverMode, 
--    cpeExtPsePortDeviceDetected, cpeExtPsePortIeeePd, 
--    cpeExtPsePortAdditionalStatus, cpeExtPsePortPwrMax, 
--    cpeExtPsePortPwrAllocated, cpeExtPsePortPwrAvailable, 
--    cpeExtPsePortPwrConsumption

cpeExtPsePortGlobalConfigGroup OBJECT IDENTIFIER ::= { cpeExtMIBGroups 2 }
-- OBJECT-GROUP
--  Status
--    mandatory
--  Descr
--    This is a collection of objects which provide global
--    configuration of the PSE interfaces.
--  objects
--    cpeExtDefaultAllocation

cpeExtPsePortPwrMonitorGroup OBJECT IDENTIFIER ::= { cpeExtMIBGroups 3 }
-- OBJECT-GROUP
--  Status
--    mandatory
--  Descr
--    This is a collection of objects which provide power
--    monitoring on PD's connected to the PSE interfaces.
--  objects
--    cpeExtPsePortMaxPwrDrawn

cpeExtMainPseGroup OBJECT IDENTIFIER ::= { cpeExtMIBGroups 4 }
-- OBJECT-GROUP
--  Status
--    deprecated
--  Descr
--    This is a collection of objects which provide
--    additional information for the PSE group.
--  objects
--    cpeExtMainPseEntPhyIndex, cpeExtMainPseDescr, 
--    cpeExtMainPsePwrMonitorCapable

cpeExtPortEntityIndexGroup OBJECT IDENTIFIER ::= { cpeExtMIBGroups 5 }
-- OBJECT-GROUP
--  Status
--    mandatory
--  Descr
--    This is a collection of objects which provide
--    entity physical index information for PSE port.
--  objects
--    cpeExtPsePortEntPhyIndex

cpeExtPortPolicingGroup OBJECT IDENTIFIER ::= { cpeExtMIBGroups 6 }
-- OBJECT-GROUP
--  Status
--    mandatory
--  Descr
--    This is a collection of objects which provide
--    the hardware power consumption policing information 
--    for PSE port.
--  objects
--    cpeExtPsePortPolicingCapable, cpeExtPsePortPolicingEnable

cpeExtPdStatsGroup OBJECT IDENTIFIER ::= { cpeExtMIBGroups 7 }
-- OBJECT-GROUP
--  Status
--    mandatory
--  Descr
--    This is a collection of objects which provide
--    the statistics information for powered devices.
--  objects
--    cpeExtPdStatsTotalDevices, cpeExtPdStatsDeviceCount

cpeExtMainPseGroup2 OBJECT IDENTIFIER ::= { cpeExtMIBGroups 8 }
-- OBJECT-GROUP
--  Status
--    mandatory
--  Descr
--    This is a collection of objects which provide
--    additional information to identify the PSE group.
--  objects
--    cpeExtMainPseEntPhyIndex, cpeExtMainPseDescr

cpeExtPseGrpPwrGroup OBJECT IDENTIFIER ::= { cpeExtMIBGroups 9 }
-- OBJECT-GROUP
--  Status
--    mandatory
--  Descr
--    This is a collection of objects which provide
--    power monitoring information for the PSE group.
--  objects
--    cpeExtMainPsePwrMonitorCapable

cpeExtMIBCompliance OBJECT IDENTIFIER ::= { cpeExtMIBCompliances 1 }
-- MODULE-COMPLIANCE
--  Status
--    deprecated
--  Descr
--    The compliance statement for the
--    CISCO-POWER-ETHERNET-EXT-MIB.
--  Module
--    >>current<<
--   MandGroup
--    cpeExtPsePortGroup
--   OptGroup
--    cpeExtPsePortGlobalConfigGroup

cpeExtMIBCompliance2 OBJECT IDENTIFIER ::= { cpeExtMIBCompliances 2 }
-- MODULE-COMPLIANCE
--  Status
--    deprecated
--  Descr
--    The compliance statement for the
--    CISCO-POWER-ETHERNET-EXT-MIB.
--  Module
--    >>current<<
--   MandGroup
--    cpeExtPsePortGroup
--   OptGroup
--    cpeExtPsePortGlobalConfigGroup
--   OptGroup
--    cpeExtPsePortPwrMonitorGroup
--   OptGroup
--    cpeExtMainPseGroup

cpeExtMIBCompliance3 OBJECT IDENTIFIER ::= { cpeExtMIBCompliances 3 }
-- MODULE-COMPLIANCE
--  Status
--    mandatory
--  Descr
--    The compliance statement for the
--    CISCO-POWER-ETHERNET-EXT-MIB.
--  Module
--    >>current<<
--   MandGroup
--    cpeExtPsePortGroup
--   OptGroup
--    cpeExtPsePortGlobalConfigGroup
--   OptGroup
--    cpeExtPsePortPwrMonitorGroup
--   OptGroup
--    cpeExtMainPseGroup2
--   OptGroup
--    cpeExtPseGrpPwrGroup
--   OptGroup
--    cpeExtPortEntityIndexGroup
--   OptGroup
--    cpeExtPortPolicingGroup
--   OptGroup
--    cpeExtPdStatsGroup


END
