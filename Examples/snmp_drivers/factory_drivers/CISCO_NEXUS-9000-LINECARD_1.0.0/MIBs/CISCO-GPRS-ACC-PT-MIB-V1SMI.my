-- MIB file created 13-May-2008 22:56:17, by
--   SMICng version 2.2.11-beta(PRO)(Solaris), January 20, 2001. Enterprise key cisco.com

CISCO-GPRS-ACC-PT-MIB DEFINITIONS ::= BEGIN

-- From file: "CISCO-GPRS-ACC-PT-MIB.my"
-- Compile options "4 7 F H N O W 03 06 0B 0G 0N 0T"

IMPORTS
    TruthValue, RowStatus, DisplayString
            FROM SNMPv2-TC-v1
    SnmpAdminString
            FROM SNMP-FRAMEWORK-MIB
    InetAddressType, InetAddress, InetPortNumber
            FROM INET-ADDRESS-MIB
    InterfaceIndexOrZero, CiscoInetAddressMask
            FROM CISCO-TC
    ciscoMgmt
            FROM CISCO-SMI
    Counter, Gauge, IpAddress
            FROM RFC1155-SMI
    OBJECT-TYPE
            FROM RFC-1212
    TRAP-TYPE
            FROM RFC-1215;

ciscoGprsAccPtMIB OBJECT IDENTIFIER ::= { ciscoMgmt 183 }
-- MODULE-IDENTITY
--  LastUpdated
--    200803030000Z
--  OrgName
--    Cisco Systems, Inc.
--  ContactInfo
--    Cisco Systems
--    Customer Service
--    
--    Postal: 170 W Tasman Drive
--    San Jose, CA  95134
--    USA
--    
--    Tel: +1 800 553-NETS
--    
--    E-mail: cs-gprs@cisco.com
--  Descr
--    This MIB module supports access point configuration
--    for GGSN in a GPRS system. GPRS [1] is a GSM network 
--    providing mobile wireless data communication services.
--    
--    GGSN is the Gateway GPRS Support Node in the GPRS
--    architecture. It provides interworking with external 
--    packet-switched networks - PDNs or other data networks. 
--    
--    GGSN is a software extension of a router.
--    
--    A GGSN provides data access for its mobile subscribers 
--    to parts of the data network identified by the list of 
--    APNs configured on the node. 
--    
--    The following diagram illustrates the network 
--    elements in a GPRS network, and the interfaces 
--    between them: 
--    
--        +=====+    +======+      +======+      +=====+ 
--        | BSS |====| SGSN |==Gn==| GGSN |==Gi==| PDN |
--        +=====+    +======+      +======+      +=====+ 
--           ^                         ^
--          /|\                       /|\
--           |                         |
--           | Visited access      +========+
--           | provider network    | Access |
--           |                     | point  |
--          \|/                    | table  |
--           V                     +========+
--        +=====+
--        | MS  |
--        +=====+
--    
--    Access points must be configured on the GGSN.
--    The Access Point Name is defined in GSM 03.03 [2] and 
--    consists of two parts, the APN Network Identifier and 
--    the APN Operator Identifier (more details in the 
--    object description in this MIB module). The 
--    cgprsAccPtTable contains the list of APNs supported 
--    by this GGSN and a set of engineering parameters that 
--    define the access point's operation. 
--    
--    Acronyms and terms:
--    
--        APN    Access Point Name
--    
--        BSS    Base Station Subsystem
--    
--        CAC    Call Admission Control
--    
--        COA    Change of Authorization
--    
--        ETSI   European Telecommunications Standards 
--               Instititute 
--    
--        Gi     Name of the Interface between GGSN and PDN
--    
--        Gn     Name of the Interface between GGSN and SGSN
--    
--        GGSN   Gateway GPRS Support Node
--    
--        GPRS   General Packet Radio Service 
--    
--        GSM    Global System for Mobile communication
--    
--        IMS    IP Multimedia Subsystem
--    
--        MS     Mobile Station
--    
--        P-CSCF Proxy Call Session Control Function
--    
--        PCO    Protocol Config Options
--    
--        PDF    Policy Decision Function
--    
--        PDN    Public Data Network 
--    
--        PDP    Packet Data Protocol         
--    
--        PLMN   Public Land Mobile Network
--    
--        SGSN   Serving GPRS support Node
--    
--        UE     User Equipment
--    
--        VPN    Virtual Private Network
--    
--        VRF    VPN Routing and Forwarding
--    
--    REFERENCE
--    
--    [1] GSM 03.60: Digital cellular telecommunications 
--        system (Phase 2+); General Packet Radio Service 
--        (GPRS); Service description; Stage 2.
--    
--    [2] GSM 03.03: Digital cellular telecommunication 
--        system (Phase 2+); General Packet Radio Service 
--        (GPRS); Service description; Stage 1.
--  RevDate
--    200803030000Z
--  RevDescr
--    Added cgprsAccPtAaaAccountInterRadius to
--    cgprsAccPtExtTable.
--  RevDate
--    200802270000Z
--  RevDescr
--    Added cgprsAccPtGtpUpdateFailDelete,
--    cgprsAccPtAaaAccountInterPeriod to
--    cgprsAccPtExtTable.
--    
--    Added cgprsAccPtPdpUpdateReqSent,
--    cgprsAccPtSuccPdpUpdateResRcvd,
--    cgprsAccPtCoaRcvd,
--    cgprsAccPtCoaSuccess,
--    cgprsAccPtDtEnabled to
--    cgprsAccPtStatisticsTable.
--  RevDate
--    200608300000Z
--  RevDescr
--    Deprecated cgprsAccPtImsConfigTable, as IMS is
--    not supported from GGSN release 5.0 onwards.
--    
--    Added cgprsAccPtPcscfServerGroupName to 
--    cgprsAccPtTable.
--  RevDate
--    200605181300Z
--  RevDescr
--    Added cgprsAccPtIpv6Configs to ciscoGprsAccPtConfig.
--    
--    Added following objects to cgprsAccPtStatisticsTable:
--     cgprsAccPtIpv6MsActivatedPdps,
--     cgprsAccPtIpv6MsSuccActivatedPdps,
--     cgprsAccPtIpv6NetworkInitDeactPdps,
--     cgprsAccPtIpv6NetworkInitDeactSuccPdps,
--     cgprsAccPtIpv6MsActivatedDynPdps,
--     cgprsAccPtIpv6MsSuccActivatedDynPdps,
--     cgprsAccPtIpv6MsDeactivatedPdps,
--     cgprsAccPtIpv6MsSuccDeactivatedPdps,
--     cgprsAccPtIpv6GgsnDeactivatedPdps,
--     cgprsAccPtIpv6GgsnSuccDeactivatedPdps,
--     cgprsAccPtIpv6UpstreamTrafficVolume,
--     cgprsAccPtIpv6DownstreamTrafficVolume,
--     cgprsAccPtIpv6UpstreamPackets,
--     cgprsAccPtIpv6DownstreamPackets.
--  RevDate
--    200511221400Z
--  RevDescr
--    Changed the range of cgprsAccPtName and
--    cgprsAccPtMsIsdnSuppressedValue.
--  RevDate
--    200510281700Z
--  RevDescr
--    Modified the description for the object
--    cgprsAccPtName.
--    
--    Modified the description for the object
--    cgprsAccPtChgProfile.
--    
--    Added new value to the object
--    cgprsAccPtType.
--    
--    Added new objects cgprsAccPtServiceAware,
--    cgprsAccPtAdvDownlinkNextHopAddrType,
--    cgprsAccPtAdvDownlinkNextHopAddr to 
--    cgprsAccPtExtTable.
--  RevDate
--    200407260200Z
--  RevDescr
--    Modified the description for the object
--    cgprsAccPtChgProfile.
--  RevDate
--    200402112000Z
--  RevDescr
--    + Added cgprsAccPtInterimAccountinEnable,
--    cgprsAccPtSetRadiusAttributes,
--    cgprsAccPtOperationMode,
--    cgprsAccPtAbsoluteSessionTimer,
--    cgprsAccPtRadiusAttrNasId,
--    cgprsAccPtPdpInServicePolicyName,
--    cgprsAccPtPdpOutServicePolicyNam,
--    cgprsAccPtPppRegenVerifyDomain,
--    cgprsAccPtIpAddrLocalPoolName to cgprsAccPtExtTable.
--    
--    + Added cgprsAccPtGenServerConfigs,
--    cgprsAccPtImsConfigs, cgprsAccPtChargingParams,
--    cgprsAccPtCacConfigs, cgprsAccPtRouteProbeConfigs to
--    ciscoGprsAccPtConfig.
--    
--    + Added cgprsAccPtThruputStatsTable to
--    ciscoGprsAccPtStatistics.
--    
--    + Added cgprsAccPtRevUpstreamTrafficVol,
--    cgprsAccPtRevDownstrTrafficVol,
--    cgprsAccPtUpstreamPacketCount,
--    cgprsAccPtDownstreamPacketCount,
--    cgprsAccPtDhcpAddrRequests,
--    cgprsAccPtSuccDhcpAddrRequests,
--    cgprsAccPtDhcpAddrReleases to
--    cgprsAccPtStatisticsTable.
--    
--    + Added cgprsAccPtSecSrcViolNotif,
--    cgprsAccPtSecDestViolNotif,
--    cgprsAccPtMaintenanceNotif and 
--    cgprsAccPtInServiceNotif to
--    cgprsAccPtMIBNotifications.
--    
--    + Deprecated cgprsAccPtUpstreamTrafficVol,
--    cgprsAccPtDownstreamTrafficVol.
--  RevDate
--    200208261800Z
--  RevDescr
--    + Added cgprsAccPtSuppressRadiusAttribs to
--    cgprsAccPtExtTable.
--    + Deprecated cgprsAccPtImsiSuppressed.
--  RevDate
--    200206131800Z
--  RevDescr
--    + Added cgprsAccPtImsiSuppressed,
--    cgprsAccPtVerifyUpStrTpduSrcAddr,
--    cgprsAccPtVerifyUpStrTpduDstAddr,
--    cgprsAccPtRedirInterMobilAddrTyp,
--    cgprsAccPtRedirInterMobilAddr to cgprsAccPtExtTable.
--    + Added cgprsAccPtSourceAddrViolTpdus,
--    cgprsAccPtDestAddrViolTpdus,
--    cgprsAccPtRedirInterMobilTraffic to 
--    cgprsAccPtStatisticsTable.
--    + Updated the DESCRIPTION and DEFVAL of 
--    cgprsAccPtPppRegenMaxSessions.
--    + Updated the DESCRIPTION of 
--    cgprsAccPtMsIsdnSuppressed.
--  RevDate
--    200112281430Z
--  RevDescr
--    + Added cgprsAccPtExtTable.
--    + Added cgprsAccPtType, cgprsAccPtVrfName,
--      cgprsAccPtDhcpAddrSpace,
--      cgprsAccPtPppRegenEnable, 
--      cgprsAccPtPppRegenMaxSessions,
--      cgprsAccPtPppRegenSetupTime, 
--      cgprsAccPtAutoAggregation.
--    + Added objects for performance data measurements
--      related to GGSN.
--    + Added cgprsAccPtIdlePdpPurgeTimer, 
--      cgprsAccPtBlockMsRoaming,
--      cgprsAccPtAnonymousUserName, 
--      cgprsAccPtAnonymousUserPassword
--      cgprsAccPtMsIsdnSuppressed, 
--      cgprsAccPtMsIsdnSuppressedValue,
--      cgprsAccPtAaaAuthServerGroup,
--      cgprsAccPtAaaAccountServerGroup,
--      cgprsAccPtAaaAccountingEnable.
--    + Deprecated cgprsAccPtUsers, cgprsAccPtRadiusServerPri
--      and cgprsAccPtRadiusServerSec.
--  RevDate
--    200007210000Z
--  RevDescr
--    Initial version of this MIB module.

ciscoGprsAccPtMIBObjects OBJECT IDENTIFIER ::= { ciscoGprsAccPtMIB 1 }
ciscoGprsAccPtConfig OBJECT IDENTIFIER ::= { ciscoGprsAccPtMIBObjects 1 }
ciscoGprsAccPtCfgNotifInfo OBJECT IDENTIFIER ::= { ciscoGprsAccPtMIBObjects 2 }
ciscoGprsAccPtStatistics OBJECT IDENTIFIER ::= { ciscoGprsAccPtMIBObjects 3 }
ciscoGprsAccPtNotifInfo OBJECT IDENTIFIER ::= { ciscoGprsAccPtMIBObjects 4 }
cgprsAccPtGenServerConfigs OBJECT IDENTIFIER ::= { ciscoGprsAccPtConfig 4 }
cgprsAccPtImsConfigs OBJECT IDENTIFIER ::= { ciscoGprsAccPtConfig 5 }
cgprsAccPtChargingParams OBJECT IDENTIFIER ::= { ciscoGprsAccPtConfig 6 }
cgprsAccPtCacConfigs OBJECT IDENTIFIER ::= { ciscoGprsAccPtConfig 7 }
cgprsAccPtRouteProbeConfigs OBJECT IDENTIFIER ::= { ciscoGprsAccPtConfig 8 }
cgprsAccPtIpv6Configs OBJECT IDENTIFIER ::= { ciscoGprsAccPtConfig 9 }
cgprsAccPtMIBNotificationPrefix OBJECT IDENTIFIER ::= { ciscoGprsAccPtMIB 2 }
cgprsAccPtMIBNotifications OBJECT IDENTIFIER ::= { cgprsAccPtMIBNotificationPrefix 0 }
cgprsAccPtConformances OBJECT IDENTIFIER ::= { ciscoGprsAccPtMIB 3 }
cgprsAccPtMIBCompliances OBJECT IDENTIFIER ::= { cgprsAccPtConformances 1 }
cgprsAccPtMIBGroups OBJECT IDENTIFIER ::= { cgprsAccPtConformances 2 }

AccessControlListId ::= INTEGER(1..2699)
-- TEXTUAL-CONVENTION
--  Status
--    mandatory
--  Descr
--    Access Control List (ACL) specifies criteria by
--    which packets are evaluated as matching or
--    non-matching. The ACL also specifies an action
--    which is applied to packets which match.
--    Objects which use this textual convention identify
--    ACLs. 
--    
--    ACLs are configured/defined outside the scope of 
--    this MIB. The value of an object with this syntax 
--    associates to an ACL with the same ACL number.

AccessControlListOrZero ::= INTEGER(0..199|1300..2699)
-- TEXTUAL-CONVENTION
--  Status
--    mandatory
--  Descr
--    Access Control List (ACL) specifies criteria by
--    which packets are evaluated as matching or
--    non-matching. The ACL also specifies an action
--    which is applied to packets which match.
--    Objects which use this textual convention identify
--    ACLs.
--    
--    ACLs are configured/defined outside the scope of
--    this MIB. The value of an object with this syntax
--    associates to an ACL with the same ACL number.
--    
--    A value of zero indicates no ACL is configured.

AccessControlListName ::= OCTET STRING(SIZE(0..255))
-- TEXTUAL-CONVENTION
--  Status
--    mandatory
--  Descr
--    Access Control List (ACL) specifies the criteria by
--    which packets are evaluated as matching or
--    non-matching. The ACL also specifies an action,
--    which is applied to packets which match.
--    Objects which use this textual convention identify
--    ACLs.
--    
--    ACLs are configured/defined outside the scope of
--    this MIB. The name of an object with this syntax
--    associates to an ACL with the same ACL name.

cgprsAccPtTable OBJECT-TYPE
    SYNTAX SEQUENCE OF CgprsAccPtEntry
    ACCESS not-accessible
    STATUS mandatory
    DESCRIPTION
        "This table contains a list of access points configured
        on this GGSN."
    ::= { ciscoGprsAccPtConfig 1 }

cgprsAccPtEntry OBJECT-TYPE
    SYNTAX CgprsAccPtEntry
    ACCESS not-accessible
    STATUS mandatory
    DESCRIPTION
        "A description of an access point. Access point
        parameters cannot be changed when active PDP's exists 
        on the GGSN."
    INDEX { cgprsAccPtIndex }
    ::= { cgprsAccPtTable 1 }

CgprsAccPtEntry ::= SEQUENCE {
    cgprsAccPtIndex Gauge,
    cgprsAccPtRowStatus RowStatus,
    cgprsAccPtName SnmpAdminString,
    cgprsAccPtMode INTEGER,
    cgprsAccPtIpAddressPool INTEGER,
    cgprsAccPtDHCPServerPri IpAddress,
    cgprsAccPtDHCPServerSec IpAddress,
    cgprsAccPtDHCPGwAddr IpAddress,
    cgprsAccPtRadiusServerPri IpAddress,
    cgprsAccPtRadiusServerSec IpAddress,
    cgprsAccPtIPAccListGroupIn AccessControlListId,
    cgprsAccPtIPAccListGroupOut AccessControlListId,
    cgprsAccPtIfIndex InterfaceIndexOrZero,
    cgprsAccPtIfNextHop IpAddress,
    cgprsAccPtAccessViolation INTEGER,
    cgprsAccPtSubrRequired TruthValue,
    cgprsAccPtNetworkInitiated TruthValue,
    cgprsAccPtIpAddrAllocations Gauge,
    cgprsAccPtUsers Gauge,
    cgprsAccPtIdlePdpPurgeTimer Gauge,
    cgprsAccPtBlockMsRoaming TruthValue,
    cgprsAccPtAnonymousUserName SnmpAdminString,
    cgprsAccPtAnonymousUserPassword SnmpAdminString,
    cgprsAccPtMsIsdnSuppressed TruthValue,
    cgprsAccPtMsIsdnSuppressedValue DisplayString,
    cgprsAccPtAaaAuthServerGroup SnmpAdminString,
    cgprsAccPtAaaAccountServerGroup SnmpAdminString,
    cgprsAccPtAaaAccountingEnable TruthValue,
    cgprsAccPtType INTEGER,
    cgprsAccPtVrfName SnmpAdminString,
    cgprsAccPtDhcpAddrSpace INTEGER,
    cgprsAccPtPppRegenEnable TruthValue,
    cgprsAccPtPppRegenMaxSessions INTEGER,
    cgprsAccPtPppRegenSetupTime INTEGER,
    cgprsAccPtAutoAggregation TruthValue,
    cgprsAccPtPcscfServerGroupName SnmpAdminString
    }

cgprsAccPtIndex OBJECT-TYPE
    SYNTAX Gauge(1..65535)
    ACCESS not-accessible
    STATUS mandatory
    DESCRIPTION
        "A locally unique identifier for this access point on
        this GGSN."
    ::= { cgprsAccPtEntry 1 }

cgprsAccPtRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create or delete conceptual
        row in this table.
        
        To create a row, set this object to 'createAndGo'.
        There are no mandatory objects in a create request.
        
        To delete a row, set this object to 'destroy'."
    ::= { cgprsAccPtEntry 2 }

cgprsAccPtName OBJECT-TYPE
    SYNTAX SnmpAdminString(SIZE(0..100))
--    Rsyntax OCTET STRING(SIZE(0..100))
    ACCESS read-write
    STATUS mandatory
    DESCRIPTION
        "The Access Point Name. It is composed of two parts:
        
        - The APN Network Identifier is mandatory and is a 
          fully qualified domain name according to the DNS
          naming conventions, e.g., 'company.com.'. 
        
        - The APN Operator Identifier is optional. It is a
          fully qualified domain name according to the DNS
          naming convention, and consists of three labels,
          the last of which must be '.gprs'. For example, 
          'mncyyyy.mcczzzz.gprs'.
        
        An example of a full APN name with both the Network
        and operator identifiers is 
        'company.com.mncyyyy.mcczzzz.gprs'."
    REFERENCE
        "GSM 03.03: Digital cellular telecommunication system 
        (Phase 2+); General Packet Radio Service (GPRS); 
        Service description; Stage 1."
    DEFVAL { ''H }
    ::= { cgprsAccPtEntry 3 }

cgprsAccPtMode OBJECT-TYPE
    SYNTAX INTEGER {
        transparent(1),
        nontransparent(2)
        }
    ACCESS read-write
    STATUS mandatory
    DESCRIPTION
        "Specifies the type of access allowed to the PDN
        through this access point.
        
            - 'transparent', indicates that users can access 
            without authentication.
        
            - 'nontransparent', indicates that users must 
            be authenticated by the GGSN."
    DEFVAL { transparent }
    ::= { cgprsAccPtEntry 4 }

cgprsAccPtIpAddressPool OBJECT-TYPE
    SYNTAX INTEGER {
        global(1),
        dhcp(2),
        radius(3),
        disable(4),
        local(5)
        }
    ACCESS read-write
    STATUS mandatory
    DESCRIPTION
        "Specifies a dynamic address allocation method for
        this access point.
        
            - 'global', which indicates that no method is 
            defined specifically to this access point and the 
            DHCP or radius server configured for this GGSN 
            'globally' will be used to allocation a dynamic IP 
            address to the user. 
        
            - 'dhcp', which indicates that the DHCP server 
            will be used.
        
            - 'radius', which indicates that the radius server
            will be used.
        
            - 'disable', which indicates that dynamic address 
            allocation is disabled.
        
            - 'local', indicates that local address pool
            configured on the GGSN is going to be used.
            cgprsAccPtIpAddrLocalPoolName denotes the name
            of the corresponding address pool."
    DEFVAL { global }
    ::= { cgprsAccPtEntry 5 }

cgprsAccPtDHCPServerPri OBJECT-TYPE
    SYNTAX IpAddress
    ACCESS read-write
    STATUS mandatory
    DESCRIPTION
        "This object specifies the IP address of the primary
        DHCP server from which a mobile subscriber can request
        an IP address assignment for the access of this APN.
        
        In case this DHCP server is not available, the 
        secondary DHCP server is used."
    ::= { cgprsAccPtEntry 6 }

cgprsAccPtDHCPServerSec OBJECT-TYPE
    SYNTAX IpAddress
    ACCESS read-write
    STATUS mandatory
    DESCRIPTION
        "The IP address of the secondary DHCP server.
        
        The secondary DHCP server is used if the primary
        DHCP server is not available. This object can be
        set after configuring primary DHCP server."
    ::= { cgprsAccPtEntry 7 }

cgprsAccPtDHCPGwAddr OBJECT-TYPE
    SYNTAX IpAddress
    ACCESS read-write
    STATUS mandatory
    DESCRIPTION
        "This object specifies the DHCP gateway address that
        is used in the 'giaddr' field of the DHCP request. 
        It is used by DHCP to determine from which pool the 
        IP address will be allocated. 
        
        If no DHCP gateway is specified, the IP address 
        associated with the Gn interface is used."
    ::= { cgprsAccPtEntry 8 }

cgprsAccPtRadiusServerPri OBJECT-TYPE
    SYNTAX IpAddress
    ACCESS read-write
    STATUS obsolete
    DESCRIPTION
        "This object specifies the IP address of the primary
        RADIUS server used by this access point to 
        authenticate and/or authorize mobile users to access 
        the PDN.
        
        In case this RADIUS server is not available, the 
        secondary will be used.
        
        Obsoleted by cgprsAccPtAaaAuthServerGroup and
        cgprsAccPtAaaAccountServerGroup."
    ::= { cgprsAccPtEntry 9 }

cgprsAccPtRadiusServerSec OBJECT-TYPE
    SYNTAX IpAddress
    ACCESS read-write
    STATUS obsolete
    DESCRIPTION
        "Specifies a secondary RADIUS server.
        
        The secondary RADIUS server will be used if the primary 
        RADIUS server is not available.
        
        Obsoleted by cgprsAccPtAaaAuthServerGroup and
        cgprsAccPtAaaAccountServerGroup."
    ::= { cgprsAccPtEntry 10 }

cgprsAccPtIPAccListGroupIn OBJECT-TYPE
    SYNTAX AccessControlListId
--    Rsyntax INTEGER(1..2699)
    ACCESS read-write
    STATUS mandatory
    DESCRIPTION
        "This object specifies the ACL against which to compare
        packets received at this Access Point from the PDN for
        forwarding towards an MS.
        
        Access list at the access point level is used to 
        control which packets are allowed access between the 
        APN and the MS. Access violations by a packet according
        to the rules in this ACL could cause this packet to be
        dropped or its PDP session terminated. Which of these
        treatments is taken is specified by the object
        cgprsAccPtAccessViolation.
        
        This object is ignored if cgprsAccPtIPAccListInEnable 
        is set to 'false'."
    ::= { cgprsAccPtEntry 11 }

cgprsAccPtIPAccListGroupOut OBJECT-TYPE
    SYNTAX AccessControlListId
--    Rsyntax INTEGER(1..2699)
    ACCESS read-write
    STATUS mandatory
    DESCRIPTION
        "This object specifies the ACL against which to compare
        packets originated by an MS and received by at this 
        Access Point for forwarding to the PDN.
        
        Access list at the access point level is used to 
        control which packets are allowed access between the 
        APN and the MS. Access violations by a packet according
        to the rules in this ACL could cause this packet to be
        dropped or its PDP session terminated. Which of these
        treatments is taken is specified by the object
        cgprsAccPtAccessViolation.
        
        This object is ignored if cgprsAccPtIPAccListOutEnable 
        is set to 'false'."
    ::= { cgprsAccPtEntry 12 }

cgprsAccPtIfIndex OBJECT-TYPE
    SYNTAX InterfaceIndexOrZero
--    Rsyntax INTEGER(0..2147483647)
    ACCESS read-write
    STATUS obsolete
    DESCRIPTION
        "Specifies an interface to be used by GGSN on Gi
        interface. 
        
        The value zero indicates that no interface is 
        specified. 
        
        The cgprsAccPtIfNextHop must be specified if this 
        object is set to the Gi associated interface."
    DEFVAL { 0 }
    ::= { cgprsAccPtEntry 13 }

cgprsAccPtIfNextHop OBJECT-TYPE
    SYNTAX IpAddress
    ACCESS read-write
    STATUS obsolete
    DESCRIPTION
        "Specifies the IP address of the next hop for the
        Gi interface, specified by cgprsAccPtIfIndex.
        
        This value is mandatory if the value of 
        cgprsAccPtIfIndex is non-zero. Setting the 
        cgprsAccPtIfIndex object to zero will reset this 
        object to the value of '00000000'H, which means 
        it is not used."
    ::= { cgprsAccPtEntry 14 }

cgprsAccPtAccessViolation OBJECT-TYPE
    SYNTAX INTEGER {
        discardPacket(1),
        terminateSession(2)
        }
    ACCESS read-write
    STATUS mandatory
    DESCRIPTION
        "Specifies how access violation should be treated.
        
        An access violation occurs if the IP packets violates
        any rules in ACL as specified by either 
        cgprsAccPtIPAccListGroupIn or 
        cgprsAccPtIPAccListGroupOut.
        
            - 'discardPacket', packets are discarded.
        
            - 'terminateSession', the user's session is 
            terminated."
    DEFVAL { discardPacket }
    ::= { cgprsAccPtEntry 15 }

cgprsAccPtSubrRequired OBJECT-TYPE
    SYNTAX TruthValue
--    Rsyntax INTEGER {
--        true(1),
--        false(2)
--        }
    ACCESS read-write
    STATUS mandatory
    DESCRIPTION
        "This object indicates if a user needs to subscribe
        to this access point before accessing it."
    DEFVAL { false }
    ::= { cgprsAccPtEntry 16 }

cgprsAccPtNetworkInitiated OBJECT-TYPE
    SYNTAX TruthValue
--    Rsyntax INTEGER {
--        true(1),
--        false(2)
--        }
    ACCESS read-write
    STATUS mandatory
    DESCRIPTION
        "This object indicates whether network (PDN)
        initiated PDP sessions are allowed for this access 
        point. The more common case, is false, which 
        indicates that the PDP is initiated by the MS."
    DEFVAL { false }
    ::= { cgprsAccPtEntry 17 }

cgprsAccPtIpAddrAllocations OBJECT-TYPE
    SYNTAX Gauge
    ACCESS read-only
    STATUS mandatory
    DESCRIPTION
        "Indicates the number of IP addresses allocated to
        MS's.
        
        Trigger Condition: This gauge is 
        incremented/decremented by successful completion of
        create/delete dynamic PDP context request message
        respectively."
    ::= { cgprsAccPtEntry 18 }

cgprsAccPtUsers OBJECT-TYPE
    SYNTAX Gauge
    ACCESS read-only
    STATUS obsolete
    DESCRIPTION
        "The number of mobile subscribers currently accessing
        this APN.  Obsoleted by cgprsAccPtActivePdps."
    ::= { cgprsAccPtEntry 19 }

cgprsAccPtIdlePdpPurgeTimer OBJECT-TYPE
    SYNTAX Gauge(0..168)
--  Units
--    hours
    ACCESS read-write
    STATUS mandatory
    DESCRIPTION
        "This object indicates maximum idle connection time
        allowed to the PDP context before termination of the 
        GTP session.  A value of 0 means session idle timer 
        is not used."
    DEFVAL { 0 }
    ::= { cgprsAccPtEntry 20 }

cgprsAccPtBlockMsRoaming OBJECT-TYPE
    SYNTAX TruthValue
--    Rsyntax INTEGER {
--        true(1),
--        false(2)
--        }
    ACCESS read-write
    STATUS mandatory
    DESCRIPTION
        "This object indicates whether access to a roaming
        MS needs to be blocked for this APN."
    DEFVAL { false }
    ::= { cgprsAccPtEntry 21 }

cgprsAccPtAnonymousUserName OBJECT-TYPE
    SYNTAX SnmpAdminString
--    Rsyntax OCTET STRING(SIZE(0..255))
    ACCESS read-write
    STATUS mandatory
    DESCRIPTION
        "This object specifies the anonymous user name, which
        is used when a MS tries to access a non-transparent 
        APN without supplying user name and password."
    REFERENCE
        "GSM 03.03: Digital cellular telecommunication
        system (Phase 2+); General Packet Radio Service
        (GPRS); Service description; Stage 1."
    ::= { cgprsAccPtEntry 22 }

cgprsAccPtAnonymousUserPassword OBJECT-TYPE
    SYNTAX SnmpAdminString
--    Rsyntax OCTET STRING(SIZE(0..255))
    ACCESS read-write
    STATUS mandatory
    DESCRIPTION
        "This object specifies the password corresponding
        to cgprsAccPtAnonymousUserName.  For security reasons, 
        retrieving this object returns a zero-length string."
    REFERENCE
        "GSM 03.03: Digital cellular telecommunication
        system (Phase 2+); General Packet Radio Service
        (GPRS); Service description; Stage 1."
    ::= { cgprsAccPtEntry 23 }

cgprsAccPtMsIsdnSuppressed OBJECT-TYPE
    SYNTAX TruthValue
--    Rsyntax INTEGER {
--        true(1),
--        false(2)
--        }
    ACCESS read-write
    STATUS mandatory
    DESCRIPTION
        "This object specifies whether the ISDN ID used
        by the MS, when authenticating with a radius server,
        needs to be suppressed or not.  When set to 'true', 
        the ISDN ID attribute will not be sent by the GGSN.
        When set to 'false', the ISDN ID attribute will be 
        sent by the GGSN.  To set this object to 'true', AAA
        radius group for authentication should have been
        configured on the GGSN(either at global or APN level)."
    REFERENCE
        "GSM 09.02: Digital cellular telecommunication
        system (Phase 2+); Mobile Application Part (MAP) 
        specification."
    DEFVAL { false }
    ::= { cgprsAccPtEntry 24 }

cgprsAccPtMsIsdnSuppressedValue OBJECT-TYPE
    SYNTAX DisplayString(SIZE(0..20))
--    Rsyntax OCTET STRING(SIZE(0..20))
    ACCESS read-write
    STATUS mandatory
    DESCRIPTION
        "This object specifies the value that will be
        transmitted to the radius server in place of 
        mobile stations ISDN ID.  This object can only 
        be set if cgprsAccPtMsIsdnSuppressed is 'true'.
        
        Valid characters for this object are 0..9, 
        a, b, c, * and #.  If no value is set, no MS-ISDN
        ID will be sent to the radius server."
    REFERENCE
        "GSM 09.02: Digital cellular telecommunication
        system (Phase 2+); Mobile Application Part (MAP) 
        specification."
    DEFVAL { ''H }
    ::= { cgprsAccPtEntry 25 }

cgprsAccPtAaaAuthServerGroup OBJECT-TYPE
    SYNTAX SnmpAdminString
--    Rsyntax OCTET STRING(SIZE(0..255))
    ACCESS read-write
    STATUS mandatory
    DESCRIPTION
        "This object specifies the AAA radius server group
        that is used for authentication by this APN."
    ::= { cgprsAccPtEntry 26 }

cgprsAccPtAaaAccountServerGroup OBJECT-TYPE
    SYNTAX SnmpAdminString
--    Rsyntax OCTET STRING(SIZE(0..255))
    ACCESS read-write
    STATUS mandatory
    DESCRIPTION
        "This object specifies the AAA radius server group
        that is used for accounting by this APN.  If no
        group is specified for accounting,
        cgprsAccPtAaaAuthServerGroup will be used."
    ::= { cgprsAccPtEntry 27 }

cgprsAccPtAaaAccountingEnable OBJECT-TYPE
    SYNTAX TruthValue
--    Rsyntax INTEGER {
--        true(1),
--        false(2)
--        }
    ACCESS read-write
    STATUS mandatory
    DESCRIPTION
        "This object is used to enable accounting when the
        APN is in 'transparent' mode.  When the object is set to
        'true', cgprsAccPtAaaAccountServerGroup is used for
        accounting.  If cgprsAccPtAaaAccountServerGroup is not
        specified, cgprsAccPtAaaAuthServerGroup will be used.
        
        When the APN is in 'non-transparent' mode, the 
        accounting will always be enabled i.e., this object 
        will be 'true' by default."
    ::= { cgprsAccPtEntry 28 }

cgprsAccPtType OBJECT-TYPE
    SYNTAX INTEGER {
        real(1),
        virtual(2),
        virtualPreAuth(3)
        }
    ACCESS read-write
    STATUS mandatory
    DESCRIPTION
        "This object specifies the type of APN.
        
        'virtual' - Specifies an APN type that is not 
        associated with any specific physical target network 
        on the GGSN.  When this object is set to 'virtual', 
        all other APN parameters are ignored.
        
        'real' - Specifies an APN type that corresponds to a 
        physical interface to an external network on the GGSN.
        
        'virtualPreAuth' - Specifies an APN type that is not
        associated with any specific physical target network
        on the GGSN. It applies a pre-authentication phase 
        for any create PDP request that includes a virtual 
        APN. During pre-authentication, an Access-Request 
        message is sent to an AAA server and the AAA server 
        then returns a target APN encoded in a Radius 
        attribute in the Access-Accept message."
    DEFVAL { real }
    ::= { cgprsAccPtEntry 29 }

cgprsAccPtVrfName OBJECT-TYPE
    SYNTAX SnmpAdminString
--    Rsyntax OCTET STRING(SIZE(0..255))
    ACCESS read-write
    STATUS mandatory
    DESCRIPTION
        "This object specifies the name of the VRF with
        which this APN is associated."
    ::= { cgprsAccPtEntry 30 }

cgprsAccPtDhcpAddrSpace OBJECT-TYPE
    SYNTAX INTEGER {
        global(1),
        vrf(2)
        }
    ACCESS read-write
    STATUS mandatory
    DESCRIPTION
        "This object specifies the address space used
        by the dhcp server.  This object can only be
        set if cgprsAccPtDHCPServerPri is set."
    DEFVAL { global }
    ::= { cgprsAccPtEntry 31 }

cgprsAccPtPppRegenEnable OBJECT-TYPE
    SYNTAX TruthValue
--    Rsyntax INTEGER {
--        true(1),
--        false(2)
--        }
    ACCESS read-write
    STATUS mandatory
    DESCRIPTION
        "This object is used to enable GGSN to regenerate
        a PPP session for each IP PDP context on this APN."
    DEFVAL { false }
    ::= { cgprsAccPtEntry 32 }

cgprsAccPtPppRegenMaxSessions OBJECT-TYPE
    SYNTAX INTEGER(1..65535)
    ACCESS read-write
    STATUS mandatory
    DESCRIPTION
        "This object specifies the maximum number of regenerated
        PPP sessions allowed for this access-point.
        
        This object can only be set if cgprsAccPtPppRegenEnable
        is set to 'true'.
        
        The maximum value that can be held by this object
        depends on the GGSN platform used."
    DEFVAL { 65535 }
    ::= { cgprsAccPtEntry 33 }

cgprsAccPtPppRegenSetupTime OBJECT-TYPE
    SYNTAX INTEGER(1..65535)
--  Units
--    seconds
    ACCESS read-write
    STATUS mandatory
    DESCRIPTION
        "This object specifies the maximum tolerance time within
        which a regenerated PPP session has to fully come up.
        
        This object can only be set if cgprsAccPtPppRegenEnable
        is set to 'true'."
    DEFVAL { 60 }
    ::= { cgprsAccPtEntry 34 }

cgprsAccPtAutoAggregation OBJECT-TYPE
    SYNTAX TruthValue
--    Rsyntax INTEGER {
--        true(1),
--        false(2)
--        }
    ACCESS read-write
    STATUS mandatory
    DESCRIPTION
        "This object is used to enable auto aggregation on this
        APN.  When a user tries to configure entries in 
        cgprsAccPtAggregTable, this object will automatically 
        be set to 'false'. When this object is set to 'true',
        the entries in cgprsAccPtAggregTable, if any, will be
        deleted."
    DEFVAL { false }
    ::= { cgprsAccPtEntry 35 }

cgprsAccPtPcscfServerGroupName OBJECT-TYPE
    SYNTAX SnmpAdminString(SIZE(0..100))
--    Rsyntax OCTET STRING(SIZE(0..100))
    ACCESS read-write
    STATUS mandatory
    DESCRIPTION
        "This object represents the Proxy-CSCF server group that
        will be used by this APN.  The Proxy-CSCF server group
        contains a list of Proxy-CSCF addresses which will be
        provided to the MS(UE) in response to a PDP contexts for
        which the P-CSCF address request field is set in PCO."
    ::= { cgprsAccPtEntry 36 }

cgprsAccPtAggregTable OBJECT-TYPE
    SYNTAX SEQUENCE OF CgprsAccPtAggregEntry
    ACCESS not-accessible
    STATUS mandatory
    DESCRIPTION
        "This table contains the list of aggregate routes
        configured on this APN.  GGSN uses a static host route 
        to forward user data packets for each PDP context 
        received from Gi interface to Gn interface.  Using the 
        aggregate route (address range), total number of static 
        routes implemented in the GGSN for PDP requests can be 
        greatly reduced.  If there is no aggregate route 
        configured on this access-point, then default aggregate 
        routes configured on GGSN will be used."
    ::= { ciscoGprsAccPtConfig 2 }

cgprsAccPtAggregEntry OBJECT-TYPE
    SYNTAX CgprsAccPtAggregEntry
    ACCESS not-accessible
    STATUS mandatory
    DESCRIPTION
        "An Entry contains the IP network prefix which is used
        to combine the routes of PDP requests for the same 
        network as a single route on the GGSN."
    INDEX { cgprsAccPtIndex, cgprsAccPtAggregIpAddrType, cgprsAccPtAggregIpAddr, cgprsAccPtAggregIpMask }
    ::= { cgprsAccPtAggregTable 1 }

CgprsAccPtAggregEntry ::= SEQUENCE {
    cgprsAccPtAggregIpAddrType InetAddressType,
    cgprsAccPtAggregIpAddr InetAddress,
    cgprsAccPtAggregIpMask CiscoInetAddressMask,
    cgprsAccPtAggregRowStatus RowStatus
    }

cgprsAccPtAggregIpAddrType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS not-accessible
    STATUS mandatory
    DESCRIPTION
        "This object specifies the type of Internet address
        denoted by cgprsAccPtAggregIpAddr."
    ::= { cgprsAccPtAggregEntry 1 }

cgprsAccPtAggregIpAddr OBJECT-TYPE
    SYNTAX InetAddress
--    Rsyntax OCTET STRING(SIZE(0..255))
    ACCESS not-accessible
    STATUS mandatory
    DESCRIPTION
        "This object specifies the IP address whose network
        prefix is going to be defined by 
        cgprsAccPtAggregIpMask.
        
        When this object is set, cgprsAccPtAggregIpMask must be 
        specified."
    ::= { cgprsAccPtAggregEntry 2 }

cgprsAccPtAggregIpMask OBJECT-TYPE
    SYNTAX CiscoInetAddressMask
--    Rsyntax Gauge(0..128)
    ACCESS not-accessible
    STATUS mandatory
    DESCRIPTION
        "This object specifies the net-mask pertaining to
        cgprsAccPtAggregIpAddr."
    ::= { cgprsAccPtAggregEntry 3 }

cgprsAccPtAggregRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create a new row or delete an
        existing row in this table.
        
        To create a row, set this object to 'createAndGo'.
        To delete a row, set this object to 'destroy'."
    ::= { cgprsAccPtAggregEntry 4 }

cgprsAccPtExtTable OBJECT-TYPE
    SYNTAX SEQUENCE OF CgprsAccPtExtEntry
    ACCESS not-accessible
    STATUS mandatory
    DESCRIPTION
        "This table is an extension of cgprsAccPtTable."
    ::= { ciscoGprsAccPtConfig 3 }

cgprsAccPtExtEntry OBJECT-TYPE
    SYNTAX CgprsAccPtExtEntry
    ACCESS not-accessible
    STATUS mandatory
    DESCRIPTION
        "An entry in cgprsAccPtExtTable."
    INDEX { cgprsAccPtIndex }
-- Augments cgprsAccPtEntry
    ::= { cgprsAccPtExtTable 1 }

CgprsAccPtExtEntry ::= SEQUENCE {
    cgprsAccPtIPAccListInEnable TruthValue,
    cgprsAccPtIPAccListOutEnable TruthValue,
    cgprsAccPtGtpRespMesgWaitAcctng TruthValue,
    cgprsAccPtImsiSuppressed TruthValue,
    cgprsAccPtVerifyUpStrTpduSrcAddr TruthValue,
    cgprsAccPtVerifyUpStrTpduDstAddr TruthValue,
    cgprsAccPtRedirInterMobilAddrTyp InetAddressType,
    cgprsAccPtRedirInterMobilAddr InetAddress,
    cgprsAccPtSuppressRadiusAttribs OCTET STRING,
    cgprsAccPtInterimAccountinEnable TruthValue,
    cgprsAccPtSetRadiusAttributes OCTET STRING,
    cgprsAccPtOperationMode INTEGER,
    cgprsAccPtAbsoluteSessionTimer Gauge,
    cgprsAccPtRadiusAttrNasId SnmpAdminString,
    cgprsAccPtPdpInServicePolicyName SnmpAdminString,
    cgprsAccPtPdpOutServicePolicyNam SnmpAdminString,
    cgprsAccPtPppRegenVerifyDomain TruthValue,
    cgprsAccPtIpAddrLocalPoolName SnmpAdminString,
    cgprsAccPtServiceAware TruthValue,
    cgprsAccPtAdvDownlinkNextHopAddrType InetAddressType,
    cgprsAccPtAdvDownlinkNextHopAddr InetAddress,
    cgprsAccPtGtpUpdateFailDelete TruthValue,
    cgprsAccPtAaaAccountInterPeriod Gauge,
    cgprsAccPtAaaAccountInterRadius TruthValue
    }

cgprsAccPtIPAccListInEnable OBJECT-TYPE
    SYNTAX TruthValue
--    Rsyntax INTEGER {
--        true(1),
--        false(2)
--        }
    ACCESS read-write
    STATUS mandatory
    DESCRIPTION
        "When this object is set to 'true', ACL denoted by
        cgprsAccPtIPAccListGroupIn will be active. When
        set to 'false', it will become inactive."
    DEFVAL { false }
    ::= { cgprsAccPtExtEntry 1 }

cgprsAccPtIPAccListOutEnable OBJECT-TYPE
    SYNTAX TruthValue
--    Rsyntax INTEGER {
--        true(1),
--        false(2)
--        }
    ACCESS read-write
    STATUS mandatory
    DESCRIPTION
        "When this object is set to 'true', ACL denoted by
        cgprsAccPtIPAccListGroupOut will be active. When
        set to 'false', it will become inactive."
    DEFVAL { false }
    ::= { cgprsAccPtExtEntry 2 }

cgprsAccPtGtpRespMesgWaitAcctng OBJECT-TYPE
    SYNTAX TruthValue
--    Rsyntax INTEGER {
--        true(1),
--        false(2)
--        }
    ACCESS read-write
    STATUS mandatory
    DESCRIPTION
        "When this object is set to 'true', GGSN waits for a
        RADIUS accounting response before sending a create PDP
        context response to the SGSN, for create PDP context
        requests received at a particular APN.
        
        When this object is set to 'false', GGSN sends create
        PDP response to SGSN after sending a RADIUS start 
        accounting message to the RADIUS server (without waiting
        for a response from the RADIUS accounting server)."
    DEFVAL { false }
    ::= { cgprsAccPtExtEntry 3 }

cgprsAccPtImsiSuppressed OBJECT-TYPE
    SYNTAX TruthValue
--    Rsyntax INTEGER {
--        true(1),
--        false(2)
--        }
    ACCESS read-write
    STATUS obsolete
    DESCRIPTION
        "This object specifies whether GGSN will be sending
        the radius attribute, IMSI value, in any of the 
        radius requests to the radius server or not.  When set
        to 'true', the IMSI attribute will not be sent by
        the GGSN.  When set to 'false', the IMSI attribute 
        will be sent by the GGSN.  This object is obsoleted by 
        cgprsAccPtSuppressRadiusAttribs."
    REFERENCE
        "3GPP TS 29.061 Release 1999: Digital cellular 
        telecommunications system (Phase 2+) (GSM); Universal 
        Mobile Telecommunications System (UMTS);Interworking 
        between the Public Land Mobile Network (PLMN) 
        supporting Packet Based services and Packet Data 
        Networks (PDN)."
    DEFVAL { false }
    ::= { cgprsAccPtExtEntry 4 }

cgprsAccPtVerifyUpStrTpduSrcAddr OBJECT-TYPE
    SYNTAX TruthValue
--    Rsyntax INTEGER {
--        true(1),
--        false(2)
--        }
    ACCESS read-write
    STATUS mandatory
    DESCRIPTION
        "When this object is set to 'true', GGSN will check the
        upstream TPDU source address against the address 
        previously assigned to this user.  If the addresses are
        different, the TPDU is dropped, the notification
        cgprsAccPtSecSrcViolNotif is generated and
        cgprsAccPtSourceAddrViolTpdus is incremented.  This 
        check will enable the GGSN to restrict the users with 
        fake identity.
        
        When the object is set to 'false', no checking is
        performed by the GGSN."
    DEFVAL { false }
    ::= { cgprsAccPtExtEntry 5 }

cgprsAccPtVerifyUpStrTpduDstAddr OBJECT-TYPE
    SYNTAX TruthValue
--    Rsyntax INTEGER {
--        true(1),
--        false(2)
--        }
    ACCESS read-write
    STATUS mandatory
    DESCRIPTION
        "When this object is set to 'true', GGSN will check the
        upstream TPDU destination address against the range of
        IP addresses reserved for PLMN devices.  If there is a
        match, the TPDU is dropped, the notification
        cgprsAccPtSecDestViolNotif is generated and 
        cgprsAccPtDestAddrViolTpdus is incremented.  The 
        configuration of IP address ranges reserved for PLMN 
        device is out of the scope of this MIB.  This check
        would enable the GGSN to protect the GPRS network from
        some hacker who may try to flood the GGSN and PLMN 
        nodes with intense data traffic.
        
        When the object is set to 'false', no checking is
        performed by the GGSN."
    DEFVAL { false }
    ::= { cgprsAccPtExtEntry 6 }

cgprsAccPtRedirInterMobilAddrTyp OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-write
    STATUS mandatory
    DESCRIPTION
        "This object indicates the type of Internet address by
        which cgprsAccPtRedirInterMobilAddr is reachable."
    ::= { cgprsAccPtExtEntry 7 }

cgprsAccPtRedirInterMobilAddr OBJECT-TYPE
    SYNTAX InetAddress
--    Rsyntax OCTET STRING(SIZE(0..255))
    ACCESS read-write
    STATUS mandatory
    DESCRIPTION
        "This object represents the IP address of the device
        to which inter-mobile traffic will be re-directed.
        When this redirection is active on an APN, before
        downstream packets exit the GGSN, they are screened
        to see if they come from other GTP tunnels.  If so,
        they won't be GTP-tunneled downstream, but will get
        redirected to the device specified by this object and
        cgprsAccPtRedirInterMobilTraffic is incremented.
        When this object is set to zero value, inter-mobile
        traffic will not be redirected i.e., the traffic will
        get switched through GGSN without going through any
        Gi interface."
    ::= { cgprsAccPtExtEntry 8 }

cgprsAccPtSuppressRadiusAttribs OBJECT-TYPE
    SYNTAX OCTET STRING(SIZE(1..2))
        -- BITS are:
        --   none(0)
        --   imsi(1)
        --   sgsnAddr(2)
        --   qos(3)
    ACCESS read-write
    STATUS mandatory
    DESCRIPTION
        "This object indicates the attributes that will be
        suppressed by the GGSN in its its authorization and
        accounting requests to the RADIUS server."
    REFERENCE
        "3GPP TS 29.061 Release 1999: Digital cellular
        telecommunications system (Phase 2+) (GSM); Universal
        Mobile Telecommunications System (UMTS);Interworking
        between the Public Land Mobile Network (PLMN)
        supporting Packet Based services and Packet Data
        Networks (PDN)."
    DEFVAL { '80'h }
    ::= { cgprsAccPtExtEntry 9 }

cgprsAccPtInterimAccountinEnable OBJECT-TYPE
    SYNTAX TruthValue
--    Rsyntax INTEGER {
--        true(1),
--        false(2)
--        }
    ACCESS read-write
    STATUS mandatory
    DESCRIPTION
        "This object is used to enable Interim Accounting for a
        PDP context on this APN.  When set to 'true', accounting
        updates will be triggered whenever a update PDP request
        is received.  This object can set to 'true' only when
        accounting(cgprsAccPtAaaAccountingEnable) is enabled."
    DEFVAL { false }
    ::= { cgprsAccPtExtEntry 10 }

cgprsAccPtSetRadiusAttributes OBJECT-TYPE
    SYNTAX OCTET STRING(SIZE(1..2))
        -- BITS are:
        --   none(0)
        --   userNameMsisdn(1)
        --   accSessIdChargingId(2)
    ACCESS read-write
    STATUS mandatory
    DESCRIPTION
        "This object indicates the values set in various radius
        attributes by the GGSN while communicating with RADIUS
        Server.  When set to
        
        'none' - reset the value set by the options below.
        
        'userNameMsisdn' - MSISDN of the mobile is sent in the
             user-name attribute.
        
        'accSessIdChargingId' - Charging ID is sent in the
             accounting session ID attribute."
    ::= { cgprsAccPtExtEntry 11 }

cgprsAccPtOperationMode OBJECT-TYPE
    SYNTAX INTEGER {
        --?? enum value of zero may cause problems
        inService(0),
        maintenance(1)
        }
    ACCESS read-write
    STATUS mandatory
    DESCRIPTION
        "This object denotes the operation mode of this APN.
        Each mode has different PDP context activation and
        deactivation behavior and is given as below:
        
        inService - normal operational mode in which all
            functions are allowed.  cgprsAccPtInServiceNotif
            notification will be sent to indicate the state
            change.
        
        maintenance - No new PDPs can be activated in this
            state. cgprsAccPtMaintenanceNotif notification
            will be sent to indicate the state change."
    DEFVAL { inService }
    ::= { cgprsAccPtExtEntry 12 }

cgprsAccPtAbsoluteSessionTimer OBJECT-TYPE
    SYNTAX Gauge(0|30..4294967)
--  Units
--    seconds
    ACCESS read-write
    STATUS mandatory
    DESCRIPTION
        "Absolute session timer is a RADIUS attribute (#27) sent
        by the AAA server in the Access-Accept packet.  GGSN
        will deactivate the PDP when this timer expires.  This
        object denotes the timer used by the GGSN when the same
        is not received from the AAA server.  Value of '0'
        denotes that the timer is disabled."
    DEFVAL { 0 }
    ::= { cgprsAccPtExtEntry 13 }

cgprsAccPtRadiusAttrNasId OBJECT-TYPE
    SYNTAX SnmpAdminString
--    Rsyntax OCTET STRING(SIZE(0..255))
    ACCESS read-write
    STATUS mandatory
    DESCRIPTION
        "This object denotes the value used as NAS ID in the
        RADIUS access requests sent by GGSN on this APN.  A
        zero length string needs to be set to unconfigure the
        NAS ID value."
    ::= { cgprsAccPtExtEntry 14 }

cgprsAccPtPdpInServicePolicyName OBJECT-TYPE
    SYNTAX SnmpAdminString(SIZE(0..40))
--    Rsyntax OCTET STRING(SIZE(0..40))
    ACCESS read-write
    STATUS mandatory
    DESCRIPTION
        "Per PDP Policy feature on GGSN ensures that the PDP
        contexts does not exceed bandwidth negotiated as part
        of PDP context activation procedure.  A service policy
        contains classification and policing parameters, details
        of the same is out of the scope of this MIB.  This
        object denotes the name of the service policy that is
        applicable to inbound traffic on all the PDP's
        pertaining to this APN."
    ::= { cgprsAccPtExtEntry 15 }

cgprsAccPtPdpOutServicePolicyNam OBJECT-TYPE
    SYNTAX SnmpAdminString(SIZE(0..40))
--    Rsyntax OCTET STRING(SIZE(0..40))
    ACCESS read-write
    STATUS mandatory
    DESCRIPTION
        "This object denotes the name of the service policy that
        is applicable to outbound traffic on all the PDP's
        pertaining to this APN."
    ::= { cgprsAccPtExtEntry 16 }

cgprsAccPtPppRegenVerifyDomain OBJECT-TYPE
    SYNTAX TruthValue
--    Rsyntax INTEGER {
--        true(1),
--        false(2)
--        }
    ACCESS read-write
    STATUS mandatory
    DESCRIPTION
        "When this object is set to 'true', a PPP regen session
        creation would be rejected if the domain name in PCO
        field is different than the APN name.  This object can
        only be set when cgprsAccPtPppRegenEnable is 'true'."
    DEFVAL { false }
    ::= { cgprsAccPtExtEntry 17 }

cgprsAccPtIpAddrLocalPoolName OBJECT-TYPE
    SYNTAX SnmpAdminString
--    Rsyntax OCTET STRING(SIZE(0..255))
    ACCESS read-write
    STATUS mandatory
    DESCRIPTION
        "This object represents the name of the local address
        pool used when cgprsAccPtIpAddressPool is set to
        'local'."
    ::= { cgprsAccPtExtEntry 18 }

cgprsAccPtServiceAware OBJECT-TYPE
    SYNTAX TruthValue
--    Rsyntax INTEGER {
--        true(1),
--        false(2)
--        }
    ACCESS read-write
    STATUS mandatory
    DESCRIPTION
        "This object is to enable service-aware billing
        (Diameter Credit Control Application [DCCA]
        support) on the access-point. This object can be
        set only when the object cGgsnSAServiceAware present
        in CISCO-GGSN-SERVICE-AWARE-MIB is set to 'true'."
    DEFVAL { false }
    ::= { cgprsAccPtExtEntry 19 }

cgprsAccPtAdvDownlinkNextHopAddrType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-write
    STATUS mandatory
    DESCRIPTION
        "This object indicates the type of Internet address
        of downlink next hop address."
    ::= { cgprsAccPtExtEntry 20 }

cgprsAccPtAdvDownlinkNextHopAddr OBJECT-TYPE
    SYNTAX InetAddress
--    Rsyntax OCTET STRING(SIZE(0..255))
    ACCESS read-write
    STATUS mandatory
    DESCRIPTION
        "This object advertises the next hop address on the
        GGSN to which downlink traffic destined for the GGSN 
        is to be routed. The address type is given by the  
        cgprsAccPtAdvDownlinkNextHopAddrType object."
    ::= { cgprsAccPtExtEntry 21 }

cgprsAccPtGtpUpdateFailDelete OBJECT-TYPE
    SYNTAX TruthValue
--    Rsyntax INTEGER {
--        true(1),
--        false(2)
--        }
    ACCESS read-write
    STATUS mandatory
    DESCRIPTION
        "This object denotes the action to be taken when a COA
        initiated update request for QOS change fails for a
        PDP context on this Access Point. If the object is
        set to 'true' and the update response from SGSN (for
        a update request) is not got after the configured retries
        or the received response indicates a cause value other than
        'request accepted', then the PDP context will be
        deleted by GGSN."
    DEFVAL { false }
    ::= { cgprsAccPtExtEntry 22 }

cgprsAccPtAaaAccountInterPeriod OBJECT-TYPE
    SYNTAX Gauge(0|15..71582)
--  Units
--    minutes
    ACCESS read-write
    STATUS mandatory
    DESCRIPTION
        "This object specifies the periodic accounting timer
        interval value for the access point. When this object 
        is set to a value, 'interim' type accounting records
        will be sent at the specified interval for the PDP
        contexts on this APN. When set to '0' the 'interim'
        type accounting records will not be sent out."
    DEFVAL { 0 }
    ::= { cgprsAccPtExtEntry 23 }

cgprsAccPtAaaAccountInterRadius OBJECT-TYPE
    SYNTAX TruthValue
--    Rsyntax INTEGER {
--        true(1),
--        false(2)
--        }
    ACCESS read-write
    STATUS mandatory
    DESCRIPTION
        "This object when set to 'true', enables GGSN to receive
         and use the Accounting Periodic Interval from Radius for 
         the PDP contexts on this APN."
    DEFVAL { false }
    ::= { cgprsAccPtExtEntry 24 }

cgprsAccPtGenServerConfigTable OBJECT-TYPE
    SYNTAX SEQUENCE OF CgprsAccPtGenServerConfigEntry
    ACCESS not-accessible
    STATUS mandatory
    DESCRIPTION
        "Each column in this table represent IP address of
        different generic servers, for example: DNS, NetBIOS, 
        configured on the APN."
    ::= { cgprsAccPtGenServerConfigs 1 }

cgprsAccPtGenServerConfigEntry OBJECT-TYPE
    SYNTAX CgprsAccPtGenServerConfigEntry
    ACCESS not-accessible
    STATUS mandatory
    DESCRIPTION
        "An entry in cgprsAccPtGenServerConfigTable."
    INDEX { cgprsAccPtIndex }
-- Augments cgprsAccPtEntry
    ::= { cgprsAccPtGenServerConfigTable 1 }

CgprsAccPtGenServerConfigEntry ::= SEQUENCE {
    cgprsAccPtDnsServerAddrType InetAddressType,
    cgprsAccPtPriDnsServer InetAddress,
    cgprsAccPtSecDnsServer InetAddress,
    cgprsAccPtNetbiosServerAddrType InetAddressType,
    cgprsAccPtPriNetbiosServer InetAddress,
    cgprsAccPtSecNetbiosServer InetAddress
    }

cgprsAccPtDnsServerAddrType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-write
    STATUS mandatory
    DESCRIPTION
        "This object indicates the type of Internet address by
        which cgprsAccPtPriDnsServer and cgprsAccPtSecDnsServer
        are reachable.
        
        DNS addresses to be sent to the MS can come from DHCP
        server or RADIUS server based on IP address allocation
        scheme chosen by cgprsAccPtIpAddressPool.  The IP
        address configured to cgprsAccPtPriDnsServer and
        cgprsAccPtSecDnsServer will be sent to MS only when
        
         - DHCP/RADIUS servers does not return any DNS address.
         - local address pool is used for IP address
           allocation for MS."
    ::= { cgprsAccPtGenServerConfigEntry 1 }

cgprsAccPtPriDnsServer OBJECT-TYPE
    SYNTAX InetAddress
--    Rsyntax OCTET STRING(SIZE(0..255))
    ACCESS read-write
    STATUS mandatory
    DESCRIPTION
        "This object specifies the IP address of the primary
        DNS server that will be sent to MS."
    ::= { cgprsAccPtGenServerConfigEntry 2 }

cgprsAccPtSecDnsServer OBJECT-TYPE
    SYNTAX InetAddress
--    Rsyntax OCTET STRING(SIZE(0..255))
    ACCESS read-write
    STATUS mandatory
    DESCRIPTION
        "This object specifies the IP address of the secondary
        DNS server that will be sent to MS.  A secondary server
        can be configured only if primary exists."
    ::= { cgprsAccPtGenServerConfigEntry 3 }

cgprsAccPtNetbiosServerAddrType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-write
    STATUS mandatory
    DESCRIPTION
        "This object indicates the type of Internet address by
        which cgprsAccPtPriNetbiosServer and
        cgprsAccPtSecNetbiosServer are reachable.
        
        NBNS addresses to be sent to the MS can come from DHCP
        server or RADIUS server based on IP address allocation
        scheme chosen by cgprsAccPtIpAddressPool.  The IP
        address configured to cgprsAccPtPriNetbiosServer and
        cgprsAccPtSecNetbiosServer will be sent to MS only when
        
         - DHCP/RADIUS servers does not return any NBNS address.
         - local address pool is used for IP address allocation
           for MS."
    ::= { cgprsAccPtGenServerConfigEntry 4 }

cgprsAccPtPriNetbiosServer OBJECT-TYPE
    SYNTAX InetAddress
--    Rsyntax OCTET STRING(SIZE(0..255))
    ACCESS read-write
    STATUS mandatory
    DESCRIPTION
        "This object specifies the IP address of the primary
        NetBIOS name server(NBNS) that will be sent to MS."
    ::= { cgprsAccPtGenServerConfigEntry 5 }

cgprsAccPtSecNetbiosServer OBJECT-TYPE
    SYNTAX InetAddress
--    Rsyntax OCTET STRING(SIZE(0..255))
    ACCESS read-write
    STATUS mandatory
    DESCRIPTION
        "This object specifies the IP address of the secondary
        NetBIOS name server(NBNS) that will be sent to MS.  A
        secondary server can be configured only if primary
        exists."
    ::= { cgprsAccPtGenServerConfigEntry 6 }

cgprsAccPtImsConfigTable OBJECT-TYPE
    SYNTAX SEQUENCE OF CgprsAccPtImsConfigEntry
    ACCESS not-accessible
    STATUS deprecated
    DESCRIPTION
        "IP Multimedia Subsystem(IMS) has been introduced in
        3GPP release 5 for the provision of multimedia services.
        GGSN terminates the GPRS bearer to carry IMS signaling
        and traffic. It communicates with Policy Decision
        Function(PDF) over the Go interface and acts as a Policy
        Enforcement Point(PEP) to enforce QoS per media flows
        using COPS protocol.
        
        This table represents various parameters required to
        support IMS.  This table is deprecated as IMS is not
        supported from GGSN 5.0 release onwards."
    REFERENCE
        "3GPP TS 29.207: Policy Control over Go interface."
    ::= { cgprsAccPtImsConfigs 1 }

cgprsAccPtImsConfigEntry OBJECT-TYPE
    SYNTAX CgprsAccPtImsConfigEntry
    ACCESS not-accessible
    STATUS deprecated
    DESCRIPTION
        "An entry in cgprsAccPtImsConfigTable"
    INDEX { cgprsAccPtIndex }
-- Augments cgprsAccPtEntry
    ::= { cgprsAccPtImsConfigTable 1 }

CgprsAccPtImsConfigEntry ::= SEQUENCE {
    cgprsAccPtImsEnable OCTET STRING,
    cgprsAccPtPCscfGroupName SnmpAdminString,
    cgprsAccPtImsSigAccGroupIn AccessControlListOrZero,
    cgprsAccPtImsSigAccGroupOut AccessControlListOrZero,
    cgprsAccPtRejNonImsPdp TruthValue
    }

cgprsAccPtImsEnable OBJECT-TYPE
    SYNTAX OCTET STRING(SIZE(1..2))
        -- BITS are:
        --   disable(0)
        --   enable(1)
        --   exclusive(2)
        --   transformPrimary(3)
    ACCESS read-write
    STATUS deprecated
    DESCRIPTION
        "This object indicates whether IMS traffic, both
        signalling and data, is allowed on this APN. When set to
        
        disable   - IMS traffic is not allowed.
        enable    - IMS traffic is allowed.
        exclusive - Only IMS traffic is allowed, non-IMS
                    traffic will be rejected.
        transformPrimary - non IMS traffic will be allowed
                    but all the rules applicable to IMS
                    traffic will also apply, for example. ACL's.
        
        The options 'exclusive' and 'transformPrimary' are
        mutually exclusive and can be set only when IMS is
        enabled, i.e., when 'enable' is set."
    DEFVAL { '80'h }
    ::= { cgprsAccPtImsConfigEntry 1 }

cgprsAccPtPCscfGroupName OBJECT-TYPE
    SYNTAX SnmpAdminString(SIZE(0..100))
--    Rsyntax OCTET STRING(SIZE(0..100))
    ACCESS read-write
    STATUS deprecated
    DESCRIPTION
        "This object represents the Proxy-CSCF server group that
        will be used by this APN.  Proxy-CSCF server group
        contains list of Proxy-CSCF addresses which will be
        provided to MS(UE) in response to a PDP contexts for
        which P-CSCF address request field is set in PCO."
    ::= { cgprsAccPtImsConfigEntry 2 }

cgprsAccPtImsSigAccGroupIn OBJECT-TYPE
    SYNTAX AccessControlListOrZero
--    Rsyntax INTEGER(0..199|1300..2699)
    ACCESS read-write
    STATUS deprecated
    DESCRIPTION
        "This object represents the access list that will be
        applied to all the IMS signalling PDP context received
        by this APN from the PDN for forwarding towards a MS.
        An IMS signalling PDP context will have IMS signalling
        flag set in the PCO field."
    DEFVAL { 0 }
    ::= { cgprsAccPtImsConfigEntry 3 }

cgprsAccPtImsSigAccGroupOut OBJECT-TYPE
    SYNTAX AccessControlListOrZero
--    Rsyntax INTEGER(0..199|1300..2699)
    ACCESS read-write
    STATUS deprecated
    DESCRIPTION
        "This object represents the access list that will be
        applied to all the IMS signalling PDP context received
        by this APN from a MS for forwarding towards PDN.  An
        IMS signalling PDP context will have IMS signalling flag
        set in the PCO field."
    DEFVAL { 0 }
    ::= { cgprsAccPtImsConfigEntry 4 }

cgprsAccPtRejNonImsPdp OBJECT-TYPE
    SYNTAX TruthValue
--    Rsyntax INTEGER {
--        true(1),
--        false(2)
--        }
    ACCESS read-write
    STATUS deprecated
    DESCRIPTION
        "This object represents the action to be taken on a non
        IMS PDP context, when cgprsAccPtImsEnable is set to
        'true' on this APN.  When this object is set to 'true',
        respective PDP context activation will be rejected.
        When set to 'false', PDP activation will be based on the
        QoS negotiation."
    DEFVAL { false }
    ::= { cgprsAccPtImsConfigEntry 5 }

cgprsAccPtChgProfTable OBJECT-TYPE
    SYNTAX SEQUENCE OF CgprsAccPtChgProfEntry
    ACCESS not-accessible
    STATUS mandatory
    DESCRIPTION
        "Charging characteristics is a parameter that allows the
        operator to apply different charging methods on a per
        PDP basis.  Each charging profile is associated with an
        index, set of charging parameters like subscriber
        category, volume limit trigger, etc., details of the
        same is outside the scope of the MIB and are defined
        in CISCO-GPRS-CHARGING-MIB.
        
        Charging characteristics can be received from SGSN as
        an Information Element in the create PDP request or
        defaults can be configured at GGSN and/or APN level.
        
        This table represents the charging profiles that can
        be applied to different type of mobile subscribers on
        an APN.  GGSN level configurations are dealt in
        CISCO-GPRS-CHARGING-MIB."
    REFERENCE
        "3GPP TS 32.215 V5.2.0 Charging data description for 
        the Packet Switched domain(Release 4)."
    ::= { cgprsAccPtChargingParams 1 }

cgprsAccPtChgProfEntry OBJECT-TYPE
    SYNTAX CgprsAccPtChgProfEntry
    ACCESS not-accessible
    STATUS mandatory
    DESCRIPTION
        "An entry in cgprsAccPtChgProfTable."
    INDEX { cgprsAccPtIndex, cgprsAccPtMsType }
    ::= { cgprsAccPtChgProfTable 1 }

CgprsAccPtChgProfEntry ::= SEQUENCE {
    cgprsAccPtMsType INTEGER,
    cgprsAccPtChgProfile Gauge,
    cgprsAccPtChgProfOverride TruthValue,
    cgprsAccPtChgProfRowStatus RowStatus
    }

cgprsAccPtMsType OBJECT-TYPE
    SYNTAX INTEGER {
        all(1),
        home(2),
        roaming(3),
        roamingTrusted(4),
        visiting(5),
        visitingTrusted(6)
        }
    ACCESS not-accessible
    STATUS mandatory
    DESCRIPTION
        "This object represents the type of MS to which the
        charging profile selected by cgprsAccPtChgProfile is
        applied on this APN. Different types of MS -
        
        A roaming MS belongs to a SGSN of a different PLMN.
        A visitor MS is one whose IMSI value belongs to a
        different PLMN.  A home MS is neither roamer nor
        visitor, i.e., IMSI and SGSN corresponds to same PLMN.
        
        A roamer/visitor is said to be Trusted/Friendly if
        the different PLMN is a trusted/friendly PLMN."
    ::= { cgprsAccPtChgProfEntry 1 }

cgprsAccPtChgProfile OBJECT-TYPE
    SYNTAX Gauge
    ACCESS read-write
    STATUS mandatory
    DESCRIPTION
        "This object represents the charging profile number to
        be applied to MS denoted by cgprsAccPtMsType on this
        APN.  Details of charging profile parameters are outside
        the scope of this MIB and are covered by 
        CISCO-GPRS-CHARGING-MIB.  This object is mandatory while
        creating a row. The current valid values are 1 to 255."
    ::= { cgprsAccPtChgProfEntry 2 }

cgprsAccPtChgProfOverride OBJECT-TYPE
    SYNTAX TruthValue
--    Rsyntax INTEGER {
--        true(1),
--        false(2)
--        }
    ACCESS read-write
    STATUS mandatory
    DESCRIPTION
        "This object specifies whether charging characteristics
        value supplied by SGSN will be ignored and the values
        supplied in this table are used.  When this object is
        set to 'true', the value supplied by SGSN will be
        ignored."
    DEFVAL { true }
    ::= { cgprsAccPtChgProfEntry 3 }

cgprsAccPtChgProfRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create a new row or delete an
        existing row in this table.
        
        To create a row, set this object to 'createAndGo'.
        To delete a row, set this object to 'destroy'."
    ::= { cgprsAccPtChgProfEntry 4 }

cgprsAccPtCacTable OBJECT-TYPE
    SYNTAX SEQUENCE OF CgprsAccPtCacEntry
    ACCESS not-accessible
    STATUS mandatory
    DESCRIPTION
        "Call Admission Control(CAC) on GGSN ensures that
        required network resources are available for real-time
        data traffic, such as voice, video, etc., and to support
        establishment and modification of the QoS parameters by
        signalling and negotiating during PDP context activation
        procedure and modification procedure.  CAC performs this
        by examining various QoS parameters like traffic class,
        maximum bit rate and guaranteed bit rate for both uplink
        and downlink received from the SGSN with the local
        configured parameters or policy received from Policy
        Decision Function(PDF).
        
        This table represents various parameters required to
        support CAC."
    ::= { cgprsAccPtCacConfigs 1 }

cgprsAccPtCacEntry OBJECT-TYPE
    SYNTAX CgprsAccPtCacEntry
    ACCESS not-accessible
    STATUS mandatory
    DESCRIPTION
        "An entry in cgprsAccPtCacTable."
    INDEX { cgprsAccPtIndex }
-- Augments cgprsAccPtEntry
    ::= { cgprsAccPtCacTable 1 }

CgprsAccPtCacEntry ::= SEQUENCE {
    cgprsAccPtCacPolicyName SnmpAdminString,
    cgprsAccPtCacUpStrBandWidthPool SnmpAdminString,
    cgprsAccPtCacDnStrBandWidthPool SnmpAdminString
    }

cgprsAccPtCacPolicyName OBJECT-TYPE
    SYNTAX SnmpAdminString(SIZE(0..40))
--    Rsyntax OCTET STRING(SIZE(0..40))
    ACCESS read-write
    STATUS mandatory
    DESCRIPTION
        "This object represents the local policy name that will
        be used by CAC for the PDP's pertaining to this APN.
        
        Details of QoS parameters pertaining to a CAC policy
        are out of scope of this MIB and are covered in
        CISCO-GGSN-QOS-MIB.
        
        A zero-length string denotes that no policy is
        configured."
    ::= { cgprsAccPtCacEntry 1 }

cgprsAccPtCacUpStrBandWidthPool OBJECT-TYPE
    SYNTAX SnmpAdminString(SIZE(0..40))
--    Rsyntax OCTET STRING(SIZE(0..40))
    ACCESS read-write
    STATUS mandatory
    DESCRIPTION
        "A Bandwidth pool is a user defined pool with bandwidth
        pre-allocation details like amount of available
        bandwidth, percent of bandwidth available to a specific
        traffic class.  CAC uses this information during PDP
        context activation and modification procedures.
        
        This object represents the name of the bandwidth pool
        used for upstream traffic. Configuration of the
        bandwidth pool is covered in CISCO-GGSN-QOS-MIB.
        
        A zero-length string denotes that no policy is
        configured."
    ::= { cgprsAccPtCacEntry 2 }

cgprsAccPtCacDnStrBandWidthPool OBJECT-TYPE
    SYNTAX SnmpAdminString(SIZE(0..40))
--    Rsyntax OCTET STRING(SIZE(0..40))
    ACCESS read-write
    STATUS mandatory
    DESCRIPTION
        "This object represents the name of the bandwidth pool
        used for downstream traffic. Configuration of the
        bandwidth pool is covered in CISCO-GGSN-QOS-MIB.
        
        A zero-length string denotes that no policy is
        configured."
    ::= { cgprsAccPtCacEntry 3 }

cgprsAccPtRouteProbeTable OBJECT-TYPE
    SYNTAX SEQUENCE OF CgprsAccPtRouteProbeEntry
    ACCESS not-accessible
    STATUS mandatory
    DESCRIPTION
        "Route probe feature enables GGSN to send out a route
        probe packet to a configured destination after a
        successful PDP activation procedure.  The source IP
        address of the packet would be the IP address of the
        PDP context.
        
        This table represents various parameters set in the
        route probe packet.  At this point, UDP packets will be
        sent, a new column will be added to represent the
        protocol when the support is extended to other
        protocols."
    ::= { cgprsAccPtRouteProbeConfigs 1 }

cgprsAccPtRouteProbeEntry OBJECT-TYPE
    SYNTAX CgprsAccPtRouteProbeEntry
    ACCESS not-accessible
    STATUS mandatory
    DESCRIPTION
        "An entry in cgprsAccPtRouteProbeTable."
    INDEX { cgprsAccPtIndex }
-- Augments cgprsAccPtEntry
    ::= { cgprsAccPtRouteProbeTable 1 }

CgprsAccPtRouteProbeEntry ::= SEQUENCE {
    cgprsAccPtRpDestAddrType InetAddressType,
    cgprsAccPtRpDestAddr InetAddress,
    cgprsAccPtRpProtocol INTEGER,
    cgprsAccPtRpDestPort InetPortNumber,
    cgprsAccPtRpTtl Gauge
    }

cgprsAccPtRpDestAddrType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-write
    STATUS mandatory
    DESCRIPTION
        "This object indicates the type of Internet address by
        which cgprsAccPtRpDestAddr is reachable."
    ::= { cgprsAccPtRouteProbeEntry 1 }

cgprsAccPtRpDestAddr OBJECT-TYPE
    SYNTAX InetAddress
--    Rsyntax OCTET STRING(SIZE(0..255))
    ACCESS read-write
    STATUS mandatory
    DESCRIPTION
        "This object specifies the destination IP address to
        which the route probe packet needs to be sent."
    ::= { cgprsAccPtRouteProbeEntry 2 }

cgprsAccPtRpProtocol OBJECT-TYPE
    SYNTAX INTEGER {
        udp(1),
        icmp(2)
        }
    ACCESS read-write
    STATUS mandatory
    DESCRIPTION
        "This objects specifies the protocol type of route probe
        packet.  This object can be set only after
        cgprsAccPtRpDestAddr is being set."
    DEFVAL { udp }
    ::= { cgprsAccPtRouteProbeEntry 3 }

cgprsAccPtRpDestPort OBJECT-TYPE
    SYNTAX InetPortNumber
--    Rsyntax Gauge(0..65535)
    ACCESS read-write
    STATUS mandatory
    DESCRIPTION
        "This object specifies the destination port number of
        the route probe packet when cgprsAccPtRpProtocol is
        set to 'udp'.  This object can be set only after
        cgprsAccPtRpDestAddr is being set."
    DEFVAL { 9 }
    ::= { cgprsAccPtRouteProbeEntry 4 }

cgprsAccPtRpTtl OBJECT-TYPE
    SYNTAX Gauge(1..255)
--  Units
--    seconds
    ACCESS read-write
    STATUS mandatory
    DESCRIPTION
        "This object specifies the TTL value set in the route
        probe packet.  This object can be set only after
        cgprsAccPtRpDestAddr is being set."
    DEFVAL { 255 }
    ::= { cgprsAccPtRouteProbeEntry 5 }

cgprsAccPtIpv6Table OBJECT-TYPE
    SYNTAX SEQUENCE OF CgprsAccPtIpv6Entry
    ACCESS not-accessible
    STATUS mandatory
    DESCRIPTION
        "GGSN supports IPv6 PDP type and its user traffic.
        It will provide the IPv6 prefix and interface identifier
        to the MS; generate IPv6 PDP address in the appropriate
        charging records and AAA accounting record. 
        
        This table represents various parameters required to 
        support IPv6 PDP under APN."
    ::= { cgprsAccPtIpv6Configs 1 }

cgprsAccPtIpv6Entry OBJECT-TYPE
    SYNTAX CgprsAccPtIpv6Entry
    ACCESS not-accessible
    STATUS mandatory
    DESCRIPTION
        "An entry in cgprsAccPtIpv6Table.
        
        The agent can create/destroy/modify a profile as a
        result of actions from the local console.  The table
        objects can be modified, when the RowStatus is active.
        
        The entries in this table are stored in NVRAM when the
        agent writes the configuration to memory before 
        restart."
    INDEX { cgprsAccPtIndex }
-- Augments cgprsAccPtEntry
    ::= { cgprsAccPtIpv6Table 1 }

CgprsAccPtIpv6Entry ::= SEQUENCE {
    cgprsAccPtIpv6BaseVTemplate Gauge,
    cgprsAccPtIpv6DnsAddrType InetAddressType,
    cgprsAccPtIpv6DnsPriAddress InetAddress,
    cgprsAccPtIpv6DnsSecAddress InetAddress,
    cgprsAccPtIpv6Enable TruthValue,
    cgprsAccPtIpv6Exclusive TruthValue,
    cgprsAccPtIpv6AccessGroupDown AccessControlListName,
    cgprsAccPtIpv6AccessGroupUp AccessControlListName,
    cgprsAccPtIpv6AddrPool INTEGER,
    cgprsAccPtIpv6AddrLocalPoolName SnmpAdminString,
    cgprsAccPtIpv6Redirect INTEGER,
    cgprsAccPtIpv6RedirectAddrType InetAddressType,
    cgprsAccPtIpv6RedirectAddr InetAddress,
    cgprsAccPtIpv6SecurityVerifySrc TruthValue,
    cgprsAccPtIpv6SecurityVerifyDst TruthValue
    }

cgprsAccPtIpv6BaseVTemplate OBJECT-TYPE
    SYNTAX Gauge
    ACCESS read-write
    STATUS mandatory
    DESCRIPTION
        "This object specifies the base virtual template
        for an APN.  To create a sub-interface for each PDP, 
        a base virtual-template needs to be configured so that 
        virtual-access interface can be cloned from it.  Many 
        APN can share one base virtual-template.  But one APN  
        can only use one base virtual-template.
        
        This object must be set to appropriate value for IPv6 
        APN i.e., when the object cgprsAccPtIpv6Enable or 
        cgprsAccPtIpv6Exclusive is set to 'true'."
    ::= { cgprsAccPtIpv6Entry 1 }

cgprsAccPtIpv6DnsAddrType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-write
    STATUS mandatory
    DESCRIPTION
        "This object specifies the type of
        cgprsAccPtIpv6DnsPriAddress and 
        cgprsAccPtIpv6DnsSecAddress.
        
        DNS addresses to be sent to the MS can come from DHCP
        server or RADIUS server based on IP address allocation
        scheme chosen by cgprsAccPtIpv6AddrPool.  The IP address
        configured to cgprsAccPtIpv6DnsPriAddress and 
        cgprsAccPtIpv6DnsSecAddress will be sent to MS only when
        
         - DHCP/RADIUS servers does not return any DNS address.
         - local address pool is used for IP address
           allocation for MS."
    ::= { cgprsAccPtIpv6Entry 2 }

cgprsAccPtIpv6DnsPriAddress OBJECT-TYPE
    SYNTAX InetAddress
--    Rsyntax OCTET STRING(SIZE(0..255))
    ACCESS read-write
    STATUS mandatory
    DESCRIPTION
        "This object specifies the IPv6 address of the primary
        DNS server that will be sent to MS."
    ::= { cgprsAccPtIpv6Entry 3 }

cgprsAccPtIpv6DnsSecAddress OBJECT-TYPE
    SYNTAX InetAddress
--    Rsyntax OCTET STRING(SIZE(0..255))
    ACCESS read-write
    STATUS mandatory
    DESCRIPTION
        "This object specifies the IPv6 address of the secondary
        DNS server that will be sent to MS.  This object can 
        be configured only after configuring the primary DNS
        address(cgprsAccPtIpv6DnsPriAddress)."
    ::= { cgprsAccPtIpv6Entry 4 }

cgprsAccPtIpv6Enable OBJECT-TYPE
    SYNTAX TruthValue
--    Rsyntax INTEGER {
--        true(1),
--        false(2)
--        }
    ACCESS read-write
    STATUS mandatory
    DESCRIPTION
        "This object specifies whether the APN supports
        IPv6 PDP. 
        
        GGSN supports dual stack APN.  Both IPv6 and IPv4 PDP 
        can be created for the same APN."
    ::= { cgprsAccPtIpv6Entry 5 }

cgprsAccPtIpv6Exclusive OBJECT-TYPE
    SYNTAX TruthValue
--    Rsyntax INTEGER {
--        true(1),
--        false(2)
--        }
    ACCESS read-write
    STATUS mandatory
    DESCRIPTION
        "This object specifies whether the APN supports only
        IPv6 PDPs."
    ::= { cgprsAccPtIpv6Entry 6 }

cgprsAccPtIpv6AccessGroupDown OBJECT-TYPE
    SYNTAX AccessControlListName
--    Rsyntax OCTET STRING(SIZE(0..255))
    ACCESS read-write
    STATUS mandatory
    DESCRIPTION
        "This object specifies the name of the access list
        applied to all the traffic received by this APN from 
        the PDN,  for forwarding towards a MS."
    ::= { cgprsAccPtIpv6Entry 7 }

cgprsAccPtIpv6AccessGroupUp OBJECT-TYPE
    SYNTAX AccessControlListName
--    Rsyntax OCTET STRING(SIZE(0..255))
    ACCESS read-write
    STATUS mandatory
    DESCRIPTION
        "This object specifies the name of the access list
        applied to all the traffic received by this APN from
        a MS,  for forwarding towards PDN."
    ::= { cgprsAccPtIpv6Entry 8 }

cgprsAccPtIpv6AddrPool OBJECT-TYPE
    SYNTAX INTEGER {
        global(1),
        dhcp(2),
        disable(3),
        local(4),
        radius(5)
        }
    ACCESS read-write
    STATUS mandatory
    DESCRIPTION
        "This object specifies a dynamic address allocation
        method followed by this access point.
        
            - 'global', which indicates that no method is
            defined specifically to this access point and the
            DHCP or radius server configured for this GGSN
            under AAA configurations will be used to 
            allocation a dynamic IPv6 address to the user.
        
            - 'dhcp', which indicates that the DHCP server
            will be used.
        
            - 'radius', which indicates that the radius server
            will be used.
        
            - 'disable', which indicates that dynamic address
            allocation is disabled.
        
            - 'local', indicates that local address pool
            configured on the GGSN is going to be used.
            cgprsAccPtIpv6AddrLocalPoolName denotes the name
            of the corresponding address pool."
    DEFVAL { global }
    ::= { cgprsAccPtIpv6Entry 9 }

cgprsAccPtIpv6AddrLocalPoolName OBJECT-TYPE
    SYNTAX SnmpAdminString
--    Rsyntax OCTET STRING(SIZE(0..255))
    ACCESS read-write
    STATUS mandatory
    DESCRIPTION
        "This object specifies the name of the local address
        pool used when cgprsAccPtIpv6AddrPool is set to
        'local'."
    ::= { cgprsAccPtIpv6Entry 10 }

cgprsAccPtIpv6Redirect OBJECT-TYPE
    SYNTAX INTEGER {
        --?? enum value of zero may cause problems
        none(0),
        all(1),
        intermobile(2)
        }
    ACCESS read-write
    STATUS mandatory
    DESCRIPTION
        "This object specifies the traffic redirection in an
        APN.
        
         - 'none', indicates that, traffic will not be 
         redirected i.e., the traffic will get switched through 
         GGSN without going through any Gi interface. 
        
         - 'intermobile', when this redirection is active on 
         an APN, before downstream packets exit the GGSN, they
         are screened to see if they come from other GTP 
         tunnels.  If so, packets won't be GTP-tunneled 
         downstream, but will get redirected to the device
         specified by the object cgprsAccPtIpv6RedirectAddr. 
        
         - 'all', when this redirection is active on an APN, 
         redirect all packets to a specified destination, given
         by the object cgprsAccPtIpv6RedirectAddr, regardless  
         whether the destination address belongs to a MS on the 
         same GGSN or not."
    ::= { cgprsAccPtIpv6Entry 11 }

cgprsAccPtIpv6RedirectAddrType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-write
    STATUS mandatory
    DESCRIPTION
        "This object specifies the type of
        cgprsAccPtIpv6RedirectAddr."
    ::= { cgprsAccPtIpv6Entry 12 }

cgprsAccPtIpv6RedirectAddr OBJECT-TYPE
    SYNTAX InetAddress
--    Rsyntax OCTET STRING(SIZE(0..255))
    ACCESS read-write
    STATUS mandatory
    DESCRIPTION
        "This object specifies the Internet address of the
        device to which traffic will be re-directed."
    ::= { cgprsAccPtIpv6Entry 13 }

cgprsAccPtIpv6SecurityVerifySrc OBJECT-TYPE
    SYNTAX TruthValue
--    Rsyntax INTEGER {
--        true(1),
--        false(2)
--        }
    ACCESS read-write
    STATUS mandatory
    DESCRIPTION
        "When this object is set to 'true', GGSN will check the
        upstream TPDU source address against the address
        previously assigned to this user.  If the addresses are
        different, the TPDU is dropped. This check will enable
        the GGSN to restrict the users with fake identity.
        
        When the object is set to 'false', GGSN will not
        perform any checking on the upstream TPDU for the 
        source address."
    DEFVAL { false }
    ::= { cgprsAccPtIpv6Entry 14 }

cgprsAccPtIpv6SecurityVerifyDst OBJECT-TYPE
    SYNTAX TruthValue
--    Rsyntax INTEGER {
--        true(1),
--        false(2)
--        }
    ACCESS read-write
    STATUS mandatory
    DESCRIPTION
        "When this object is set to 'true', GGSN will check the
        upstream TPDU destination address against the range of
        IP addresses reserved for PLMN devices.  If there is a
        match, the TPDU is dropped. This check would enable 
        the GGSN to protect the GPRS network from some hacker
        who may try to flood the GGSN and PLMN nodes with 
        intense data traffic.
        
        When the object is set to 'false', GGSN will not
        perform any checking on the upstream TPDU for the 
        destination address."
    DEFVAL { false }
    ::= { cgprsAccPtIpv6Entry 15 }

cgprsAccPtCfgNotifHistTable OBJECT-TYPE
    SYNTAX SEQUENCE OF CgprsAccPtCfgNotifHistEntry
    ACCESS not-accessible
    STATUS mandatory
    DESCRIPTION
        "This table contains a history of access point
        configuration change notifications generated by 
        the agent for changes in the access point 
        configuration. 
        
        The object cgprsAccPtCfgNotifHistMax specifies the 
        maximum number of entries stored in this table. 
        When the table is full, the oldest entries are 
        discarded to make space for new entries."
    ::= { ciscoGprsAccPtCfgNotifInfo 1 }

cgprsAccPtCfgNotifHistEntry OBJECT-TYPE
    SYNTAX CgprsAccPtCfgNotifHistEntry
    ACCESS not-accessible
    STATUS mandatory
    DESCRIPTION
        "A description of a configuration change in the
        cgprsAccPtTable. A configuration change is said 
        to occur if one of the following happens:
        
            - An access point has been created. In this 
            case the object cgprsAccPtCfgNotifAccPtIndex
            is set to the index of the access point being
            created and cgprsAccPtCfgNotifReason is 
            set to 'creation'.
        
            - An access point has been deleted. In this 
            case the object cgprsAccPtCfgNotifAccPtIndex
            is set to the index of the access point being
            deleted and cgprsAccPtCfgNotifReason is
            set to 'deletion'.
        
            - The configuration of an access point has 
            changed. In this case the object 
            cgprsAccPtCfgNotifAccPtIndex is set to the 
            index of the access point being changed and
            cgprsAccPtCfgNotifReason is set to 
            'modification'. The configuration change of 
            an access point is said to occur if any of the 
            configurable attributes are changed."
    INDEX { cgprsAccPtCfgNotifIndex }
    ::= { cgprsAccPtCfgNotifHistTable 1 }

CgprsAccPtCfgNotifHistEntry ::= SEQUENCE {
    cgprsAccPtCfgNotifIndex Gauge,
    cgprsAccPtCfgNotifAccPtIndex Gauge,
    cgprsAccPtCfgNotifReason INTEGER
    }

cgprsAccPtCfgNotifIndex OBJECT-TYPE
    SYNTAX Gauge(1..4294967295)
    ACCESS not-accessible
    STATUS mandatory
    DESCRIPTION
        "An arbitrary non-zero integer value uniquely
        identifying each notification previously sent 
        by the GPRS. This value increases monotonically 
        with each notification sent by the GGSN.
        
        When it reaches the maximum value, it wraps to 1."
    ::= { cgprsAccPtCfgNotifHistEntry 1 }

cgprsAccPtCfgNotifAccPtIndex OBJECT-TYPE
    SYNTAX Gauge(1..65535)
    ACCESS read-only
    STATUS mandatory
    DESCRIPTION
        "This object specifies the access point which has
        been created, changed or modified."
    ::= { cgprsAccPtCfgNotifHistEntry 2 }

cgprsAccPtCfgNotifReason OBJECT-TYPE
    SYNTAX INTEGER {
        modification(1),
        creation(2),
        deletion(3)
        }
    ACCESS read-only
    STATUS mandatory
    DESCRIPTION
        "This object describes the reason of the notification."
    ::= { cgprsAccPtCfgNotifHistEntry 3 }

cgprsAccPtCfgNotifEnable OBJECT-TYPE
    SYNTAX TruthValue
--    Rsyntax INTEGER {
--        true(1),
--        false(2)
--        }
    ACCESS read-write
    STATUS mandatory
    DESCRIPTION
        "This object controls whether the access point
        notifications, cgprsAccPtMIBNotifications, are
        generated. Note that entries in the
        cgprsAccPtCfgNotifHistTable are generated 
        irrespectively to this object."
    DEFVAL { false }
    ::= { ciscoGprsAccPtCfgNotifInfo 2 }

cgprsAccPtCfgNotifHistMax OBJECT-TYPE
    SYNTAX Gauge(1..5000)
    ACCESS read-write
    STATUS mandatory
    DESCRIPTION
        "The maximum size of the event history table,
        cgprsAccPtCfgNotifHistTable.
        
        When the table is full, the oldest entries are 
        removed to make space for new entries."
    DEFVAL { 200 }
    ::= { ciscoGprsAccPtCfgNotifInfo 3 }

cgprsAccPtCfgNotifLatestIndex OBJECT-TYPE
    SYNTAX Gauge(1..4294967295)
    ACCESS read-only
    STATUS mandatory
    DESCRIPTION
        "The value of cgprsAccPtCfgNotifIndex for the most
        recently created entry in cgprsAccPtCfgNotifHistTable."
    ::= { ciscoGprsAccPtCfgNotifInfo 4 }

cgprsAccPtStatisticsTable OBJECT-TYPE
    SYNTAX SEQUENCE OF CgprsAccPtStatisticsEntry
    ACCESS not-accessible
    STATUS mandatory
    DESCRIPTION
        "This table contains the performance statistics of
        each APN on this GGSN [3]."
    ::= { ciscoGprsAccPtStatistics 1 }

cgprsAccPtStatisticsEntry OBJECT-TYPE
    SYNTAX CgprsAccPtStatisticsEntry
    ACCESS not-accessible
    STATUS mandatory
    DESCRIPTION
        "Entry for each APN in statistics table."
    INDEX { cgprsAccPtIndex }
-- Augments cgprsAccPtEntry
    ::= { cgprsAccPtStatisticsTable 1 }

CgprsAccPtStatisticsEntry ::= SEQUENCE {
    cgprsAccPtMsActivatedPdps Counter,
    cgprsAccPtSuccMsActivatedPdps Counter,
    cgprsAccPtMsActivatedDynPdps Counter,
    cgprsAccPtSuccMsActivatedDynPdps Counter,
    cgprsAccPtMsDeactivatedPdps Counter,
    cgprsAccPtSuccMsDeactivatedPdps Counter,
    cgprsAccPtNetworkInitPdps Counter,
    cgprsAccPtSuccNetworkInitPdps Counter,
    cgprsAccPtGgsnDeactivatedPdps Counter,
    cgprsAccPtSuccGgsDeactivatedPdps Counter,
    cgprsAccPtActivePdps Gauge,
    cgprsAccPtUpstreamTrafficVol Counter,
    cgprsAccPtDownstreamTrafficVol Counter,
    cgprsAccPtSourceAddrViolTpdus Counter,
    cgprsAccPtDestAddrViolTpdus Counter,
    cgprsAccPtRedirInterMobilTraffic Counter,
    cgprsAccPtRevUpstreamTrafficVol Counter,
    cgprsAccPtRevDownstrTrafficVol Counter,
    cgprsAccPtUpstreamPacketCount Counter,
    cgprsAccPtDownstreamPacketCount Counter,
    cgprsAccPtDhcpAddrRequests Counter,
    cgprsAccPtSuccDhcpAddrRequests Counter,
    cgprsAccPtDhcpAddrReleases Counter,
    cgprsAccPtIpv6MsActivatedPdps Counter,
    cgprsAccPtIpv6MsSuccActivatedPdps Counter,
    cgprsAccPtIpv6NetworkInitDeactPdps Counter,
    cgprsAccPtIpv6NetworkInitDeactSuccPdps Counter,
    cgprsAccPtIpv6MsActivatedDynPdps Counter,
    cgprsAccPtIpv6MsSuccActivatedDynPdps Counter,
    cgprsAccPtIpv6MsDeactivatedPdps Counter,
    cgprsAccPtIpv6MsSuccDeactivatedPdps Counter,
    cgprsAccPtIpv6GgsnDeactivatedPdps Counter,
    cgprsAccPtIpv6GgsnSuccDeactivatedPdps Counter,
    cgprsAccPtIpv6UpstreamTrafficVolume Counter,
    cgprsAccPtIpv6DownstreamTrafficVolume Counter,
    cgprsAccPtIpv6UpstreamPackets Counter,
    cgprsAccPtIpv6DownstreamPackets Counter,
    cgprsAccPtPdpUpdateReqSent Counter,
    cgprsAccPtSuccPdpUpdateResRcvd Counter,
    cgprsAccPtCoaRcvd Counter,
    cgprsAccPtCoaSuccess Counter,
    cgprsAccPtDtEnabled Counter
    }

cgprsAccPtMsActivatedPdps OBJECT-TYPE
    SYNTAX Counter
    ACCESS read-only
    STATUS mandatory
    DESCRIPTION
        "This object indicates the total number of PDP context
        activation procedures initiated by any MS on this APN.
        
        Trigger Condition: This counter is triggered by create
        PDP request message."
    REFERENCE
        "GSM 12.04: Digital cellular telecommunications
        system (Phase 2+); Performance data measurements,
        Section: B.9.1.1."
    ::= { cgprsAccPtStatisticsEntry 1 }

cgprsAccPtSuccMsActivatedPdps OBJECT-TYPE
    SYNTAX Counter
    ACCESS read-only
    STATUS mandatory
    DESCRIPTION
        "This object indicates the total number of successfully
        completed PDP context activation procedures initiated 
        by MS on this APN.
        
        Trigger Condition: This counter is triggered by create
        PDP request message."
    REFERENCE
        "GSM 12.04: Digital cellular telecommunications
        system (Phase 2+); Performance data measurements,
        Section: B.9.1.2."
    ::= { cgprsAccPtStatisticsEntry 2 }

cgprsAccPtMsActivatedDynPdps OBJECT-TYPE
    SYNTAX Counter
    ACCESS read-only
    STATUS mandatory
    DESCRIPTION
        "This object indicates the total number of dynamic
        PDP context activation procedures initiated by the 
        MS on this APN.  When a MS requests dynamic PDP 
        address from the PLMN, a dynamic PDP context 
        activation procedure is initiated.
        
        Trigger Condition: This counter is triggered by create
        PDP request message."
    REFERENCE
        "GSM 12.04: Digital cellular telecommunications
        system (Phase 2+); Performance data measurements,
        Section: B.9.1.3."
    ::= { cgprsAccPtStatisticsEntry 3 }

cgprsAccPtSuccMsActivatedDynPdps OBJECT-TYPE
    SYNTAX Counter
    ACCESS read-only
    STATUS mandatory
    DESCRIPTION
        "This object indicates the total number of successfully
        completed dynamic PDP context activation procedures 
        initiated by MS on this APN.
        
        Trigger Condition: This counter is triggered by create
        PDP request message."
    REFERENCE
        "GSM 12.04: Digital cellular telecommunications
        system (Phase 2+); Performance data measurements,
        Section: B.9.1.4."
    ::= { cgprsAccPtStatisticsEntry 4 }

cgprsAccPtMsDeactivatedPdps OBJECT-TYPE
    SYNTAX Counter
    ACCESS read-only
    STATUS mandatory
    DESCRIPTION
        "This object indicates the total number of PDP
        context deactivation procedures initiated by the 
        MS on this APN.
        
        Trigger Condition: This counter is triggered by delete
        PDP request message."
    REFERENCE
        "GSM 12.04: Digital cellular telecommunications
        system (Phase 2+); Performance data measurements,
        Section: B.9.1.5."
    ::= { cgprsAccPtStatisticsEntry 5 }

cgprsAccPtSuccMsDeactivatedPdps OBJECT-TYPE
    SYNTAX Counter
    ACCESS read-only
    STATUS mandatory
    DESCRIPTION
        "This object indicates the total number of
        successfully completed PDP context deactivation 
        procedures initiated by the MS.
        
        Trigger Condition: This counter is triggered by delete
        PDP request message."
    REFERENCE
        "GSM 12.04: Digital cellular telecommunications
        system (Phase 2+); Performance data measurements,
        Section: B.9.1.6."
    ::= { cgprsAccPtStatisticsEntry 6 }

cgprsAccPtNetworkInitPdps OBJECT-TYPE
    SYNTAX Counter
    ACCESS read-only
    STATUS mandatory
    DESCRIPTION
        "This object indicates the total number of network
        initiated PDP context activation procedures.
        
        Trigger Condition: This counter is triggered by create
        PDP request message."
    ::= { cgprsAccPtStatisticsEntry 7 }

cgprsAccPtSuccNetworkInitPdps OBJECT-TYPE
    SYNTAX Counter
    ACCESS read-only
    STATUS mandatory
    DESCRIPTION
        "This object indicates the total number of
        successfully completed network initiated PDP 
        context activation procedures.
        
        Trigger Condition: This counter is triggered by create
        PDP request message."
    ::= { cgprsAccPtStatisticsEntry 8 }

cgprsAccPtGgsnDeactivatedPdps OBJECT-TYPE
    SYNTAX Counter
    ACCESS read-only
    STATUS mandatory
    DESCRIPTION
        "This object indicates the total number of PDP
        context deactivation procedures initiated by the 
        GGSN.
        
        Trigger Condition: This counter is triggered by delete
        PDP request message."
    REFERENCE
        "GSM 12.04: Digital cellular telecommunications
        system (Phase 2+); Performance data measurements,
        Section: B.9.1.7."
    ::= { cgprsAccPtStatisticsEntry 9 }

cgprsAccPtSuccGgsDeactivatedPdps OBJECT-TYPE
    SYNTAX Counter
    ACCESS read-only
    STATUS mandatory
    DESCRIPTION
        "This object indicates the total number of
        successfully completed PDP context deactivation 
        procedures initiated by the GGSN.
        
        Trigger Condition: This counter is triggered by delete
        PDP request message."
    REFERENCE
        "GSM 12.04: Digital cellular telecommunications
        system (Phase 2+); Performance data measurements,
        Section: B.9.1.8."
    ::= { cgprsAccPtStatisticsEntry 10 }

cgprsAccPtActivePdps OBJECT-TYPE
    SYNTAX Gauge
    ACCESS read-only
    STATUS mandatory
    DESCRIPTION
        "This object indicates the current number of active
        PDP contexts on this APN.
        
        Trigger Condition: This counter is incremented/
        decremented by create/delete PDP context request
        messages respectively."
    REFERENCE
        "GSM 12.04: Digital cellular telecommunications
        system (Phase 2+); Performance data measurements,
        Section: B.9.1.9."
    ::= { cgprsAccPtStatisticsEntry 11 }

cgprsAccPtUpstreamTrafficVol OBJECT-TYPE
    SYNTAX Counter
--  Units
--    bytes
    ACCESS read-only
    STATUS deprecated
    DESCRIPTION
        "This object indicates the total payload volume in
        upstream traffic.  Data flow from MS to PDN is 
        considered to be upstream traffic.
        
        This object is deprecated by
        cgprsAccPtRevUpstreamTrafficVol."
    ::= { cgprsAccPtStatisticsEntry 12 }

cgprsAccPtDownstreamTrafficVol OBJECT-TYPE
    SYNTAX Counter
--  Units
--    bytes
    ACCESS read-only
    STATUS deprecated
    DESCRIPTION
        "This object indicates the total payload volume in
        downstream traffic.  Data flow from PDN to MS is 
        considered as downstream traffic.
        
        This object is deprecated by
        cgprsAccPtRevDownstrTrafficVol."
    ::= { cgprsAccPtStatisticsEntry 13 }

cgprsAccPtSourceAddrViolTpdus OBJECT-TYPE
    SYNTAX Counter
--  Units
--    packets
    ACCESS read-only
    STATUS mandatory
    DESCRIPTION
        "This object indicates the total number of upstream
        TPDU's that have been dropped due to source address 
        violation as specified by 
        cgprsAccPtVerifyUpStrTpduSrcAddr."
    ::= { cgprsAccPtStatisticsEntry 14 }

cgprsAccPtDestAddrViolTpdus OBJECT-TYPE
    SYNTAX Counter
--  Units
--    packets
    ACCESS read-only
    STATUS mandatory
    DESCRIPTION
        "This object indicates the total number of upstream
        TPDU's that have been dropped due to destination
        address violation as specified by
        cgprsAccPtVerifyUpStrTpduDstAddr."
    ::= { cgprsAccPtStatisticsEntry 15 }

cgprsAccPtRedirInterMobilTraffic OBJECT-TYPE
    SYNTAX Counter
--  Units
--    packets
    ACCESS read-only
    STATUS mandatory
    DESCRIPTION
        "This object represents the total number of packets,
        pertaining to inter mobile communication, that have 
        been redirected to device specified by
        cgprsAccPtRedirInterMobilAddr."
    ::= { cgprsAccPtStatisticsEntry 16 }

cgprsAccPtRevUpstreamTrafficVol OBJECT-TYPE
    SYNTAX --?? syntax is not convertable to SMIv1
           Counter
--  Units
--    bytes
    ACCESS read-only
    STATUS mandatory
    DESCRIPTION
        "This object indicates the total payload volume in
        upstream traffic.  Data flow from MS to PDN is
        considered to be upstream traffic.
        
        Trigger Condition: This counter is triggered when
        upstream traffic is being routed to PDN."
    ::= { cgprsAccPtStatisticsEntry 17 }

cgprsAccPtRevDownstrTrafficVol OBJECT-TYPE
    SYNTAX --?? syntax is not convertable to SMIv1
           Counter
--  Units
--    bytes
    ACCESS read-only
    STATUS mandatory
    DESCRIPTION
        "This object indicates the total payload volume in
        downstream traffic.  Data flow from PDN to MS is
        considered as downstream traffic.
        
        Trigger Condition: This counter is triggered when
        downstream traffic is being routed to PDN."
    ::= { cgprsAccPtStatisticsEntry 18 }

cgprsAccPtUpstreamPacketCount OBJECT-TYPE
    SYNTAX Counter
--  Units
--    packets
    ACCESS read-only
    STATUS mandatory
    DESCRIPTION
        "This object represents the total number of upstream
        packets sent on this APN.  Data flow from MS to PDN is
        considered to be upstream traffic.
        
        Trigger Condition: This counter is triggered when
        upstream traffic is being routed to PDN."
    ::= { cgprsAccPtStatisticsEntry 19 }

cgprsAccPtDownstreamPacketCount OBJECT-TYPE
    SYNTAX Counter
--  Units
--    packets
    ACCESS read-only
    STATUS mandatory
    DESCRIPTION
        "This object represents the total number of downstream
        packets sent on this APN.  Data flow from PDN to MS is
        considered to be downstream traffic.
        
        Trigger Condition: This counter is triggered when
        downstream traffic is being routed to PDN."
    ::= { cgprsAccPtStatisticsEntry 20 }

cgprsAccPtDhcpAddrRequests OBJECT-TYPE
    SYNTAX Counter
--  Units
--    packets
    ACCESS read-only
    STATUS mandatory
    DESCRIPTION
        "This object represents the total number of DHCP
        address request sent by the GGSN on this APN.
        
        Trigger Condition: This counter is triggered by create
        PDP request message."
    ::= { cgprsAccPtStatisticsEntry 21 }

cgprsAccPtSuccDhcpAddrRequests OBJECT-TYPE
    SYNTAX Counter
--  Units
--    packets
    ACCESS read-only
    STATUS mandatory
    DESCRIPTION
        "This object represents the total number of successful
        DHCP address request sent by the GGSN on this APN.
        
        Trigger Condition: This counter is triggered by create
        PDP request message."
    ::= { cgprsAccPtStatisticsEntry 22 }

cgprsAccPtDhcpAddrReleases OBJECT-TYPE
    SYNTAX Counter
--  Units
--    packets
    ACCESS read-only
    STATUS mandatory
    DESCRIPTION
        "This object represents the total number of DHCP
        address release request sent by the GGSN on this APN.
        
        Trigger Condition: This counter is triggered by delete
        PDP request message."
    ::= { cgprsAccPtStatisticsEntry 23 }

cgprsAccPtIpv6MsActivatedPdps OBJECT-TYPE
    SYNTAX Counter
    ACCESS read-only
    STATUS mandatory
    DESCRIPTION
        "This object indicates the total number of IPv6 PDP
        context activation procedures initiated by any MS on 
        this APN.
        
        Trigger Condition: This counter is triggered by create
        PDP request message."
    ::= { cgprsAccPtStatisticsEntry 24 }

cgprsAccPtIpv6MsSuccActivatedPdps OBJECT-TYPE
    SYNTAX Counter
    ACCESS read-only
    STATUS mandatory
    DESCRIPTION
        "This object indicates the total number of successfully
        completed IPv6 PDP context activation procedures 
        initiated by MS on this APN.
        
        Trigger Condition: This counter is triggered by create
        PDP response message sent by the GGSN."
    ::= { cgprsAccPtStatisticsEntry 25 }

cgprsAccPtIpv6NetworkInitDeactPdps OBJECT-TYPE
    SYNTAX Counter
    ACCESS read-only
    STATUS mandatory
    DESCRIPTION
        "This object indicates the total number of IPv6 PDP
        context deactivation procedures initiated by network.
        
        Trigger Condition: This counter is triggered by delete 
        PDP request message by network."
    ::= { cgprsAccPtStatisticsEntry 26 }

cgprsAccPtIpv6NetworkInitDeactSuccPdps OBJECT-TYPE
    SYNTAX Counter
    ACCESS read-only
    STATUS mandatory
    DESCRIPTION
        "This object indicates the total number of
        successfully completed IPv6 PDP context deactivation
        procedures initiated by the network on this APN.
        
        Trigger Condition: This counter is triggered by delete 
        PDP response message by GGSN."
    ::= { cgprsAccPtStatisticsEntry 27 }

cgprsAccPtIpv6MsActivatedDynPdps OBJECT-TYPE
    SYNTAX Counter
    ACCESS read-only
    STATUS mandatory
    DESCRIPTION
        "This object indicates the total number of dynamic IPv6
        PDP context activation procedures initiated by the MS
        on this APN.  When a MS requests dynamic PDP address 
        from the PLMN, a dynamic PDP context activation 
        procedure is initiated.
        
        Trigger Condition: This counter is triggered by create
        PDP request message, received by GGSN from an MS."
    ::= { cgprsAccPtStatisticsEntry 28 }

cgprsAccPtIpv6MsSuccActivatedDynPdps OBJECT-TYPE
    SYNTAX Counter
    ACCESS read-only
    STATUS mandatory
    DESCRIPTION
        "This object indicates the total number of successfully
        completed dynamic IPv6 PDP context activation procedures
        initiated by MS on this APN.
        
        Trigger Condition: This counter is triggered by create
        PDP response message."
    ::= { cgprsAccPtStatisticsEntry 29 }

cgprsAccPtIpv6MsDeactivatedPdps OBJECT-TYPE
    SYNTAX Counter
    ACCESS read-only
    STATUS mandatory
    DESCRIPTION
        "This object indicates the total number of IPv6 PDP
        context deactivation procedures initiated by the
        MS on this APN.
        
        Trigger Condition: This counter is triggered by delete
        PDP request message, received by GGSN from an SGSN."
    ::= { cgprsAccPtStatisticsEntry 30 }

cgprsAccPtIpv6MsSuccDeactivatedPdps OBJECT-TYPE
    SYNTAX Counter
    ACCESS read-only
    STATUS mandatory
    DESCRIPTION
        "This object indicates the total number of
        successfully completed IPv6 PDP context deactivation
        procedures initiated by the MS on this APN.
        
        Trigger Condition: This counter is triggered by delete
        PDP context response message, sent by GGSN to an SGSN."
    ::= { cgprsAccPtStatisticsEntry 31 }

cgprsAccPtIpv6GgsnDeactivatedPdps OBJECT-TYPE
    SYNTAX Counter
    ACCESS read-only
    STATUS mandatory
    DESCRIPTION
        "This object indicates the total number of IPv6 PDP
        context deactivation procedures initiated by the
        GGSN on this APN.
        
        Trigger Condition: This counter is triggered by delete
        PDP request message, sent by GGSN to an SGSN."
    ::= { cgprsAccPtStatisticsEntry 32 }

cgprsAccPtIpv6GgsnSuccDeactivatedPdps OBJECT-TYPE
    SYNTAX Counter
    ACCESS read-only
    STATUS mandatory
    DESCRIPTION
        "This object indicates the total number of
        successfully completed IPv6 PDP context deactivation
        procedures initiated by the GGSN on this APN.
        
        Trigger Condition: This counter is triggered by delete
        PDP response message, received by the GGSN from an 
        SGSN."
    ::= { cgprsAccPtStatisticsEntry 33 }

cgprsAccPtIpv6UpstreamTrafficVolume OBJECT-TYPE
    SYNTAX --?? syntax is not convertable to SMIv1
           Counter
--  Units
--    bytes
    ACCESS read-only
    STATUS mandatory
    DESCRIPTION
        "This object indicates the total payload volume in
        upstream traffic sent on this APN.  Data flow from 
        MS to PDN is considered to be upstream traffic.
        
        Trigger Condition: This counter is triggered when
        upstream traffic is being routed to PDN."
    ::= { cgprsAccPtStatisticsEntry 34 }

cgprsAccPtIpv6DownstreamTrafficVolume OBJECT-TYPE
    SYNTAX --?? syntax is not convertable to SMIv1
           Counter
--  Units
--    bytes
    ACCESS read-only
    STATUS mandatory
    DESCRIPTION
        "This object indicates the total payload volume in
        downstream traffic sent on this APN.  Data flow from 
        PDN to MS is considered as downstream traffic.
        
        Trigger Condition: This counter is triggered when
        downstream traffic is being routed to PDN."
    ::= { cgprsAccPtStatisticsEntry 35 }

cgprsAccPtIpv6UpstreamPackets OBJECT-TYPE
    SYNTAX Counter
--  Units
--    packets
    ACCESS read-only
    STATUS mandatory
    DESCRIPTION
        "This object indicates the total number of upstream
        packets sent on this APN.  Data flow from MS to PDN is
        considered to be upstream traffic.
        
        Trigger Condition: This counter is triggered when
        upstream traffic is being routed to PDN."
    ::= { cgprsAccPtStatisticsEntry 36 }

cgprsAccPtIpv6DownstreamPackets OBJECT-TYPE
    SYNTAX Counter
--  Units
--    packets
    ACCESS read-only
    STATUS mandatory
    DESCRIPTION
        "This object represents the total number of downstream
        packets sent on this APN.  Data flow from PDN to MS is
        considered to be downstream traffic.
        
        Trigger Condition: This counter is triggered when
        downstream traffic is being routed to PDN."
    ::= { cgprsAccPtStatisticsEntry 37 }

cgprsAccPtPdpUpdateReqSent OBJECT-TYPE
    SYNTAX Counter
--  Units
--    messages
    ACCESS read-only
    STATUS mandatory
    DESCRIPTION
        "This object represents the total number of GGSN
        initiated update requests sent on this APN.
        
        Trigger Condition: This counter is triggered when a
        Update request is initiated from the GGSN."
    ::= { cgprsAccPtStatisticsEntry 38 }

cgprsAccPtSuccPdpUpdateResRcvd OBJECT-TYPE
    SYNTAX Counter
--  Units
--    messages
    ACCESS read-only
    STATUS mandatory
    DESCRIPTION
        "This object represents the total number of successful
        update responses received from the SGSN with a cause
        value 'Request accepted' for the GGSN initiated update
        requests on this APN.
        
        Trigger condition: This counter is triggered when a 
        update response with cause value 'Request accepted' is
        received on this APN."
    ::= { cgprsAccPtStatisticsEntry 39 }

cgprsAccPtCoaRcvd OBJECT-TYPE
    SYNTAX Counter
--  Units
--    messages
    ACCESS read-only
    STATUS mandatory
    DESCRIPTION
        "This object represents the total number of Change of
        Authorization (COA) messages received on this APN.                                                                  
        Trigger condition: This counter is triggered when a COA
        message is received."
    ::= { cgprsAccPtStatisticsEntry 40 }

cgprsAccPtCoaSuccess OBJECT-TYPE
    SYNTAX Counter
--  Units
--    messages
    ACCESS read-only
    STATUS mandatory
    DESCRIPTION
        "This object represents the number of COA messages
        that were acknowledged by the GGSN with a COA ACK. 
        
        Trigger condition: This counter is triggered when a
        COA ACK is sent by the GGSN."
    ::= { cgprsAccPtStatisticsEntry 41 }

cgprsAccPtDtEnabled OBJECT-TYPE
    SYNTAX Counter
--  Units
--    pdps
    ACCESS read-only
    STATUS mandatory
    DESCRIPTION
        "This object represents the number of times Direct
        tunnel is enabled for the PDP contexts on this APN
        in GGSN."
    ::= { cgprsAccPtStatisticsEntry 42 }

cgprsAccPtThruputStatsTable OBJECT-TYPE
    SYNTAX SEQUENCE OF CgprsAccPtThruputStatsEntry
    ACCESS not-accessible
    STATUS mandatory
    DESCRIPTION
        "This table contains the throughput statistics of
        each APN on this GGSN."
    ::= { ciscoGprsAccPtStatistics 3 }

cgprsAccPtThruputStatsEntry OBJECT-TYPE
    SYNTAX CgprsAccPtThruputStatsEntry
    ACCESS not-accessible
    STATUS mandatory
    DESCRIPTION
        "An entry in this table."
    INDEX { cgprsAccPtIndex, cgprsAccPtThruputInterval }
    ::= { cgprsAccPtThruputStatsTable 1 }

CgprsAccPtThruputStatsEntry ::= SEQUENCE {
    cgprsAccPtThruputInterval INTEGER,
    cgprsAccPtThruPutLastCollected INTEGER,
    cgprsAccPtUpstrByteCount Gauge,
    cgprsAccPtDownstrByteCount Gauge,
    cgprsAccPtUpstrPktCount Gauge,
    cgprsAccPtDownstrPktCount Gauge
    }

cgprsAccPtThruputInterval OBJECT-TYPE
    SYNTAX INTEGER(1..65535)
--  Units
--    minutes
    ACCESS not-accessible
    STATUS mandatory
    DESCRIPTION
        "This object represents the time interval at which the
        statistics are sampled.  Interval configuration is out
        of the scope of the MIB and are covered in
        CISCO-GGSN-MIB."
    ::= { cgprsAccPtThruputStatsEntry 1 }

cgprsAccPtThruPutLastCollected OBJECT-TYPE
    SYNTAX INTEGER(0..65535)
--  Units
--    minutes
    ACCESS read-only
    STATUS mandatory
    DESCRIPTION
        "This object represents the delta value between the time
        when this data is collected and the time it is been
        retrieved."
    ::= { cgprsAccPtThruputStatsEntry 2 }

cgprsAccPtUpstrByteCount OBJECT-TYPE
    SYNTAX Gauge
--  Units
--    bytes
    ACCESS read-only
    STATUS mandatory
    DESCRIPTION
        "This object represents the total payload volume in
        upstream traffic sent on this APN in the last sampling
        period specified by cgprsAccPtThruputInterval."
    ::= { cgprsAccPtThruputStatsEntry 3 }

cgprsAccPtDownstrByteCount OBJECT-TYPE
    SYNTAX Gauge
--  Units
--    bytes
    ACCESS read-only
    STATUS mandatory
    DESCRIPTION
        "This object represents the total payload volume in
        downstream traffic sent on this APN in the last sampling
        period specified by cgprsAccPtThruputInterval."
    ::= { cgprsAccPtThruputStatsEntry 4 }

cgprsAccPtUpstrPktCount OBJECT-TYPE
    SYNTAX Gauge
--  Units
--    packets
    ACCESS read-only
    STATUS mandatory
    DESCRIPTION
        "This object represents the number of upstream packets
        sent on this APN in the last sampling period specified
        by cgprsAccPtThruputInterval."
    ::= { cgprsAccPtThruputStatsEntry 5 }

cgprsAccPtDownstrPktCount OBJECT-TYPE
    SYNTAX Gauge
--  Units
--    packets
    ACCESS read-only
    STATUS mandatory
    DESCRIPTION
        "This object represents the number of downstream packets
        sent on this APN in the last sampling period specified
        by cgprsAccPtThruputInterval."
    ::= { cgprsAccPtThruputStatsEntry 6 }

cgprsAccPtMsAddrType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS not-accessible
    STATUS mandatory
    DESCRIPTION
        "This object specifies the type of Internet address
        denoted by cgprsAccPtMsAllocAddr, cgprsAccPtMsNewAddr 
        and cgprsAccPtMsTpduDstAddr."
    ::= { ciscoGprsAccPtNotifInfo 1 }

cgprsAccPtMsAllocAddr OBJECT-TYPE
    SYNTAX InetAddress
--    Rsyntax OCTET STRING(SIZE(0..255))
    ACCESS not-accessible
    STATUS mandatory
    DESCRIPTION
        "This object specifies the IP address that is assigned
        to the MS during PDP activation."
    ::= { ciscoGprsAccPtNotifInfo 2 }

cgprsAccPtMsNewAddr OBJECT-TYPE
    SYNTAX InetAddress
--    Rsyntax OCTET STRING(SIZE(0..255))
    ACCESS not-accessible
    STATUS mandatory
    DESCRIPTION
        "This object specifies the fake IP address that is used
        by the MS."
    ::= { ciscoGprsAccPtNotifInfo 3 }

cgprsAccPtMsTpduDstAddr OBJECT-TYPE
    SYNTAX InetAddress
--    Rsyntax OCTET STRING(SIZE(0..255))
    ACCESS not-accessible
    STATUS mandatory
    DESCRIPTION
        "This object specifies the upstream TPDU destination
        address used by a MS that falls in the reserved range
        of IP addresses for PLMN devices."
    ::= { ciscoGprsAccPtNotifInfo 4 }

cgprsAccPtCfgNotif TRAP-TYPE
-- Reverse mappable trap
    ENTERPRISE cgprsAccPtMIBNotificationPrefix
    VARIABLES {
        cgprsAccPtCfgNotifAccPtIndex, cgprsAccPtCfgNotifReason }
--  Status
--    mandatory
    DESCRIPTION
        "A notification of this type is generated when an
        entry is generated in the 
        cgprsAccPtCfgNotifHistTable and 
        cgprsAccPtCfgNotifEnable is set to true."
    ::= 1

cgprsAccPtSecSrcViolNotif TRAP-TYPE
-- Reverse mappable trap
    ENTERPRISE cgprsAccPtMIBNotificationPrefix
    VARIABLES {
        cgprsAccPtCfgNotifAccPtIndex, cgprsAccPtMsAddrType, 
        cgprsAccPtMsAllocAddr, cgprsAccPtMsNewAddr }
--  Status
--    mandatory
    DESCRIPTION
        "A notification of this type is generated when security
        violation as specified by
        cgprsAccPtVerifyUpStrTpduSrcAddr occurs on an APN."
    ::= 2

cgprsAccPtSecDestViolNotif TRAP-TYPE
-- Reverse mappable trap
    ENTERPRISE cgprsAccPtMIBNotificationPrefix
    VARIABLES {
        cgprsAccPtCfgNotifAccPtIndex, cgprsAccPtMsAddrType, 
        cgprsAccPtMsAllocAddr, cgprsAccPtMsTpduDstAddr }
--  Status
--    mandatory
    DESCRIPTION
        "A notification of this type is generated when security
        violation as specified by
        cgprsAccPtVerifyUpStrTpduDstAddr occurs on an APN."
    ::= 3

cgprsAccPtMaintenanceNotif TRAP-TYPE
-- Reverse mappable trap
    ENTERPRISE cgprsAccPtMIBNotificationPrefix
    VARIABLES {
        cgprsAccPtCfgNotifAccPtIndex }
--  Status
--    mandatory
    DESCRIPTION
        "A notification of this type is generated when APN is
        placed in maintenance mode which is specified by
        cgprsAccPtOperationMode."
    ::= 4

cgprsAccPtInServiceNotif TRAP-TYPE
-- Reverse mappable trap
    ENTERPRISE cgprsAccPtMIBNotificationPrefix
    VARIABLES {
        cgprsAccPtCfgNotifAccPtIndex }
--  Status
--    mandatory
    DESCRIPTION
        "A notification of this type is generated when APN is
        placed in in-service mode which is specified by
        cgprsAccPtOperationMode."
    ::= 5

cgprsAccPtMIBGroup OBJECT IDENTIFIER ::= { cgprsAccPtMIBGroups 1 }
-- OBJECT-GROUP
--  Status
--    obsolete
--  Descr
--    A collection of objects providing APN configurations.
--  objects
--    cgprsAccPtRowStatus, cgprsAccPtName, cgprsAccPtMode, 
--    cgprsAccPtIpAddressPool, cgprsAccPtDHCPServerPri, 
--    cgprsAccPtDHCPServerSec, cgprsAccPtDHCPGwAddr, 
--    cgprsAccPtRadiusServerPri, cgprsAccPtRadiusServerSec, 
--    cgprsAccPtIPAccListGroupIn, cgprsAccPtIPAccListGroupOut, 
--    cgprsAccPtIfIndex, cgprsAccPtIfNextHop, 
--    cgprsAccPtAccessViolation, cgprsAccPtSubrRequired, 
--    cgprsAccPtNetworkInitiated, cgprsAccPtIpAddrAllocations, 
--    cgprsAccPtUsers, cgprsAccPtIdlePdpPurgeTimer, 
--    cgprsAccPtBlockMsRoaming, cgprsAccPtAnonymousUserName, 
--    cgprsAccPtAnonymousUserPassword, cgprsAccPtMsIsdnSuppressed, 
--    cgprsAccPtMsIsdnSuppressedValue, cgprsAccPtAaaAuthServerGroup, 
--    cgprsAccPtAaaAccountServerGroup, 
--    cgprsAccPtAaaAccountingEnable, cgprsAccPtAggregRowStatus

cgprsAccPtCfgNotifGroup OBJECT IDENTIFIER ::= { cgprsAccPtMIBGroups 2 }
-- OBJECT-GROUP
--  Status
--    mandatory
--  Descr
--    A collection of objects providing GPRS access point
--    configuration change event related information.
--  objects
--    cgprsAccPtCfgNotifEnable, cgprsAccPtCfgNotifAccPtIndex, 
--    cgprsAccPtCfgNotifReason, cgprsAccPtCfgNotifHistMax, 
--    cgprsAccPtCfgNotifLatestIndex

cgprsAccPtStatisticsGroup OBJECT IDENTIFIER ::= { cgprsAccPtMIBGroups 3 }
-- OBJECT-GROUP
--  Status
--    obsolete
--  Descr
--    A collection of objects providing GPRS access point
--    performance statistics.
--    This is obsoleted by cgprsAccPtStatisticsGroupRev1.
--  objects
--    cgprsAccPtMsActivatedPdps, cgprsAccPtSuccMsActivatedPdps, 
--    cgprsAccPtMsActivatedDynPdps, 
--    cgprsAccPtSuccMsActivatedDynPdps, cgprsAccPtMsDeactivatedPdps, 
--    cgprsAccPtSuccMsDeactivatedPdps, cgprsAccPtNetworkInitPdps, 
--    cgprsAccPtSuccNetworkInitPdps, cgprsAccPtGgsnDeactivatedPdps, 
--    cgprsAccPtSuccGgsDeactivatedPdps, cgprsAccPtActivePdps, 
--    cgprsAccPtUpstreamTrafficVol, cgprsAccPtDownstreamTrafficVol

cgprsAccPtMIBGroupRev1 OBJECT IDENTIFIER ::= { cgprsAccPtMIBGroups 4 }
-- OBJECT-GROUP
--  Status
--    mandatory
--  Descr
--    A collection of objects providing APN configurations.
--  objects
--    cgprsAccPtRowStatus, cgprsAccPtName, cgprsAccPtMode, 
--    cgprsAccPtIpAddressPool, cgprsAccPtDHCPServerPri, 
--    cgprsAccPtDHCPServerSec, cgprsAccPtDHCPGwAddr, 
--    cgprsAccPtIPAccListGroupIn, cgprsAccPtIPAccListGroupOut, 
--    cgprsAccPtAccessViolation, cgprsAccPtSubrRequired, 
--    cgprsAccPtNetworkInitiated, cgprsAccPtIpAddrAllocations, 
--    cgprsAccPtIdlePdpPurgeTimer, cgprsAccPtBlockMsRoaming, 
--    cgprsAccPtAnonymousUserName, cgprsAccPtAnonymousUserPassword, 
--    cgprsAccPtMsIsdnSuppressed, cgprsAccPtMsIsdnSuppressedValue, 
--    cgprsAccPtAaaAuthServerGroup, cgprsAccPtAaaAccountServerGroup, 
--    cgprsAccPtAaaAccountingEnable, cgprsAccPtType, 
--    cgprsAccPtVrfName, cgprsAccPtDhcpAddrSpace, 
--    cgprsAccPtPppRegenEnable, cgprsAccPtPppRegenMaxSessions, 
--    cgprsAccPtPppRegenSetupTime, cgprsAccPtAutoAggregation, 
--    cgprsAccPtAggregRowStatus

cgprsAccPtExtMIBGroup OBJECT IDENTIFIER ::= { cgprsAccPtMIBGroups 5 }
-- OBJECT-GROUP
--  Status
--    obsolete
--  Descr
--    A collection of objects providing APN configurations.
--  objects
--    cgprsAccPtIPAccListInEnable, cgprsAccPtIPAccListOutEnable, 
--    cgprsAccPtGtpRespMesgWaitAcctng

cgprsAccPtExtMIBGroupRev1 OBJECT IDENTIFIER ::= { cgprsAccPtMIBGroups 7 }
-- OBJECT-GROUP
--  Status
--    obsolete
--  Descr
--    A collection of objects providing APN configurations.
--    This is obsoleted by cgprsAccPtExtMIBGroupRev2.
--  objects
--    cgprsAccPtIPAccListInEnable, cgprsAccPtIPAccListOutEnable, 
--    cgprsAccPtGtpRespMesgWaitAcctng, cgprsAccPtImsiSuppressed, 
--    cgprsAccPtVerifyUpStrTpduSrcAddr, 
--    cgprsAccPtVerifyUpStrTpduDstAddr, 
--    cgprsAccPtRedirInterMobilAddrTyp, 
--    cgprsAccPtRedirInterMobilAddr

cgprsAccPtStatisticsGroupRev1 OBJECT IDENTIFIER ::= { cgprsAccPtMIBGroups 8 }
-- OBJECT-GROUP
--  Status
--    deprecated
--  Descr
--    A collection of objects providing GPRS access point
--    performance statistics.  This is deprecated by
--    cgprsAccPtStatisticsGroupRev2.
--  objects
--    cgprsAccPtMsActivatedPdps, cgprsAccPtSuccMsActivatedPdps, 
--    cgprsAccPtMsActivatedDynPdps, 
--    cgprsAccPtSuccMsActivatedDynPdps, cgprsAccPtMsDeactivatedPdps, 
--    cgprsAccPtSuccMsDeactivatedPdps, cgprsAccPtNetworkInitPdps, 
--    cgprsAccPtSuccNetworkInitPdps, cgprsAccPtGgsnDeactivatedPdps, 
--    cgprsAccPtSuccGgsDeactivatedPdps, cgprsAccPtActivePdps, 
--    cgprsAccPtUpstreamTrafficVol, cgprsAccPtDownstreamTrafficVol, 
--    cgprsAccPtSourceAddrViolTpdus, cgprsAccPtDestAddrViolTpdus, 
--    cgprsAccPtRedirInterMobilTraffic

cgprsAccPtExtMIBGroupRev2 OBJECT IDENTIFIER ::= { cgprsAccPtMIBGroups 9 }
-- OBJECT-GROUP
--  Status
--    deprecated
--  Descr
--    A collection of objects providing APN configurations.
--    This is deprecated by cgprsAccPtExtMIBGroupRev3.
--  objects
--    cgprsAccPtIPAccListInEnable, cgprsAccPtIPAccListOutEnable, 
--    cgprsAccPtGtpRespMesgWaitAcctng, 
--    cgprsAccPtVerifyUpStrTpduSrcAddr, 
--    cgprsAccPtVerifyUpStrTpduDstAddr, 
--    cgprsAccPtRedirInterMobilAddrTyp, 
--    cgprsAccPtRedirInterMobilAddr, 
--    cgprsAccPtSuppressRadiusAttribs

cgprsAccPtExtMIBGroupRev3 OBJECT IDENTIFIER ::= { cgprsAccPtMIBGroups 10 }
-- OBJECT-GROUP
--  Status
--    mandatory
--  Descr
--    A collection of objects providing APN configurations.
--  objects
--    cgprsAccPtIPAccListInEnable, cgprsAccPtIPAccListOutEnable, 
--    cgprsAccPtGtpRespMesgWaitAcctng, 
--    cgprsAccPtVerifyUpStrTpduSrcAddr, 
--    cgprsAccPtVerifyUpStrTpduDstAddr, 
--    cgprsAccPtRedirInterMobilAddrTyp, 
--    cgprsAccPtRedirInterMobilAddr, 
--    cgprsAccPtSuppressRadiusAttribs, 
--    cgprsAccPtInterimAccountinEnable, 
--    cgprsAccPtSetRadiusAttributes, cgprsAccPtOperationMode, 
--    cgprsAccPtAbsoluteSessionTimer, cgprsAccPtRadiusAttrNasId, 
--    cgprsAccPtPdpInServicePolicyName, 
--    cgprsAccPtPdpOutServicePolicyNam, 
--    cgprsAccPtPppRegenVerifyDomain, cgprsAccPtIpAddrLocalPoolName

cgprsAccPtGenServerGroup OBJECT IDENTIFIER ::= { cgprsAccPtMIBGroups 11 }
-- OBJECT-GROUP
--  Status
--    mandatory
--  Descr
--    A collection of objects providing address of generic
--    server configurations on the APN.
--  objects
--    cgprsAccPtDnsServerAddrType, cgprsAccPtPriDnsServer, 
--    cgprsAccPtSecDnsServer, cgprsAccPtNetbiosServerAddrType, 
--    cgprsAccPtPriNetbiosServer, cgprsAccPtSecNetbiosServer

cgprsAccPtImsGroup OBJECT IDENTIFIER ::= { cgprsAccPtMIBGroups 12 }
-- OBJECT-GROUP
--  Status
--    deprecated
--  Descr
--    A collection of objects providing IMS configurations
--    under APN.
--  objects
--    cgprsAccPtImsEnable, cgprsAccPtPCscfGroupName, 
--    cgprsAccPtImsSigAccGroupIn, cgprsAccPtImsSigAccGroupOut, 
--    cgprsAccPtRejNonImsPdp

cgprsAccPtChargingGroup OBJECT IDENTIFIER ::= { cgprsAccPtMIBGroups 13 }
-- OBJECT-GROUP
--  Status
--    mandatory
--  Descr
--    A collection of objects providing Charging
--    configurations under APN.
--  objects
--    cgprsAccPtChgProfile, cgprsAccPtChgProfOverride, 
--    cgprsAccPtChgProfRowStatus

cgprsAccPtCacGroup OBJECT IDENTIFIER ::= { cgprsAccPtMIBGroups 14 }
-- OBJECT-GROUP
--  Status
--    mandatory
--  Descr
--    A collection of objects providing CAC configurations
--    under APN.
--  objects
--    cgprsAccPtCacPolicyName, cgprsAccPtCacUpStrBandWidthPool, 
--    cgprsAccPtCacDnStrBandWidthPool

cgprsAccPtRouteProbeGroup OBJECT IDENTIFIER ::= { cgprsAccPtMIBGroups 15 }
-- OBJECT-GROUP
--  Status
--    mandatory
--  Descr
--    A collection of objects providing configurations for
--    route probe feature on GGSN.
--  objects
--    cgprsAccPtRpDestAddrType, cgprsAccPtRpDestAddr, 
--    cgprsAccPtRpProtocol, cgprsAccPtRpDestPort, cgprsAccPtRpTtl

cgprsAccPtStatisticsGroupRev2 OBJECT IDENTIFIER ::= { cgprsAccPtMIBGroups 16 }
-- OBJECT-GROUP
--  Status
--    deprecated
--  Descr
--    A collection of objects providing GPRS access point
--    performance statistics per name. This is deprecated by
--    cgprsAccPtStatisticsGroupRev3.
--  objects
--    cgprsAccPtMsActivatedPdps, cgprsAccPtSuccMsActivatedPdps, 
--    cgprsAccPtMsActivatedDynPdps, 
--    cgprsAccPtSuccMsActivatedDynPdps, cgprsAccPtMsDeactivatedPdps, 
--    cgprsAccPtSuccMsDeactivatedPdps, cgprsAccPtNetworkInitPdps, 
--    cgprsAccPtSuccNetworkInitPdps, cgprsAccPtGgsnDeactivatedPdps, 
--    cgprsAccPtSuccGgsDeactivatedPdps, cgprsAccPtActivePdps, 
--    cgprsAccPtSourceAddrViolTpdus, cgprsAccPtDestAddrViolTpdus, 
--    cgprsAccPtRedirInterMobilTraffic, 
--    cgprsAccPtRevUpstreamTrafficVol, 
--    cgprsAccPtRevDownstrTrafficVol, cgprsAccPtUpstreamPacketCount, 
--    cgprsAccPtDownstreamPacketCount, cgprsAccPtDhcpAddrRequests, 
--    cgprsAccPtSuccDhcpAddrRequests, cgprsAccPtDhcpAddrReleases

cgprsAccPtThruPutGroup OBJECT IDENTIFIER ::= { cgprsAccPtMIBGroups 17 }
-- OBJECT-GROUP
--  Status
--    mandatory
--  Descr
--    A collection of objects providing throughput statistics
--    per APN.
--  objects
--    cgprsAccPtThruPutLastCollected, cgprsAccPtUpstrByteCount, 
--    cgprsAccPtDownstrByteCount, cgprsAccPtUpstrPktCount, 
--    cgprsAccPtDownstrPktCount

cgprsAccPtNotifInfoGroup OBJECT IDENTIFIER ::= { cgprsAccPtMIBGroups 18 }
-- OBJECT-GROUP
--  Status
--    mandatory
--  Descr
--    A collection of objects providing notification info on
--    an APN.
--  objects
--    cgprsAccPtMsAddrType, cgprsAccPtMsAllocAddr, 
--    cgprsAccPtMsNewAddr, cgprsAccPtMsTpduDstAddr

cgprsAccPtMIBR60Group OBJECT IDENTIFIER ::= { cgprsAccPtMIBGroups 20 }
-- OBJECT-GROUP
--  Status
--    mandatory
--  Descr
--    A collection of objects added as a part of GGSN R6.0
--    release.
--  objects
--    cgprsAccPtServiceAware, cgprsAccPtAdvDownlinkNextHopAddrType, 
--    cgprsAccPtAdvDownlinkNextHopAddr

cgprsAccPtIpv6Group OBJECT IDENTIFIER ::= { cgprsAccPtMIBGroups 21 }
-- OBJECT-GROUP
--  Status
--    mandatory
--  Descr
--    A collection of objects providing configurations for
--    IPv6 feature on GGSN.
--  objects
--    cgprsAccPtIpv6BaseVTemplate, cgprsAccPtIpv6DnsAddrType, 
--    cgprsAccPtIpv6DnsPriAddress, cgprsAccPtIpv6DnsSecAddress, 
--    cgprsAccPtIpv6Enable, cgprsAccPtIpv6Exclusive, 
--    cgprsAccPtIpv6AccessGroupDown, cgprsAccPtIpv6AccessGroupUp, 
--    cgprsAccPtIpv6AddrPool, cgprsAccPtIpv6AddrLocalPoolName, 
--    cgprsAccPtIpv6Redirect, cgprsAccPtIpv6RedirectAddrType, 
--    cgprsAccPtIpv6RedirectAddr, cgprsAccPtIpv6SecurityVerifySrc, 
--    cgprsAccPtIpv6SecurityVerifyDst

cgprsAccPtStatisticsGroupRev3 OBJECT IDENTIFIER ::= { cgprsAccPtMIBGroups 22 }
-- OBJECT-GROUP
--  Status
--    mandatory
--  Descr
--    A collection of objects providing GPRS access point
--    performance statistics per name.
--  objects
--    cgprsAccPtMsActivatedPdps, cgprsAccPtSuccMsActivatedPdps, 
--    cgprsAccPtMsActivatedDynPdps, 
--    cgprsAccPtSuccMsActivatedDynPdps, cgprsAccPtMsDeactivatedPdps, 
--    cgprsAccPtSuccMsDeactivatedPdps, cgprsAccPtNetworkInitPdps, 
--    cgprsAccPtSuccNetworkInitPdps, cgprsAccPtGgsnDeactivatedPdps, 
--    cgprsAccPtSuccGgsDeactivatedPdps, cgprsAccPtActivePdps, 
--    cgprsAccPtSourceAddrViolTpdus, cgprsAccPtDestAddrViolTpdus, 
--    cgprsAccPtRedirInterMobilTraffic, 
--    cgprsAccPtRevUpstreamTrafficVol, 
--    cgprsAccPtRevDownstrTrafficVol, cgprsAccPtUpstreamPacketCount, 
--    cgprsAccPtDownstreamPacketCount, cgprsAccPtDhcpAddrRequests, 
--    cgprsAccPtSuccDhcpAddrRequests, cgprsAccPtDhcpAddrReleases, 
--    cgprsAccPtIpv6MsActivatedPdps, 
--    cgprsAccPtIpv6MsSuccActivatedPdps, 
--    cgprsAccPtIpv6NetworkInitDeactPdps, 
--    cgprsAccPtIpv6NetworkInitDeactSuccPdps, 
--    cgprsAccPtIpv6MsActivatedDynPdps, 
--    cgprsAccPtIpv6MsSuccActivatedDynPdps, 
--    cgprsAccPtIpv6MsDeactivatedPdps, 
--    cgprsAccPtIpv6MsSuccDeactivatedPdps, 
--    cgprsAccPtIpv6GgsnDeactivatedPdps, 
--    cgprsAccPtIpv6GgsnSuccDeactivatedPdps, 
--    cgprsAccPtIpv6UpstreamTrafficVolume, 
--    cgprsAccPtIpv6DownstreamTrafficVolume, 
--    cgprsAccPtIpv6UpstreamPackets, 
--    cgprsAccPtIpv6DownstreamPackets

cgprsAccPtPcscfGroup OBJECT IDENTIFIER ::= { cgprsAccPtMIBGroups 23 }
-- OBJECT-GROUP
--  Status
--    mandatory
--  Descr
--    A collection of pcscf related objects.
--  objects
--    cgprsAccPtPcscfServerGroupName

cgprsAccPtMIBR80Group OBJECT IDENTIFIER ::= { cgprsAccPtMIBGroups 24 }
-- OBJECT-GROUP
--  Status
--    mandatory
--  Descr
--    A collection of config objects added for GGSN 8.0.
--  objects
--    cgprsAccPtGtpUpdateFailDelete, 
--    cgprsAccPtAaaAccountInterPeriod

cgprsAccPtStatisticsGroupSup1 OBJECT IDENTIFIER ::= { cgprsAccPtMIBGroups 25 }
-- OBJECT-GROUP
--  Status
--    mandatory
--  Descr
--    A collection of objects providing GPRS access point
--    performance statistics per name.
--  objects
--    cgprsAccPtPdpUpdateReqSent, cgprsAccPtSuccPdpUpdateResRcvd, 
--    cgprsAccPtCoaRcvd, cgprsAccPtCoaSuccess, cgprsAccPtDtEnabled

cgprsAccPtMIBR80GroupSup1 OBJECT IDENTIFIER ::= { cgprsAccPtMIBGroups 26 }
-- OBJECT-GROUP
--  Status
--    mandatory
--  Descr
--    A collection of config objects added for GGSN 8.0.
--  objects
--    cgprsAccPtAaaAccountInterRadius

cgprsAccPtMIBNotifGroup OBJECT IDENTIFIER ::= { cgprsAccPtMIBGroups 6 }
-- NOTIFICATION-GROUP
--  Status
--    deprecated
--  Descr
--    A collection of objects providing GPRS access point
--    notifications.
--  notifications
--    cgprsAccPtCfgNotif

cgprsAccPtMIBNotifGroupRev1 OBJECT IDENTIFIER ::= { cgprsAccPtMIBGroups 19 }
-- NOTIFICATION-GROUP
--  Status
--    mandatory
--  Descr
--    A collection of objects providing GPRS access point
--    notifications.
--  notifications
--    cgprsAccPtCfgNotif, cgprsAccPtSecSrcViolNotif, 
--    cgprsAccPtSecDestViolNotif, cgprsAccPtMaintenanceNotif, 
--    cgprsAccPtInServiceNotif

cgprsAccPtMIBCompliance OBJECT IDENTIFIER ::= { cgprsAccPtMIBCompliances 1 }
-- MODULE-COMPLIANCE
--  Status
--    obsolete
--  Descr
--    The compliance statements for entities which
--    implement the CISCO-GPRS-ACC-PT-MIB.
--  Module
--    >>current<<
--   MandGroup
--    cgprsAccPtMIBGroup
--   MandGroup
--    cgprsAccPtCfgNotifGroup

cgprsAccPtMIBComplianceRev1 OBJECT IDENTIFIER ::= { cgprsAccPtMIBCompliances 2 }
-- MODULE-COMPLIANCE
--  Status
--    obsolete
--  Descr
--    The compliance statements for entities which
--    implement the CISCO-GPRS-ACC-PT-MIB.
--  Module
--    >>current<<
--   MandGroup
--    cgprsAccPtMIBGroupRev1
--   MandGroup
--    cgprsAccPtCfgNotifGroup
--   MandGroup
--    cgprsAccPtStatisticsGroup
--   MandGroup
--    cgprsAccPtExtMIBGroup
--   MandGroup
--    cgprsAccPtMIBNotifGroup

cgprsAccPtMIBComplianceRev2 OBJECT IDENTIFIER ::= { cgprsAccPtMIBCompliances 3 }
-- MODULE-COMPLIANCE
--  Status
--    obsolete
--  Descr
--    The compliance statements for entities which
--    implement the CISCO-GPRS-ACC-PT-MIB. This is
--    obsoleted by cgprsAccPtMIBComplianceRev3.
--  Module
--    >>current<<
--   MandGroup
--    cgprsAccPtMIBGroupRev1
--   MandGroup
--    cgprsAccPtCfgNotifGroup
--   MandGroup
--    cgprsAccPtStatisticsGroupRev1
--   MandGroup
--    cgprsAccPtExtMIBGroupRev1
--   MandGroup
--    cgprsAccPtMIBNotifGroup

cgprsAccPtMIBComplianceRev3 OBJECT IDENTIFIER ::= { cgprsAccPtMIBCompliances 4 }
-- MODULE-COMPLIANCE
--  Status
--    deprecated
--  Descr
--    The compliance statements for entities which
--    implement the CISCO-GPRS-ACC-PT-MIB. This is
--    deprecated by cgprsAccPtMIBComplianceRev4.
--  Module
--    >>current<<
--   MandGroup
--    cgprsAccPtMIBGroupRev1
--   MandGroup
--    cgprsAccPtCfgNotifGroup
--   MandGroup
--    cgprsAccPtStatisticsGroupRev1
--   MandGroup
--    cgprsAccPtExtMIBGroupRev2
--   MandGroup
--    cgprsAccPtMIBNotifGroup

cgprsAccPtMIBComplianceRev4 OBJECT IDENTIFIER ::= { cgprsAccPtMIBCompliances 5 }
-- MODULE-COMPLIANCE
--  Status
--    deprecated
--  Descr
--    The compliance statements for entities which
--    implement the CISCO-GPRS-ACC-PT-MIB.
--  Module
--    >>current<<
--   MandGroup
--    cgprsAccPtMIBGroupRev1
--   MandGroup
--    cgprsAccPtCfgNotifGroup
--   MandGroup
--    cgprsAccPtExtMIBGroupRev3
--   MandGroup
--    cgprsAccPtGenServerGroup
--   MandGroup
--    cgprsAccPtImsGroup
--   MandGroup
--    cgprsAccPtChargingGroup
--   MandGroup
--    cgprsAccPtCacGroup
--   MandGroup
--    cgprsAccPtRouteProbeGroup
--   MandGroup
--    cgprsAccPtStatisticsGroupRev2
--   MandGroup
--    cgprsAccPtThruPutGroup
--   MandGroup
--    cgprsAccPtNotifInfoGroup
--   MandGroup
--    cgprsAccPtMIBNotifGroupRev1

cgprsAccPtMIBComplianceRev5 OBJECT IDENTIFIER ::= { cgprsAccPtMIBCompliances 6 }
-- MODULE-COMPLIANCE
--  Status
--    deprecated
--  Descr
--    The compliance statements for entities which
--    implement the CISCO-GPRS-ACC-PT-MIB.
--  Module
--    >>current<<
--   MandGroup
--    cgprsAccPtMIBGroupRev1
--   MandGroup
--    cgprsAccPtCfgNotifGroup
--   MandGroup
--    cgprsAccPtExtMIBGroupRev3
--   MandGroup
--    cgprsAccPtGenServerGroup
--   MandGroup
--    cgprsAccPtImsGroup
--   MandGroup
--    cgprsAccPtChargingGroup
--   MandGroup
--    cgprsAccPtCacGroup
--   MandGroup
--    cgprsAccPtRouteProbeGroup
--   MandGroup
--    cgprsAccPtStatisticsGroupRev2
--   MandGroup
--    cgprsAccPtThruPutGroup
--   MandGroup
--    cgprsAccPtNotifInfoGroup
--   MandGroup
--    cgprsAccPtMIBNotifGroupRev1
--   MandGroup
--    cgprsAccPtMIBR60Group

cgprsAccPtMIBComplianceRev6 OBJECT IDENTIFIER ::= { cgprsAccPtMIBCompliances 7 }
-- MODULE-COMPLIANCE
--  Status
--    deprecated
--  Descr
--    The compliance statements for entities which
--    implement the CISCO-GPRS-ACC-PT-MIB.
--  Module
--    >>current<<
--   MandGroup
--    cgprsAccPtMIBGroupRev1
--   MandGroup
--    cgprsAccPtCfgNotifGroup
--   MandGroup
--    cgprsAccPtExtMIBGroupRev3
--   MandGroup
--    cgprsAccPtGenServerGroup
--   MandGroup
--    cgprsAccPtImsGroup
--   MandGroup
--    cgprsAccPtChargingGroup
--   MandGroup
--    cgprsAccPtCacGroup
--   MandGroup
--    cgprsAccPtRouteProbeGroup
--   MandGroup
--    cgprsAccPtStatisticsGroupRev3
--   MandGroup
--    cgprsAccPtThruPutGroup
--   MandGroup
--    cgprsAccPtNotifInfoGroup
--   MandGroup
--    cgprsAccPtMIBNotifGroupRev1
--   MandGroup
--    cgprsAccPtMIBR60Group
--   MandGroup
--    cgprsAccPtIpv6Group

cgprsAccPtMIBComplianceRev7 OBJECT IDENTIFIER ::= { cgprsAccPtMIBCompliances 8 }
-- MODULE-COMPLIANCE
--  Status
--    deprecated
--  Descr
--    The compliance statements for entities which
--    implement the CISCO-GPRS-ACC-PT-MIB.
--  Module
--    >>current<<
--   MandGroup
--    cgprsAccPtMIBGroupRev1
--   MandGroup
--    cgprsAccPtCfgNotifGroup
--   MandGroup
--    cgprsAccPtExtMIBGroupRev3
--   MandGroup
--    cgprsAccPtGenServerGroup
--   MandGroup
--    cgprsAccPtChargingGroup
--   MandGroup
--    cgprsAccPtCacGroup
--   MandGroup
--    cgprsAccPtRouteProbeGroup
--   MandGroup
--    cgprsAccPtStatisticsGroupRev3
--   MandGroup
--    cgprsAccPtThruPutGroup
--   MandGroup
--    cgprsAccPtNotifInfoGroup
--   MandGroup
--    cgprsAccPtMIBNotifGroupRev1
--   MandGroup
--    cgprsAccPtMIBR60Group
--   MandGroup
--    cgprsAccPtIpv6Group
--   MandGroup
--    cgprsAccPtPcscfGroup

cgprsAccPtMIBComplianceRev8 OBJECT IDENTIFIER ::= { cgprsAccPtMIBCompliances 9 }
-- MODULE-COMPLIANCE
--  Status
--    deprecated
--  Descr
--    The compliance statements for entities which
--    implement the CISCO-GPRS-ACC-PT-MIB. This is deprecated
--    by cgprsAccPtMIBComplianceRev9.
--  Module
--    >>current<<
--   MandGroup
--    cgprsAccPtMIBGroupRev1
--   MandGroup
--    cgprsAccPtCfgNotifGroup
--   MandGroup
--    cgprsAccPtExtMIBGroupRev3
--   MandGroup
--    cgprsAccPtGenServerGroup
--   MandGroup
--    cgprsAccPtChargingGroup
--   MandGroup
--    cgprsAccPtCacGroup
--   MandGroup
--    cgprsAccPtRouteProbeGroup
--   MandGroup
--    cgprsAccPtStatisticsGroupRev3
--   MandGroup
--    cgprsAccPtThruPutGroup
--   MandGroup
--    cgprsAccPtNotifInfoGroup
--   MandGroup
--    cgprsAccPtMIBNotifGroupRev1
--   MandGroup
--    cgprsAccPtMIBR60Group
--   MandGroup
--    cgprsAccPtIpv6Group
--   MandGroup
--    cgprsAccPtPcscfGroup
--   MandGroup
--    cgprsAccPtMIBR80Group
--   MandGroup
--    cgprsAccPtStatisticsGroupSup1

cgprsAccPtMIBComplianceRev9 OBJECT IDENTIFIER ::= { cgprsAccPtMIBCompliances 10 }
-- MODULE-COMPLIANCE
--  Status
--    mandatory
--  Descr
--    The compliance statements for entities which
--    implement the CISCO-GPRS-ACC-PT-MIB.
--  Module
--    >>current<<
--   MandGroup
--    cgprsAccPtMIBGroupRev1
--   MandGroup
--    cgprsAccPtCfgNotifGroup
--   MandGroup
--    cgprsAccPtExtMIBGroupRev3
--   MandGroup
--    cgprsAccPtGenServerGroup
--   MandGroup
--    cgprsAccPtChargingGroup
--   MandGroup
--    cgprsAccPtCacGroup
--   MandGroup
--    cgprsAccPtRouteProbeGroup
--   MandGroup
--    cgprsAccPtStatisticsGroupRev3
--   MandGroup
--    cgprsAccPtThruPutGroup
--   MandGroup
--    cgprsAccPtNotifInfoGroup
--   MandGroup
--    cgprsAccPtMIBNotifGroupRev1
--   MandGroup
--    cgprsAccPtMIBR60Group
--   MandGroup
--    cgprsAccPtIpv6Group
--   MandGroup
--    cgprsAccPtPcscfGroup
--   MandGroup
--    cgprsAccPtMIBR80Group
--   MandGroup
--    cgprsAccPtStatisticsGroupSup1
--   MandGroup
--    cgprsAccPtMIBR80GroupSup1


END
