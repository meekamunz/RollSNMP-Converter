-- MIB file created 29-Oct-2007 20:24:40, by
--   SMICng version 2.2.11-beta(PRO)(Solaris), January 20, 2001. Enterprise key cisco.com

CISCO-CLASS-BASED-QOS-MIB DEFINITIONS ::= BEGIN

-- From file: "CISCO-CLASS-BASED-QOS-MIB.my"
-- Compile options "4 7 F H N O W 03 06 0B 0G 0N 0T"

IMPORTS
    DisplayString, TruthValue
            FROM SNMPv2-TC-v1
    ifIndex, InterfaceIndex
            FROM IF-MIB
    VlanIndex
            FROM Q-BRIDGE-MIB
    Unsigned64, EntPhysicalIndexOrZero
            FROM CISCO-TC
    DlciNumber
            FROM CISCO-FRAME-RELAY-MIB
    ciscoMgmt
            FROM CISCO-SMI
    Counter, Gauge
            FROM RFC1155-SMI
    OBJECT-TYPE
            FROM RFC-1212;

ciscoCBQosMIB OBJECT IDENTIFIER ::= { ciscoMgmt 166 }
-- MODULE-IDENTITY
--  LastUpdated
--    200710090000Z
--  OrgName
--    Cisco Systems, Inc.
--  ContactInfo
--    Cisco Systems
--    Customer Service
--    
--    Postal: 170 W. Tasman Drive
--    San Jose, CA  95134-1706
--    USA
--    
--    Tel: +1 800 553-NETS
--    
--    E-mail: cs-qos@cisco.com
--  Descr
--    Cisco Class-Based QoS MIB
--    
--    **********************************
--                Overview
--    **********************************
--    This MIB provides read access to Quality of Service (QoS) 
--    configuration and statistics information for Cisco 
--    platforms that support the Modular Quality of Service 
--    Command-line Interface (Modular QoS CLI).  We recommend 
--    users of this MIB to review the user documentation of 
--    MQC based QoS features.
--    
--    Configuration information available through this MIB includes
--    all ClassMap, PolicyMap, Match Statements, and Feature 
--    Actions configuration parameters. The definitions of each
--    objects mentioned above are explained in the QoS objects
--    section.
--    
--    Statistics available through this MIB include summary
--    counts/rates by traffic class before and after any configured
--    QoS policies are enforced.  In addition, detailed
--    feature-specific statistics are available for select
--    PolicyMap features.
--    
--    Contact your Cisco representative to determine on which
--    platforms the MIB is currently supported.
--    
--    **********************************
--               QoS  Acronyms
--    **********************************
--    BECN: Frame Relay Backward Explicit Congestion Notification
--    CIR : Committed Information Rate
--    DSCP: Differentiated Service Code Point
--    EB  : Estimate Bandwidth
--    ECN : Explicite Congestion Notification
--    FECN: Frame Relay Forward Explicit Congestion Notification
--    IPHC: Internet Protocol Header Compression 
--    IPSLAs: IP Service Level Agreement Technologies
--    PIR : Peak Information Rate
--    PREC: Precedence
--    QoS : Quality Of Services
--    RED : Random Early Detect
--    SRP : Spatial Reuse Protocol
--    WRED: Weighted Random Early Detect
--    
--    **********************************
--                MIB Objects
--    **********************************
--    This MIB consists of the following object groups:
--    1 :  cbQosServicePolicy
--    2 :  cbQosInterfacePolicy
--    3 :  cbQosFrameRelayVCPolicy
--    4 :  cbQosATMPVCPolicy
--    5 :  cbQosObjects
--    6 :  cbQosPolicyMapCfg
--    7 :  cbQosClassMapCfg
--    8 :  cbQosMatchStmtCfg
--    9 :  cbQosQueueingCfg
--    10:  cbQosREDCfg
--    11:  cbQosREDClassCfg
--    12:  cbQosPoliceCfg
--    13:  cbQosTSCfg
--    14:  cbQosSetCfg
--    15:  cbQosClassMapStats
--    16:  cbQosMatchStmtStats
--    17:  cbQosPoliceStats
--    18:  cbQosQueueingStats
--    19:  cbQosTSStats
--    20:  cbQosREDClassStats
--    21:  cbQosPoliceActionCfg
--    22:  cbQosIPHCCfg
--    23:  cbQosIPHCStats
--    24:  cbQosSetStats
--    25:  cbQosPoliceColorStats
--    26:  cbQosTableMapCfg
--    27:  cbQosTableMapValueCfg
--    28:  cbQosTableMapSetCfg
--    29:  cbQosEBCfg
--    30:  cbQosEBStats
--    31:  cbQosMeasureIPSLACfg
--    
--    **********************************
--              Definitions
--    **********************************
--    A logical interface in the context of this MIB is either
--    a main-interface, a sub-interface, a Frame Relay DLCI,
--    an ATM virtual circuit or the control-plane on the router.
--    
--    The (aggregate) control-plane on the router is defined as 
--    a collection of processes running at process level on the
--    platform (route) processor. This includes the functions 
--    related to networking control capabilities such as routing,
--    signaling, provisioning, as well as resource and service 
--    discovery. Also includes process switched traffic on the
--    device. 
--    
--    The term distributed control plane, in the context of 
--    this mib, represents the control-plane functionality at
--    the level of individual linecards. This is only
--    applicable for the case of distributed platforms.
--    
--    **********************************
--               QoS Objects
--    **********************************
--    To understand Class-Based QoS features and how to navigate 
--    the MIB tables above, the key element is to comprehend the 
--    relationships among the different QoS objects. QoS objects 
--    consist of ClassMaps, Match Statements and PolicyMaps, 
--    and each Feature Actions. 
--    
--    Match Statement - The specific match criteria to identify
--    packets for classification purposes.
--    
--    ClassMap - A user-defined traffic class that contains
--    one or many match statements used to classify packets into
--    different categories.
--    
--    Feature Action - An action is a QoS feature. Features 
--    include police, traffic-shaping, queueing, random detect 
--    and packet marking(set). After the traffic is being 
--    classified, based on the traffic classification, we can 
--    apply these action to each traffic class.
--    
--    PolicyMap - A user-defined policy that associates each QoS 
--    action to the user-defined traffic class (ClassMap).
--    
--    Service Policy - Service policy is a policymap
--    that is being attached to a logical interface. Because a
--    policymap can also be a part of the hierarchical structure 
--    (inside a classmap), only a policymap that is directly 
--    attached to a logical interface is considered a service 
--    policy.  Each service policy is uniquely identified by an 
--    index called cbQosPolicyIndex. This number is usually 
--    identical to its cbQosObjectsIndex as a policymap.
--    
--    *****************************************
--    Runtime Instance vs Configuration objects
--    *****************************************
--    
--    Each QoS objects have 2 sets of behaviours : 
--    1: A configuration instance
--    - Each QoS objects has it's configuration portion of
--      information attached to it. This information does
--      not change whether this object is attached on multiple
--      logical interfaces and used multiple times. We
--      uniquely identify each QoS object with identical
--      configuration with the same index - cbQosConfigIndex.
--      This index is used in all configuration related
--      tables. 
--    
--    2: A runtime instance
--    - Each QoS objects has it's statistical portion of
--      information attached to it. This information changes
--      when this object is attached on multiple logical 
--      interfaces and used in various different places. We
--      uniquely identify each QoS runtime object instance 
--      with an index that is unique across multiple 
--      instances of the identical object - cbQosObjectsIndex.
--      This index is used in all statistical related tables. 
--    
--    In summary, a QoS object has 2 indexes associated with it:
--    cbQosConfigIndex is used to identify it's configuration, 
--    which does not change regardless of number of times and
--    where it is being used; and cbQosObjectsIndex is used 
--    to identify it's runtime statistics, depending on which
--    logical interface and where in a given PolicyMap hierarchy
--    this object is used, it may have multiple unique 
--    identifiers to distinguish each unique usage (instance) of
--    the same object.
--    
--    **********************************
--                Navigation
--    **********************************
--    The recommended method of navigating through all of the MIB 
--    tables is to start by learning the cbQosServicePolicyTable 
--    and cbQosObjectsTable MIB tables. In particular, Cisco 
--    Systems recommends understanding the cbQosObjectsIndex and 
--    cbQosParentObjectsIndex of each QoS feature.
--    
--    The cbQosPolicyIndex and cbQosObjectsIndex are 
--    system-assigned numbers that identify each unique instance 
--    of a QoS feature. These indexes are never reused between 
--    router reboots, even when changes are made to the QoS 
--    configuration. The cbQosPolicyIndex is designed to identify 
--    the service policies attached to logical interfaces, while 
--    the cbQosObjectsIndex is designed to identify each QoS 
--    feature on a specified device.
--    
--    The cbQosParentObjectsIndex is designed to show the 
--    hierarchical relationship of each QoS feature. 
--    
--    **********************************
--            cbQosServicePolicyTable
--    **********************************
--    Accessing cbQosServicePolicyTable requires 
--    cbQosPolicyIndex. This index is a system-assigned number 
--    to uniquely identify each service policy hanging off of
--    each logical interface. Given cbQosPolicyIndex the tables
--    provide the type of logical interface/media type on which
--    this policy is applied, the direction in which this policy
--    is enforced, and the SNMP interface index and/or the entity
--    index of the underlying interface/entity. In the case of a
--    policy being applied on a Frame Relay DLCI, the cbQosFrDLCI
--    gives you the Frame Relay DLCI number to which this policy
--    is attached. In the case of policy being attached to an ATM
--    VC, cbQosAtmVPI and cbQosAtmVCI display the VPI and VCI of 
--    the ATM interface respectively.
--    
--    **********************************
--            cbQosObjectsTable
--    **********************************
--    Accessing cbQosObjectsTable requires two indexes, 
--    cbQosPolicyIndex and cbQosObjectsIndex. 
--    
--    Given a particular service policy on a given logical 
--    interface, there could be PolicyMaps, ClassMaps, Match 
--    Statements and Feature Actions being used. Each instance 
--    of these objects is uniquely identified by
--    cbQosObjectsIndex.
--    
--    Users need to decide which QoS object is interesting 
--    and use the cbQosPolicyIndex and cbQosObjectsIndex to
--    locate the right element of interest. This tables provides 
--    cbQosObjectsType, cbQosConfigIndex, and 
--    cbQosParentObjectsIndex. 
--    
--    To understand the relationship of cbQosObjectsIndex, 
--    cbQosParentObjectsIndex and the hierarchical relationship 
--    of the QoS objects, consider the following QoS 
--    configuration example:
--    
--    Interface ethernet 0/1
--    Input Service Policy cntlWebTraffic
--            ClassMap http
--                    match ip http
--                    set ip precedence 5
--    
--    Output Service Policy cntlSNMP_Telnet
--            ClassMap snmp
--                    match ip snmp
--                    shape average 8000 32 32
--            ClassMap Telnet
--                    match ip telnet
--                    shape average 10000 32 32
--    
--    Interface ethernet 0/2
--    Input Service Policy cntlWebTraffic
--            ClassMap http
--                    match ip http
--                    set ip precedence 5
--    
--    Output Service Policy cntlSNMP_Telnet
--            ClassMap snmp
--                    match ip snmp
--                    shape average 8000 32 32
--            ClassMap Telnet
--                    match ip telnet
--                    shape average 10000 32 32
--    
--    *** In Ethernet 0/1 ***
--    Assume the router assigned a cbQosConfigIndex=1024 and 
--    cbQosObjectsIndex=1084 to Policy cntlWebTraffic. 
--    Because it is attached to an interface, it has no parent 
--    QoS object, and thus cbQosParentObjectsIndex=0. 
--    In addition, because cntlWebTraffic is also the service 
--    policy of the interface, it has a unique cbQosPolicyIndex 
--    assigned to it. In most cases, it would be the same as 
--    the cbQosObjectsIndex, which is 1084 in this case. 
--    Therefore, the indexes are:
--    cbQosPolicyIndex = 1084
--    cbQosObjectsIndex = 1084
--    cbQosConfigIndex = 1024
--    
--    Assuming the router assigned a cbQosObjectsIndex=1085 
--    and cbQosConfigIndex=1025 to ClassMap http, it is 
--    directly being used by Policy cntlWebTraffic, and therefore
--    the cbQosParentObjectsIndex of ClassMap http will be 1084. 
--    
--    Assuming the router assigned a cbQosConfigIndex=1026 and
--    cbQosObjectsIndex=1086 to match ip http, it is directly 
--    used by ClassMap http, therefore the 
--    cbQosParentObjectsIndex of match ip http will be 1085.
--    
--    Assuming the router assigned a cbQosConfigIndex=1027 and
--    cbQosObjectsIndex=1087 to set ip precedence 5, it is 
--    directly used by ClassMap http, therefore the 
--    cbQosParentObjectsIndex of match ip http will be 1085.
--    
--    Assuming the router assigned a cbQosConfigIndex=1028 and 
--    cbQosObjectsIndex=1088 to Policy cntlSNMP_Telnet. 
--    Because it is attached to an interface, it has no parent 
--    QoS object, and thus cbQosParentObjectsIndex=0. 
--    In addition, because cntlSNMP_Telnet is also the service 
--    policy of the interface, it has a unique cbQosPolicyIndex 
--    assigned to it. In most cases, it would be the same as 
--    the cbQosObjectsIndex, which is 1088 in this case.
--    
--    Assuming the router assigned a cbQosConfigIndex=1029 and
--    cbQosObjectsIndex=1089 to ClassMap snmp, it is 
--    directly being used by Policy cntlSNMP_Telnet, and 
--    therefore the cbQosParentObjectsIndex of ClassMap snmp 
--    will be 1088. 
--    
--    Assuming the router assigned a cbQosConfigIndex=1030 and
--    cbQosObjectsIndex=1090 to match ip snmp, it is directly 
--    used by ClassMap snmp, and therefore the 
--    cbQosParentObjectsIndex of match ip snmp will be 1089.
--    
--    Assuming the router assigned a cbQosConfigIndex=1031 and
--    cbQosObjectsIndex=1091 to shape average 8000 32 32, 
--    it is directly used by ClassMap snmp, therefore the 
--    cbQosParentObjectsIndex of match ip snmp will be 1089.
--    
--    Assuming the router assigned a cbQosConfigIndex=1032 and
--    cbQosObjectsIndex=1092 to ClassMap Telnet, it is 
--    directly being used by Policy cntlSNMP_Telnet, and 
--    therefore the cbQosParentObjectsIndex of 
--    ClassMap Telnet will be 1088. 
--    
--    Assuming the router assigned a cbQosConfigIndex=1033 and
--    cbQosObjectsIndex=1093 to match ip telnet, it is 
--    directly used by ClassMap Telnet, and therefore the 
--    cbQosParentObjectsIndex of match ip telnet will be 1092.
--    
--    Assuming the router assigned a cbQosConfigIndex=1034 and
--    cbQosObjectsIndex=1094 to shape 10000 32 32, it is 
--    directly used by ClassMap telnet, therefore the 
--    cbQosParentObjectsIndex of match ip telnet will be 1092.
--    
--    *** In Ethernet 0/2 ***
--    Every objects will have a new and unique cbQosPolicyIndex 
--    and cbQosObjectsIndex, but cbQosConfigIndex will be 
--    shared across the same objects that are applied in 
--    different places.
--    
--    **********************************
--             All Config Tables
--    **********************************
--    Accessing config related tables requires the same index 
--    - cbQosConfigIndex.  (Per precedence based tables requires 
--    a second index, which is IP precedence value) Users 
--    should have already gone through the cbQosObjectsTable 
--    at this point and understood each cbQosConfigIndex and the 
--    corresponding QoS objects.  Users can uniquely identify 
--    each QoS object defined on the router and query the 
--    entries in each stats table on a per QoS object basis.  
--    
--    **********************************
--             All Stats Tables
--    **********************************
--    Accessing all stats related tables requires the same 
--    2 indexes. They are cbQosPolicyIndex and cbQosObjectsIndex.
--    (Per precedence based tables requires a third index, which 
--    is IP precedence value) Users should have already gone 
--    through the cbQosObjectsTable at this point and understood 
--    the relationship of each cbQosPolicyIndex and 
--    cbQosObjectsIndex pair and the corresponding QoS objects. 
--    Users can uniquely identify each QoS object defined on the 
--    router and query the entries in each stats table on a per 
--    QoS object basis.
--  RevDate
--    200710090000Z
--  RevDescr
--    1. Added cbQosTSCfgRate64 to cbQosTSCfgTable 
--        to support shaping rates greater than that fit in
--        the range defined for cbQosTSCfgRate.
--     2. Created cbQosTSCfgExtGroup.    
--     3. Created  new compliance module ciscocbQosMIBComplianceRev5
--        which deprecates ciscocbQosMIBComplianceRev4.
--  RevDate
--    200708300000Z
--  RevDescr
--    Added 'setL2CosInner' value to PoliceAction TC.
--  RevDate
--    200707100000Z
--  RevDescr
--    Added following enumerations to RedMechanism TC:
--    mplsExp 
--    redDefault 
--    redUserDefault
--  RevDate
--    200409200000Z
--  RevDescr
--    1. Added vlan-port as a new InterfaceType.
--    2. Created cbQosServicePolicyExtGroup.
--  RevDate
--    200404120000Z
--  RevDescr
--    Added support for Estimate Bandwidth and its Corvil
--    implementation. Corvil's algorithm generates the 
--    estimated bandwidth for a class of traffic from 
--    knowledge of the QoS targets such as delay and drop, 
--    and the observed traffic behavior.
--  RevDate
--    200307240000Z
--  RevDescr
--    Added setIpDscpTunnel, setIpPrecedenceTunnel
--    to the PoliceAction TC. 
--    Added srpPriority, frFecnBecn, ipDscpTunnel,
--    ipPrecedenceTunnel to the SetFeatureType TC. 
--    Added l2Cos, atmClp to the REDMechanism TC. 
--    Added cps to the CbQosRateType TC. 
--    Added CbQosTMSetType TC. 
--    Added cbQosQueueingCfgAggrQLimitTime
--    to the cbQosQueueingCfgTable.
--    Added cbQosREDClassCfgMinThresholdTime,
--    cbQosREDClassCfgMaxThresholdTime
--    to the cbQosREDClassCfgTable.
--    Added cbQosPoliceCfgCellRate,
--    cbQosPoliceCfgCellPir,
--    cbQosPoliceCfgBurstCell,
--    cbQosPoliceCfgExtBurstCell,
--    cbQosPoliceCfgBurstTime,
--    cbQosPoliceCfgExtBurstTime,
--    cbQosPoliceCfgCdvt,
--    cbQosPoliceCfgConformColor,
--    cbQosPoliceCfgExceedColor 
--    to the cbQosPoliceCfgTable.
--    Added cbQosTSCfgBurstTime, cbQosTSCfgExtBurstTime 
--    to the cbQosTSCfgTable.
--    Added cbQosSetCfgSrpPriority, cbQosSetCfgFrFecnBecn 
--    to the cbQosSetCfgTable.
--    Added cbQosSetStatsTable.
--    Added cbQosPoliceColorStatsTable.
--    Added cbQosTableMapCfgTable.
--    Added cbQosTableMapValueCfgTable.
--    Added cbQosTableMapSetCfgTable.
--  RevDate
--    200306090000Z
--  RevDescr
--    Added controlPlane to the InterfaceType TC.
--    Added cbQosEntityIndex to the cbQosServicePolicyTable.
--  RevDate
--    200301210000Z
--  RevDescr
--    Added compression(9) in QosObjectType TC for IPHC;
--    Added setMplsExpTopMost(11) in PoliceAction TC for 
--          POLICE;
--    Added mplsExpTopMost(8) in SetFeatureType TC for SET;
--    Added discardClass(13) in REDMechanism TC for WRED;
--    Added CbQosRateType TC for POLICE and SHAPE;
--    Added IPHCOption TC for IPHC;
--    Added cbQosPoliceCfgRateType, 
--          cbQosPoliceCfgPercentRateValue,
--          cbQosPoliceCfgPercentPirValue for POLICE;
--    Added cbQosTSCfgRateType,
--          cbQosTSCfgPercentRateValue for SHAPE;
--    Added cbQosSetCfgMplsExpTopMostValue for SET;
--    Added cbQosIPHCCfg and cbQosIPHCStats tables for IPHC.
--  RevDate
--    200212030000Z
--  RevDescr
--    Added new cbQosPoliceCfgRate64 to cbQosPoliceCfgEntry
--    table to support policing rates greater than fit in
--    the range defined for cbQosPoliceCfgRate
--  RevDate
--    200207240000Z
--  RevDescr
--    Added support for ECN; Pir policing; multiple
--    police actions; added MPLS-EXP/ATM-CLP/DR-DE/
--    L2Cos/DiscardClass marking in police action;
--    added MPLS-EXP and DiscardClass marking; 
--    modified ATM-CLP and FR-DE marking.
--    Added objects to handle queue depth unit type and 
--    queue depth pair related objects (e.g.,
--    cbQosQueueingCfgQLimitUnits and 
--    cbQosQueueingCfgAggregateQLimit pair) to support
--    queue depth in different units.
--  RevDate
--    200103140000Z
--  RevDescr
--    Added support for FR DE, ATM CLP and L2 marking.
--    Added Bandwidth remaining percent option
--  RevDate
--    200012080000Z
--  RevDescr
--    Added support for Police Violate counters and
--    DSCP WRED counters
--  RevDate
--    200007130000Z
--  RevDescr
--    Initial version of Class-based QoS configuration and
--    statistical parameters MIB

ciscoCBQosMIBObjects OBJECT IDENTIFIER ::= { ciscoCBQosMIB 1 }
ciscocbQosMIBConformance OBJECT IDENTIFIER ::= { ciscoCBQosMIB 2 }
cbQosServicePolicy OBJECT IDENTIFIER ::= { ciscoCBQosMIBObjects 1 }
cbQosInterfacePolicy OBJECT IDENTIFIER ::= { ciscoCBQosMIBObjects 2 }
cbQosFrameRelayVCPolicy OBJECT IDENTIFIER ::= { ciscoCBQosMIBObjects 3 }
cbQosATMPVCPolicy OBJECT IDENTIFIER ::= { ciscoCBQosMIBObjects 4 }
cbQosObjects    OBJECT IDENTIFIER ::= { ciscoCBQosMIBObjects 5 }
cbQosPolicyMapCfg OBJECT IDENTIFIER ::= { ciscoCBQosMIBObjects 6 }
cbQosClassMapCfg OBJECT IDENTIFIER ::= { ciscoCBQosMIBObjects 7 }
cbQosMatchStmtCfg OBJECT IDENTIFIER ::= { ciscoCBQosMIBObjects 8 }
cbQosQueueingCfg OBJECT IDENTIFIER ::= { ciscoCBQosMIBObjects 9 }
cbQosREDCfg     OBJECT IDENTIFIER ::= { ciscoCBQosMIBObjects 10 }
cbQosREDClassCfg OBJECT IDENTIFIER ::= { ciscoCBQosMIBObjects 11 }
cbQosPoliceCfg  OBJECT IDENTIFIER ::= { ciscoCBQosMIBObjects 12 }
cbQosTSCfg      OBJECT IDENTIFIER ::= { ciscoCBQosMIBObjects 13 }
cbQosSetCfg     OBJECT IDENTIFIER ::= { ciscoCBQosMIBObjects 14 }
cbQosClassMapStats OBJECT IDENTIFIER ::= { ciscoCBQosMIBObjects 15 }
cbQosMatchStmtStats OBJECT IDENTIFIER ::= { ciscoCBQosMIBObjects 16 }
cbQosPoliceStats OBJECT IDENTIFIER ::= { ciscoCBQosMIBObjects 17 }
cbQosQueueingStats OBJECT IDENTIFIER ::= { ciscoCBQosMIBObjects 18 }
cbQosTSStats    OBJECT IDENTIFIER ::= { ciscoCBQosMIBObjects 19 }
cbQosREDClassStats OBJECT IDENTIFIER ::= { ciscoCBQosMIBObjects 20 }
cbQosPoliceActionCfg OBJECT IDENTIFIER ::= { ciscoCBQosMIBObjects 21 }
cbQosIPHCCfg    OBJECT IDENTIFIER ::= { ciscoCBQosMIBObjects 22 }
cbQosIPHCStats  OBJECT IDENTIFIER ::= { ciscoCBQosMIBObjects 23 }
cbQosSetStats   OBJECT IDENTIFIER ::= { ciscoCBQosMIBObjects 24 }
cbQosPoliceColorStats OBJECT IDENTIFIER ::= { ciscoCBQosMIBObjects 25 }
cbQosTableMapCfg OBJECT IDENTIFIER ::= { ciscoCBQosMIBObjects 26 }
cbQosTableMapValueCfg OBJECT IDENTIFIER ::= { ciscoCBQosMIBObjects 27 }
cbQosTableMapSetCfg OBJECT IDENTIFIER ::= { ciscoCBQosMIBObjects 28 }
cbQosEBCfg      OBJECT IDENTIFIER ::= { ciscoCBQosMIBObjects 29 }
cbQosEBStats    OBJECT IDENTIFIER ::= { ciscoCBQosMIBObjects 30 }
cbQosMeasureIPSLACfg OBJECT IDENTIFIER ::= { ciscoCBQosMIBObjects 31 }
ciscocbQosMIBCompliances OBJECT IDENTIFIER ::= { ciscocbQosMIBConformance 1 }
ciscocbQosMIBGroups OBJECT IDENTIFIER ::= { ciscocbQosMIBConformance 2 }

QosObjectType ::= INTEGER {
        policymap(1),
        classmap(2),
        matchStatement(3),
        queueing(4),
        randomDetect(5),
        trafficShaping(6),
        police(7),
        set(8),
        compression(9),
        ipslaMeasure(10)
        }
-- TEXTUAL-CONVENTION
--  Status
--    mandatory
--  Descr
--    Enums to indicate different QoS objects .
--    policymap      - The object in query is a PolicyMap, being
--                     attached on a logical interface.
--    classmap       - The object in query is a ClassMap, being
--                     used by it's parent PolicyMap.
--    matchStatement - The object in query is a Match Statement,
--                     being used by it's parent ClassMap.
--    queueing       - The object in query is a queueing feature being
--                     applied on the parent ClassMap.
--    randomDetect   - The object in query is a Random Detect feature 
--                     being applied on the parent ClassMap.
--    trafficShaping - The object in query is a traffic-shaping 
--                     feature being applied on the parent ClassMap.
--    police         - The object in query is a Police feature being 
--                     applied on the parent ClassMap.
--    set            - The object in query is a Packet Marking 
--                     feature being applied on the parent ClassMap.
--    compression    - The object in query is a IP header compression
--                     feature being applied on the parent ClassMap.
--    ipslaMeasure   - The object in query is Measure IPSLAs feature  
--                     being applied on the parent ClassMap.

TrafficDirection ::= INTEGER {
        input(1),
        output(2)
        }
-- TEXTUAL-CONVENTION
--  Status
--    mandatory
--  Descr
--    Enums to indicate whether the Policymap is for
--    Input or Output direction.

QosClassInfo ::= INTEGER {
        none(1),
        matchAll(2),
        matchAny(3)
        }
-- TEXTUAL-CONVENTION
--  Status
--    mandatory
--  Descr
--    Enums to indicate whether the Classmap is for
--    Match All or Match Any.

QosMatchInfo ::= INTEGER {
        none(1),
        matchNot(2)
        }
-- TEXTUAL-CONVENTION
--  Status
--    mandatory
--  Descr
--    Enums to indicate whether the MatchStatement is matching
--    on negated criteria (Match Not).

InterfaceType ::= INTEGER {
        mainInterface(1),
        subInterface(2),
        frDLCI(3),
        atmPVC(4),
        controlPlane(5),
        vlanPort(6)
        }
-- TEXTUAL-CONVENTION
--  Status
--    mandatory
--  Descr
--    Enums to indicate the type of logical interface to which
--    a particular service policy is attached.
--    Main Interface   - Service policy is attached on the main 
--                  interface.
--    Sub Interface    - Service policy is attached on the sub 
--                  interface.
--    Frame Relay DLCI - Service policy is attached on the a 
--                  Frame Relay DLCI.
--    ATM VC           - Service policy is attached on the an ATM 
--                  Virtual Circuit.
--    Control Plane    - Service policy is attached to the control
--                  plane of the device.
--    Vlan Port        - Service policy is attached to a particular
--                  vlan of a layer 2 interface that can carry
--                  traffic on multiple vlans.

QueueingBandwidthUnits ::= INTEGER {
        kbps(1),
        percentage(2),
        percentageRemaining(3)
        }
-- TEXTUAL-CONVENTION
--  Status
--    mandatory
--  Descr
--    The units of the bandwidth, used to allocate
--    bandwidth. Bandwidth can be either an absolute kbps 
--    number, or be expressed as a percentage of the 
--    available bandwidth.  
--    
--    kbps            Kilo bits Per Second
--    percentage      %

TrafficShapingLimit ::= INTEGER {
        average(1),
        peak(2)
        }
-- TEXTUAL-CONVENTION
--  Status
--    mandatory
--  Descr
--    The limit used by the traffic-shaping feature.
--    This value may be 'average' or 'peak',
--    which indicates whether it is shaping by average
--    rate or peak rate.

PoliceAction ::= INTEGER {
        transmit(1),
        setIpDSCP(2),
        setIpPrecedence(3),
        setQosGroup(4),
        drop(5),
        setMplsExp(6),
        setAtmClp(7),
        setFrDe(8),
        setL2Cos(9),
        setDiscardClass(10),
        setMplsExpTopMost(11),
        setIpDscpTunnel(12),
        setIpPrecedenceTunnel(13),
        setL2CosInner(14)
        }
-- TEXTUAL-CONVENTION
--  Status
--    mandatory
--  Descr
--    The available actions taken on packets upon
--    conforming, exceeding or violating the configured 
--    police rate.
--    
--    Transmit - Transmit the packet if the packet conforms 
--               or exceeds the configured police rate.
--    Set IP DSCP - Set the IP DSCP value if the packet
--                  conforms or exceeds the configured police
--                  rate.
--    Set IP Precedence - Set the IP precedence value if
--                        the packet conforms or exceeds 
--                        the configured police rate.
--    Set Qos Group - Set the QoS Group value if
--                    the packet conforms or exceeds 
--                    the configured police rate.
--    Set MPLS Exp - Set the MPLS Experimental Imposition
--                   vaule for the applicable action.
--    Set ATM CLP  - Set the ATM CLP bit for the
--                   applicable action.
--    Set FR DE    - Set the FR DE bit for the
--                   applicable action.
--    Set L2 COS   - Set the 802.1p priority field in 802.1Q 
--                   VLAN tag for the applicable action.
--    Set Discard Class - Set the Discard Class value for the
--                   applicable action.              
--    Drop - Drop the packet if the packet conforms or 
--           exceeds the configured police rate.
--    Set MPLS Exp TopMost - Set the MPLS Experimental 
--           TopMost vaule for the applicable action.
--    Set IP DSCP Tunnel - Set the IP DSCP Tunnel
--           value for the applicable action.
--    Set IP Precedence Tunnel - Set the IP Precedence
--           Tunnel value for the applicable action.
--    Set Inner L2 COS   - Set the 802.1p priority field in inner 
--                   802.1q VLAN tag (QinQ) for the applicable
--    action.

SetFeatureType ::= OCTET STRING(SIZE(1..2))
        -- BITS are:
        --   ipDscp(0)
        --   ipPrecedence(1)
        --   qosGroupNumber(2)
        --   frDeBit(3)
        --   atmClpBit(4)
        --   l2Cos(5)
        --   mplsExp(6)
        --   discardClass(7)
        --   mplsExpTopMost(8)
        --   srpPriority(9)
        --   frFecnBecn(10)
        --   ipDscpTunnel(11)
        --   ipPrecedenceTunnel(12)
-- TEXTUAL-CONVENTION
--  Status
--    mandatory
--  Descr
--    Bit-wise representation of packet marking feature available
--    today.  For historical reason, both packet marking and SET
--    terms have been used across Cisco Class-Based QOS, but they
--    have the same meaning.  This feature is used to mark/set
--    appropriate fields(e.g, dscp, precedence, mpls-experimental
--    -topmost) for applicable packets.

REDMechanism ::= INTEGER {
        precedence(1),
        dscp(2),
        discardClass(3),
        l2Cos(4),
        atmClp(5),
        mplsExp(6),
        redDefault(7),
        redUserDefault(8)
        }
-- TEXTUAL-CONVENTION
--  Status
--    mandatory
--  Descr
--    This denotes which mechanism is used with RED.
--    
--    precedence      Based on IP precedence
--    dscp            Based on DSCP values
--    discardClass    Based on discard class
--    l2Cos           Based on L2-COS class
--    atmClp          Based on ATM-CLP class
--    mplsExp         Based on MPLS Experimental values
--    redDefault      Default RED profile
--    redUserDefault  User specified Default RED profile

CbQosQueueUnitType ::= INTEGER {
        packets(1),
        cells(2),
        bytes(3),
        ms(4),
        us(5)
        }
-- TEXTUAL-CONVENTION
--  Status
--    mandatory
--  Descr
--    A value that represents an unit type of queue
--    size.
--    
--    packets(1)   Represents the UNITS of 'packets' for
--                 queue size.
--    
--    cells(2)     Represents the UNITS of 'cells' for 
--                 queue size.
--    
--    bytes(3)     Represents the UNITS of 'bytes' for 
--                 queue size.
--    
--    ms(4)        Represents the UNITS of 'milli-seconds' for
--                 queue size
--    
--    us(5)        Represents the UNITS of 'micro-seconds' for
--                 queue size
--    
--    To support future extensions, the CbQosQueueUnitType 
--    textual convention SHOULD NOT be sub-typed in object
--    type definitions.
--    
--    It MAY be sub-typed in compliance statements in order to
--    require only a subset of these queue size types for a 
--    compliant implementation.
--    
--    Implementations must ensure that CbQosQueueUnitType 
--    objects and any dependent object (e.g. CbQosQueueDepth) 
--    are consistent. An inconsistentValue error must be 
--    generated if an attempt to change an CbQosQueueUnitType 
--    object would lead to an undefined CbQosQueueDepth value.
--    In particular, CbQoSQueueUnitType/CbQosQueueDepth pairs 
--    must be changed together if the CbQosQueueUnitType
--    type changes (e.g. from packets(1) to cells(2)).

CbQosQueueDepth ::= Gauge
-- TEXTUAL-CONVENTION
--  Status
--    mandatory
--  Descr
--    Denotes a generic Queue depth value.
--    
--    An CbQoSQueueDepth value is always interpreted within 
--    the context of an CbQosQueueUnitType value. Every usage 
--    of the CbQosQueueDepth textual convention is required to
--    specify the CbQosQueueUnitType object which provides 
--    the context. It is suggested that the 
--    CbQoSQueueUnitType object is logically registered 
--    before the object(s) which use the CbQosQueueDepth 
--    textual convention if they appear in the same logical
--    row. The value of an CbQosQueueDepth object must always
--    be consistent with the value of the associated
--    CbQosQueueUnitType object. Attempts to set an
--    CbQosQueueDepth object to a value which is inconsistent 
--    with the associated CbQosQueueUnitType must fail with 
--    an inconsistentValue error.

CbQosRateType ::= INTEGER {
        bps(1),
        percentage(2),
        cps(3)
        }
-- TEXTUAL-CONVENTION
--  Status
--    mandatory
--  Descr
--    The type of rate.  Rate type can be either an
--    absolute bps number, or be expressed as a percentage 
--    of the available interface bandwidth, or an absolute
--    cps number.
--    
--    bps             Bits Per Second
--    percentage      %
--    cps             Cells Per Second

IPHCOption ::= INTEGER {
        rtp(1),
        tcp(2),
        bothRtpTcp(3)
        }
-- TEXTUAL-CONVENTION
--  Status
--    mandatory
--  Descr
--    Enums to indicate the type of IP header compression.
--    rtp(1)         UDP/RTP compression.
--    tcp(2)         TCP compression.
--    bothRtpTcp(3)  Both UDP/RTP and TCP compression.

CbQosTMSetType ::= INTEGER {
        --?? enum value of zero may cause problems
        none(0),
        ipDscp(1),
        ipPrecedence(2),
        qosGroup(3),
        l2Cos(4),
        mplsExpImp(5),
        mplsExpTop(6)
        }
-- TEXTUAL-CONVENTION
--  Status
--    mandatory
--  Descr
--    The available packet marking types which can use
--    tablemap to establish to-from relationship for
--    enhanced packeting marking.

CbQosEBType ::= INTEGER {
        --?? enum value of zero may cause problems
        typeNone(0),
        typeCorvil(1)
        }
-- TEXTUAL-CONVENTION
--  Status
--    mandatory
--  Descr
--    A value that indicates the type of bandwidth
--    estimate algorithm.
--    typeNone         no algorithm is selected
--    typeCorvil         algorithm based on Corvil
--                     bandwidth calculation.

CbQosEBCtd ::= OCTET STRING
-- TEXTUAL-CONVENTION
--  Status
--    mandatory
--  Descr
--    A CTD (Corvil Traffic Descriptor) specific value.

cbQosMeasureIPSLACfgTable OBJECT-TYPE
    SYNTAX SEQUENCE OF CbQosMeasureIPSLACfgEntry
    ACCESS not-accessible
    STATUS mandatory
    DESCRIPTION
        "This table specifies configuration information for measure type
        IPSLA action. The measure action relates the policy class to a
        specific IPSLAs auto group. Configuration of measure action of
        type IPSLA results in automatic generation of IPSLAs synthetic
        test operations when the policy is attached to interface. The
        operations are created according to the characteristics
        specified and to the destinations specified in IPSLA auto group.
        The IPSLAs sythentic test operations measure network statistics
        such as latency, packet loss and jitter.
        This table is to be used only for retrieving the measure
        action configuration information."
    ::= { cbQosMeasureIPSLACfg 1 }

cbQosMeasureIPSLACfgEntry OBJECT-TYPE
    SYNTAX CbQosMeasureIPSLACfgEntry
    ACCESS not-accessible
    STATUS mandatory
    DESCRIPTION
        "Each entry describes configuration information about
        one instance of IPSLAs measure action in the policy map.
        The table is indexed by the cbQosConfigIndex and
        cbQosMeasureIPSLACfgGroupIndex."
    INDEX { cbQosConfigIndex, cbQosMeasureIPSLACfgGroupIndex }
    ::= { cbQosMeasureIPSLACfgTable 1 }

CbQosMeasureIPSLACfgEntry ::= SEQUENCE {
    cbQosMeasureIPSLACfgGroupIndex Gauge,
    cbQosMeasureIPSLACfgGroupName DisplayString
    }

cbQosMeasureIPSLACfgGroupIndex OBJECT-TYPE
    SYNTAX Gauge
    ACCESS read-only
    STATUS mandatory
    DESCRIPTION
        "An arbitrary (system-assigned) index for each
        instance of IPSLAs measure action. The index is unique
        for each instance for a particular class in particular
        policy-map. For example consider following configuration:
             policy-map p1
                class c1
                  measure type ip-sla group g1
                  measure type ip-sla group g2
                class c2
                  measure type ip-sla group g3
        
        In this case the cbQosMeasureIPSLACfgGroupIndex value
        for first measure action instance under class c1 will be 1,
        for second instance it will be 1, and so on. The value
        for the index will start over again from 1 for class c2."
    ::= { cbQosMeasureIPSLACfgEntry 1 }

cbQosMeasureIPSLACfgGroupName OBJECT-TYPE
    SYNTAX DisplayString(SIZE(0..64))
--    Rsyntax OCTET STRING(SIZE(0..64))
    ACCESS read-only
    STATUS mandatory
    DESCRIPTION
        "IPSLAs auto group name. Group is an aggregation of
        operations sharing the same type, for example udp-jitter
        type, with common characteristics like frequency,
        interval etc.  Groups are formed by policies dictated
        either by customer, or by service level or any other
        requirements."
    ::= { cbQosMeasureIPSLACfgEntry 2 }

cbQosServicePolicyTable OBJECT-TYPE
    SYNTAX SEQUENCE OF CbQosServicePolicyEntry
    ACCESS not-accessible
    STATUS mandatory
    DESCRIPTION
        "This table describes the logical interfaces/media types
        and the policymap that are attached to it."
    ::= { cbQosServicePolicy 1 }

cbQosServicePolicyEntry OBJECT-TYPE
    SYNTAX CbQosServicePolicyEntry
    ACCESS not-accessible
    STATUS mandatory
    DESCRIPTION
        "Each entry in this table describes to which a logical
        interface a given policymap is attached.  Depending on 
        the logical interface/media type, some fields may have
        meaningful values, and some may not.  Please see each
        individual descriptions."
    INDEX { cbQosPolicyIndex }
    ::= { cbQosServicePolicyTable 1 }

CbQosServicePolicyEntry ::= SEQUENCE {
    cbQosPolicyIndex Gauge,
    cbQosIfType InterfaceType,
    cbQosPolicyDirection TrafficDirection,
    cbQosIfIndex InterfaceIndex,
    cbQosFrDLCI DlciNumber,
    cbQosAtmVPI Gauge,
    cbQosAtmVCI Gauge,
    cbQosEntityIndex EntPhysicalIndexOrZero,
    cbQosVlanIndex VlanIndex
    }

cbQosPolicyIndex OBJECT-TYPE
    SYNTAX Gauge
    ACCESS not-accessible
    STATUS mandatory
    DESCRIPTION
        "An arbitrary (system-assigned) index for all
        service policies (PolicyMap that has been attached
        to a given logical interface)."
    ::= { cbQosServicePolicyEntry 1 }

cbQosIfType OBJECT-TYPE
    SYNTAX InterfaceType
--    Rsyntax INTEGER {
--        mainInterface(1),
--        subInterface(2),
--        frDLCI(3),
--        atmPVC(4),
--        controlPlane(5),
--        vlanPort(6)
--        }
    ACCESS read-only
    STATUS mandatory
    DESCRIPTION
        "This describes the logical interface/media type to
        which this service policy is attached."
    ::= { cbQosServicePolicyEntry 2 }

cbQosPolicyDirection OBJECT-TYPE
    SYNTAX TrafficDirection
--    Rsyntax INTEGER {
--        input(1),
--        output(2)
--        }
    ACCESS read-only
    STATUS mandatory
    DESCRIPTION
        "This indicates the direction of traffic for which
        this service policy is applied."
    ::= { cbQosServicePolicyEntry 3 }

cbQosIfIndex OBJECT-TYPE
    SYNTAX InterfaceIndex
--    Rsyntax INTEGER(1..2147483647)
    ACCESS read-only
    STATUS mandatory
    DESCRIPTION
        "ifIndex for the interface to which this service
        is attached. This field makes sense only if the
        logical interface has a snmp ifIndex. For e.g. the
        value of this field is meaningless when the
        cbQosIfType is controlPlane."
    ::= { cbQosServicePolicyEntry 4 }

cbQosFrDLCI OBJECT-TYPE
    SYNTAX DlciNumber
--    Rsyntax INTEGER(0..1023)
    ACCESS read-only
    STATUS mandatory
    DESCRIPTION
        "DLCI for the FRVC to which this service is attached.
        This field only make sense if the service policy is
        attached to a Frame Relay DLCI."
    ::= { cbQosServicePolicyEntry 5 }

cbQosAtmVPI OBJECT-TYPE
    SYNTAX Gauge(0..4095)
    ACCESS read-only
    STATUS mandatory
    DESCRIPTION
        "VPI for the ATMVC to which this service is attached.
        This field only make sense if the service policy is
        attached to a ATM VC."
    ::= { cbQosServicePolicyEntry 6 }

cbQosAtmVCI OBJECT-TYPE
    SYNTAX Gauge(0..65535)
    ACCESS read-only
    STATUS mandatory
    DESCRIPTION
        "VCI for the ATMVC to which this service is attached.
        This field only make sense if the service policy is
        attached to a ATM VC."
    ::= { cbQosServicePolicyEntry 7 }

cbQosEntityIndex OBJECT-TYPE
    SYNTAX EntPhysicalIndexOrZero
--    Rsyntax INTEGER(0..2147483647)
    ACCESS read-only
    STATUS mandatory
    DESCRIPTION
        "In cases where the policy is attached to an entity
        e.g. control-plane, this object represents the
        entity physical index of the entity to which the
        policy has been attached. A value zero may be 
        returned if the policy is not attached to a physical
        entity or the entPhysicalTable is not supported on 
        the SNMP agent."
    ::= { cbQosServicePolicyEntry 8 }

cbQosVlanIndex OBJECT-TYPE
    SYNTAX VlanIndex
--    Rsyntax Gauge
    ACCESS read-only
    STATUS mandatory
    DESCRIPTION
        "If the service policy is attached to a particular
        vlan on a trunk or multi-vlan access port, then this
        object specifies the corresponding VLAN. In all other
        cases the value of this object is '0'."
    ::= { cbQosServicePolicyEntry 9 }

cbQosInterfacePolicyTable OBJECT-TYPE
    SYNTAX SEQUENCE OF CbQosInterfacePolicyEntry
    ACCESS not-accessible
    STATUS mandatory
    DESCRIPTION
        "This table describes the service polices that are
        attached to main and sub interfaces."
    ::= { cbQosInterfacePolicy 1 }

cbQosInterfacePolicyEntry OBJECT-TYPE
    SYNTAX CbQosInterfacePolicyEntry
    ACCESS not-accessible
    STATUS mandatory
    DESCRIPTION
        "Using ifIndex and Direction, each unique index pair
        translates to a service policy that is attached to a 
        main/sub interface, for particular traffic direction."
    INDEX { ifIndex, cbQosPolicyDirection }
    ::= { cbQosInterfacePolicyTable 1 }

CbQosInterfacePolicyEntry ::= SEQUENCE {
    cbQosIFPolicyIndex Gauge
    }

cbQosIFPolicyIndex OBJECT-TYPE
    SYNTAX Gauge
    ACCESS read-only
    STATUS mandatory
    DESCRIPTION
        "An arbitrary (system-assigned) index for all
        Service Policies. 
        
        This is identical to cbQosPolicyIndex."
    ::= { cbQosInterfacePolicyEntry 1 }

cbQosFrameRelayPolicyTable OBJECT-TYPE
    SYNTAX SEQUENCE OF CbQosFrameRelayPolicyEntry
    ACCESS not-accessible
    STATUS mandatory
    DESCRIPTION
        "This table describes the service polices that are
        attached to Frame Relay DLCIs."
    ::= { cbQosFrameRelayVCPolicy 1 }

cbQosFrameRelayPolicyEntry OBJECT-TYPE
    SYNTAX CbQosFrameRelayPolicyEntry
    ACCESS not-accessible
    STATUS mandatory
    DESCRIPTION
        "Using ifIndex, FR DLCI, and Direction, each unique
        index combination translates to a service policy that 
        is attached to a FR DLCI, for particular traffic direction."
    INDEX { ifIndex, cbQosFrDLCI, cbQosPolicyDirection }
    ::= { cbQosFrameRelayPolicyTable 1 }

CbQosFrameRelayPolicyEntry ::= SEQUENCE {
    cbQosFRPolicyIndex Gauge
    }

cbQosFRPolicyIndex OBJECT-TYPE
    SYNTAX Gauge
    ACCESS read-only
    STATUS mandatory
    DESCRIPTION
        "An arbitrary (system-assigned) index for all
        Service Policies.
        
        This is identical to cbQosPolicyIndex."
    ::= { cbQosFrameRelayPolicyEntry 1 }

cbQosATMPVCPolicyTable OBJECT-TYPE
    SYNTAX SEQUENCE OF CbQosATMPVCPolicyEntry
    ACCESS not-accessible
    STATUS mandatory
    DESCRIPTION
        "This table describes the policies that are attached to a
        ATM PVC."
    ::= { cbQosATMPVCPolicy 1 }

cbQosATMPVCPolicyEntry OBJECT-TYPE
    SYNTAX CbQosATMPVCPolicyEntry
    ACCESS not-accessible
    STATUS mandatory
    DESCRIPTION
        "Using ifIndex, VPI, VCI, and Direction, each unique
        index combination translates to a service policy that 
        is attached to a ATM VC, for particular traffic direction."
    INDEX { ifIndex, cbQosAtmVPI, cbQosAtmVCI, cbQosPolicyDirection }
    ::= { cbQosATMPVCPolicyTable 1 }

CbQosATMPVCPolicyEntry ::= SEQUENCE {
    cbQosATMPolicyIndex Gauge
    }

cbQosATMPolicyIndex OBJECT-TYPE
    SYNTAX Gauge
    ACCESS read-only
    STATUS mandatory
    DESCRIPTION
        "An arbitrary (system-assigned) index for all
        Service Policies.
        
        This is identical to cbQosPolicyIndex."
    ::= { cbQosATMPVCPolicyEntry 1 }

cbQosObjectsTable OBJECT-TYPE
    SYNTAX SEQUENCE OF CbQosObjectsEntry
    ACCESS not-accessible
    STATUS mandatory
    DESCRIPTION
        "This table specifies QoS objects (classmap, policymap,
        match statements, and actions) hierarchy. This table also 
        provide relationship between each PolicyIndex/ObjectsIndex 
        pair and the ConfigIndex. ConfigIndex is essential for 
        querying any configuration tables."
    ::= { cbQosObjects 1 }

cbQosObjectsEntry OBJECT-TYPE
    SYNTAX CbQosObjectsEntry
    ACCESS not-accessible
    STATUS mandatory
    DESCRIPTION
        "A QoS object entry. Objects covered in this table are
        PolicyMap, ClassMap, Match Statements, and Actions.
        Each entry is indexed by system-generated cbQosPolicyIndex,
        and cbQosObjectsIndex, which represents a runtime instance 
        of a QoS object. In conjunction with the 
        cbQosParentObjectsIndex, a management station can 
        determine the hierarchical relationship of those QoS 
        objects. Given that classmaps and service policies can 
        be nested entites, each entry in this table represents a 
        unique instance of such object. Each runtime object 
        instance has a corresponding config object, which contains
        the configuration information of such QoS object. The
        config object is indexed by cbQosConfigIndex."
    INDEX { cbQosPolicyIndex, cbQosObjectsIndex }
    ::= { cbQosObjectsTable 1 }

CbQosObjectsEntry ::= SEQUENCE {
    cbQosObjectsIndex Gauge,
    cbQosConfigIndex Gauge,
    cbQosObjectsType QosObjectType,
    cbQosParentObjectsIndex Gauge
    }

cbQosObjectsIndex OBJECT-TYPE
    SYNTAX Gauge
    ACCESS not-accessible
    STATUS mandatory
    DESCRIPTION
        "An arbitrary (system-assigned) instance specific
        index for cbQosObjectsEntry."
    ::= { cbQosObjectsEntry 1 }

cbQosConfigIndex OBJECT-TYPE
    SYNTAX Gauge
    ACCESS read-only
    STATUS mandatory
    DESCRIPTION
        "An arbitrary (system-assigned) config (instance
        independent) index for each Object. Each objects having
        the same configuration share the same config index."
    ::= { cbQosObjectsEntry 2 }

cbQosObjectsType OBJECT-TYPE
    SYNTAX QosObjectType
--    Rsyntax INTEGER {
--        policymap(1),
--        classmap(2),
--        matchStatement(3),
--        queueing(4),
--        randomDetect(5),
--        trafficShaping(6),
--        police(7),
--        set(8),
--        compression(9),
--        ipslaMeasure(10)
--        }
    ACCESS read-only
    STATUS mandatory
    DESCRIPTION
        "The type of the QoS object."
    ::= { cbQosObjectsEntry 3 }

cbQosParentObjectsIndex OBJECT-TYPE
    SYNTAX Gauge
    ACCESS read-only
    STATUS mandatory
    DESCRIPTION
        "The parent instance index of a QoS object.
        
        For a ClassMap, the parent index would be the index of 
        the attached PolicyMap.
        
        For a Match Statement, the parent index would be the 
        index of the ClassMap that uses this Match Statement.
        
        For an action, the parent index would be the 
        index of the ClassMap that applies such Action.
        
        For a non-hierarchical PolicyMap, the parent would be 
        the logical interface to which the policy is attached,
        thus the parent index would be 0.
        
        For a hierarchical PolicyMap, the parent index would 
        be the index of the ClassMap to which the nested 
        policy is attached."
    ::= { cbQosObjectsEntry 4 }

cbQosPolicyMapCfgTable OBJECT-TYPE
    SYNTAX SEQUENCE OF CbQosPolicyMapCfgEntry
    ACCESS not-accessible
    STATUS mandatory
    DESCRIPTION
        "This table specifies Policymap configuration information"
    ::= { cbQosPolicyMapCfg 1 }

cbQosPolicyMapCfgEntry OBJECT-TYPE
    SYNTAX CbQosPolicyMapCfgEntry
    ACCESS not-accessible
    STATUS mandatory
    DESCRIPTION
        "Each entry in this table describes configuration information
        about a policymap. The information includes: Name, and it's
        description. This table contains configuration information 
        only, no statistics associated with it. Therefore, it is 
        indexed by the cbQosConfigIndex of each PolicyMap."
    INDEX { cbQosConfigIndex }
    ::= { cbQosPolicyMapCfgTable 1 }

CbQosPolicyMapCfgEntry ::= SEQUENCE {
    cbQosPolicyMapName DisplayString,
    cbQosPolicyMapDesc DisplayString
    }

cbQosPolicyMapName OBJECT-TYPE
    SYNTAX DisplayString(SIZE(0..255))
--    Rsyntax OCTET STRING(SIZE(0..255))
    ACCESS read-only
    STATUS mandatory
    DESCRIPTION
        "Name of the Policymap."
    ::= { cbQosPolicyMapCfgEntry 1 }

cbQosPolicyMapDesc OBJECT-TYPE
    SYNTAX DisplayString(SIZE(0..255))
--    Rsyntax OCTET STRING(SIZE(0..255))
    ACCESS read-only
    STATUS mandatory
    DESCRIPTION
        "Description of the PolicyMap."
    ::= { cbQosPolicyMapCfgEntry 2 }

cbQosCMCfgTable OBJECT-TYPE
    SYNTAX SEQUENCE OF CbQosCMCfgEntry
    ACCESS not-accessible
    STATUS mandatory
    DESCRIPTION
        "This table specifies ClassMap configuration information"
    ::= { cbQosClassMapCfg 1 }

cbQosCMCfgEntry OBJECT-TYPE
    SYNTAX CbQosCMCfgEntry
    ACCESS not-accessible
    STATUS mandatory
    DESCRIPTION
        "Each entry in this table describes configuration information
        about a classmap. The information includes: Name, and it's
        description and whether it is a Match-All or Match-Any
        class. This table contains configuration information only,
        no statistics associated with it. Therefore, it is indexed
        by the cbQosConfigIndex of each ClassMap."
    INDEX { cbQosConfigIndex }
    ::= { cbQosCMCfgTable 1 }

CbQosCMCfgEntry ::= SEQUENCE {
    cbQosCMName DisplayString,
    cbQosCMDesc DisplayString,
    cbQosCMInfo QosClassInfo
    }

cbQosCMName OBJECT-TYPE
    SYNTAX DisplayString(SIZE(0..255))
--    Rsyntax OCTET STRING(SIZE(0..255))
    ACCESS read-only
    STATUS mandatory
    DESCRIPTION
        "Name of the Classmap."
    ::= { cbQosCMCfgEntry 1 }

cbQosCMDesc OBJECT-TYPE
    SYNTAX DisplayString(SIZE(0..255))
--    Rsyntax OCTET STRING(SIZE(0..255))
    ACCESS read-only
    STATUS mandatory
    DESCRIPTION
        "Description of the Classmap."
    ::= { cbQosCMCfgEntry 2 }

cbQosCMInfo OBJECT-TYPE
    SYNTAX QosClassInfo
--    Rsyntax INTEGER {
--        none(1),
--        matchAll(2),
--        matchAny(3)
--        }
    ACCESS read-only
    STATUS mandatory
    DESCRIPTION
        "Match all vs Match any in a given class."
    ::= { cbQosCMCfgEntry 3 }

cbQosMatchStmtCfgTable OBJECT-TYPE
    SYNTAX SEQUENCE OF CbQosMatchStmtCfgEntry
    ACCESS not-accessible
    STATUS mandatory
    DESCRIPTION
        "This table specifies ClassMap configuration information"
    ::= { cbQosMatchStmtCfg 1 }

cbQosMatchStmtCfgEntry OBJECT-TYPE
    SYNTAX CbQosMatchStmtCfgEntry
    ACCESS not-accessible
    STATUS mandatory
    DESCRIPTION
        "Each entry in this table describes configuration information
        about a MatchStatement. The information includes: Name, 
        and whether it is a Match or Match-Not
        statement. This table contains configuration information 
        only, no statistics associated with it. Therefore, it is 
        indexed by the cbQosConfigIndex of each MatchStatement."
    INDEX { cbQosConfigIndex }
    ::= { cbQosMatchStmtCfgTable 1 }

CbQosMatchStmtCfgEntry ::= SEQUENCE {
    cbQosMatchStmtName DisplayString,
    cbQosMatchStmtInfo QosMatchInfo
    }

cbQosMatchStmtName OBJECT-TYPE
    SYNTAX DisplayString(SIZE(0..255))
--    Rsyntax OCTET STRING(SIZE(0..255))
    ACCESS read-only
    STATUS mandatory
    DESCRIPTION
        "Name of the Match Statement."
    ::= { cbQosMatchStmtCfgEntry 1 }

cbQosMatchStmtInfo OBJECT-TYPE
    SYNTAX QosMatchInfo
--    Rsyntax INTEGER {
--        none(1),
--        matchNot(2)
--        }
    ACCESS read-only
    STATUS mandatory
    DESCRIPTION
        "Match vs Match Not in a given class."
    ::= { cbQosMatchStmtCfgEntry 2 }

cbQosQueueingCfgTable OBJECT-TYPE
    SYNTAX SEQUENCE OF CbQosQueueingCfgEntry
    ACCESS not-accessible
    STATUS mandatory
    DESCRIPTION
        "This table specifies Queueing Action configuration
        information"
    ::= { cbQosQueueingCfg 1 }

cbQosQueueingCfgEntry OBJECT-TYPE
    SYNTAX CbQosQueueingCfgEntry
    ACCESS not-accessible
    STATUS mandatory
    DESCRIPTION
        "Each entry in this table describes configuration
        information about a queueing action. The information 
        includes: Bandwidth, Units, Flow Enabled, Priority Enabled, 
        and Q size.
        
        This table contains configuration information only,
        no statistics associated with it. Therefore, it is indexed
        by the cbQosConfigIndex of each Queueing Action."
    INDEX { cbQosConfigIndex }
    ::= { cbQosQueueingCfgTable 1 }

CbQosQueueingCfgEntry ::= SEQUENCE {
    cbQosQueueingCfgBandwidth INTEGER,
    cbQosQueueingCfgBandwidthUnits QueueingBandwidthUnits,
    cbQosQueueingCfgFlowEnabled TruthValue,
    cbQosQueueingCfgPriorityEnabled TruthValue,
    cbQosQueueingCfgAggregateQSize INTEGER,
    cbQosQueueingCfgIndividualQSize INTEGER,
    cbQosQueueingCfgDynamicQNumber INTEGER,
    cbQosQueueingCfgPrioBurstSize Gauge,
    cbQosQueueingCfgQLimitUnits CbQosQueueUnitType,
    cbQosQueueingCfgAggregateQLimit CbQosQueueDepth,
    cbQosQueueingCfgAggrQLimitTime Gauge
    }

cbQosQueueingCfgBandwidth OBJECT-TYPE
    SYNTAX INTEGER(0..2000000)
    ACCESS read-only
    STATUS mandatory
    DESCRIPTION
        "The configured bandwidth allocated to this traffic
        class.  In the case of a bandwidth policy, this value 
        represents a minimum b/w guarantee for the traffic 
        class.  In the case of a priority policy, this value 
        represents the maximum rate at which priority service 
        is guaranteed."
    ::= { cbQosQueueingCfgEntry 1 }

cbQosQueueingCfgBandwidthUnits OBJECT-TYPE
    SYNTAX QueueingBandwidthUnits
--    Rsyntax INTEGER {
--        kbps(1),
--        percentage(2),
--        percentageRemaining(3)
--        }
    ACCESS read-only
    STATUS mandatory
    DESCRIPTION
        "Units of the accompanying cbQosQueueingCfgbandwidth
        parameter."
    ::= { cbQosQueueingCfgEntry 2 }

cbQosQueueingCfgFlowEnabled OBJECT-TYPE
    SYNTAX TruthValue
--    Rsyntax INTEGER {
--        true(1),
--        false(2)
--        }
    ACCESS read-only
    STATUS mandatory
    DESCRIPTION
        "Boolean to indicate if flow-based fair-queue is
        enabled for this class."
    ::= { cbQosQueueingCfgEntry 3 }

cbQosQueueingCfgPriorityEnabled OBJECT-TYPE
    SYNTAX TruthValue
--    Rsyntax INTEGER {
--        true(1),
--        false(2)
--        }
    ACCESS read-only
    STATUS mandatory
    DESCRIPTION
        "Boolean to indicate if low latency queueing
        (priority) is enabled for this class."
    ::= { cbQosQueueingCfgEntry 4 }

cbQosQueueingCfgAggregateQSize OBJECT-TYPE
    SYNTAX INTEGER(0..65535)
--  Units
--    Packets
    ACCESS read-only
    STATUS deprecated
    DESCRIPTION
        "Maximum number of packets that can be held in all the
        individual queues associated with this class
        before packets are dropped. This object is deprecated
        by cbQosQueueingCfgAggregateQLimit."
    ::= { cbQosQueueingCfgEntry 5 }

cbQosQueueingCfgIndividualQSize OBJECT-TYPE
    SYNTAX INTEGER(1..32768)
--  Units
--    Packets
    ACCESS read-only
    STATUS mandatory
    DESCRIPTION
        "Maximum number of packets that can be held in an
        individual Flow-based fair-queue associated with this 
        class before it drops packets (once the AggregateQSize
        has been reached).
        
        This field only makes sense in the context of 
        Flow-based fair-queueing."
    ::= { cbQosQueueingCfgEntry 6 }

cbQosQueueingCfgDynamicQNumber OBJECT-TYPE
    SYNTAX INTEGER(1..32768)
    ACCESS read-only
    STATUS mandatory
    DESCRIPTION
        "Number of dynamic queues supported when
        flow-based fair-queue is in use."
    ::= { cbQosQueueingCfgEntry 7 }

cbQosQueueingCfgPrioBurstSize OBJECT-TYPE
    SYNTAX Gauge(32..64000000)
--  Units
--    Bytes
    ACCESS read-only
    STATUS mandatory
    DESCRIPTION
        "In the priority queue, this is the number of bytes
        allowed in a single burst. 
        This parameter only makes sense if Priority is enabled"
    ::= { cbQosQueueingCfgEntry 8 }

cbQosQueueingCfgQLimitUnits OBJECT-TYPE
    SYNTAX CbQosQueueUnitType
--    Rsyntax INTEGER {
--        packets(1),
--        cells(2),
--        bytes(3),
--        ms(4),
--        us(5)
--        }
    ACCESS read-only
    STATUS mandatory
    DESCRIPTION
        "Represents the unit type of
        cbQosQueueingCfgAggregateQLimit object."
    ::= { cbQosQueueingCfgEntry 9 }

cbQosQueueingCfgAggregateQLimit OBJECT-TYPE
    SYNTAX CbQosQueueDepth
--    Rsyntax Gauge
    ACCESS read-only
    STATUS mandatory
    DESCRIPTION
        "Maximum allowed queue size for all the individual
        queues associated with this class. When the queue size
        exceed this value, the packets will be dropped."
    ::= { cbQosQueueingCfgEntry 10 }

cbQosQueueingCfgAggrQLimitTime OBJECT-TYPE
    SYNTAX Gauge
--  Units
--    milli-seconds
    ACCESS read-only
    STATUS mandatory
    DESCRIPTION
        "Maximum allowed queue size in milli-seconds for all
        individual queues associated with this class.  It
        is internally converted to bytes by using the
        bandwidth that is available for the class."
    ::= { cbQosQueueingCfgEntry 11 }

cbQosREDCfgTable OBJECT-TYPE
    SYNTAX SEQUENCE OF CbQosREDCfgEntry
    ACCESS not-accessible
    STATUS mandatory
    DESCRIPTION
        "This table specifies WRED Action configuration
        information"
    ::= { cbQosREDCfg 1 }

cbQosREDCfgEntry OBJECT-TYPE
    SYNTAX CbQosREDCfgEntry
    ACCESS not-accessible
    STATUS mandatory
    DESCRIPTION
        "Each entry in this table describes configuration
        information about a WRED Action.  The table holds global 
        (per traffic class) configuration like: Expon Weight
        and Mean Q size.
        
        This table contains configuration information only,
        no statistics associated with it. Therefore, it is indexed
        by the cbQosConfigIndex of each WRED Action."
    INDEX { cbQosConfigIndex }
    ::= { cbQosREDCfgTable 1 }

CbQosREDCfgEntry ::= SEQUENCE {
    cbQosREDCfgExponWeight INTEGER,
    cbQosREDCfgMeanQsize INTEGER,
    cbQosREDCfgDscpPrec REDMechanism,
    cbQosREDCfgECNEnabled TruthValue
    }

cbQosREDCfgExponWeight OBJECT-TYPE
    SYNTAX INTEGER(1..16)
    ACCESS read-only
    STATUS mandatory
    DESCRIPTION
        "The decay factor for the queue average calculation.
        The decay factor is equal to raising 2 to the power 
        of N, where N could be up to 16. 
        The smaller the number, the faster it decays."
    ::= { cbQosREDCfgEntry 1 }

cbQosREDCfgMeanQsize OBJECT-TYPE
    SYNTAX INTEGER(0..65535)
--  Units
--    Packets
    ACCESS read-only
    STATUS deprecated
    DESCRIPTION
        "The average queue size, computed and used by the WRED
        algorithm. This is deprecated by cbQosREDMeanQsize."
    ::= { cbQosREDCfgEntry 2 }

cbQosREDCfgDscpPrec OBJECT-TYPE
    SYNTAX REDMechanism
--    Rsyntax INTEGER {
--        precedence(1),
--        dscp(2),
--        discardClass(3),
--        l2Cos(4),
--        atmClp(5),
--        mplsExp(6),
--        redDefault(7),
--        redUserDefault(8)
--        }
    ACCESS read-only
    STATUS mandatory
    DESCRIPTION
        "The Classification mechanism used by RED"
    ::= { cbQosREDCfgEntry 3 }

cbQosREDCfgECNEnabled OBJECT-TYPE
    SYNTAX TruthValue
--    Rsyntax INTEGER {
--        true(1),
--        false(2)
--        }
    ACCESS read-only
    STATUS mandatory
    DESCRIPTION
        "Boolean to indicate if explicit congestion notification
        enabled for this class."
    ::= { cbQosREDCfgEntry 4 }

cbQosREDClassCfgTable OBJECT-TYPE
    SYNTAX SEQUENCE OF CbQosREDClassCfgEntry
    ACCESS not-accessible
    STATUS mandatory
    DESCRIPTION
        "This table specifies WRED Action configuration
        information on a per IP precedence basis."
    ::= { cbQosREDClassCfg 1 }

cbQosREDClassCfgEntry OBJECT-TYPE
    SYNTAX CbQosREDClassCfgEntry
    ACCESS not-accessible
    STATUS mandatory
    DESCRIPTION
        "Each entry in this table describes configuration information
        about a WRED Action.  The table holds the per IP precedence
        based WRED configuration parameters. 
        
        This table contains configuration information only,
        no statistics associated with it. Therefore, it is indexed
        by the cbQosConfigIndex and cbQosREDValue 
        of each WRED Action."
    INDEX { cbQosConfigIndex, cbQosREDValue }
    ::= { cbQosREDClassCfgTable 1 }

CbQosREDClassCfgEntry ::= SEQUENCE {
    cbQosREDValue INTEGER,
    cbQosREDCfgMinThreshold INTEGER,
    cbQosREDCfgMaxThreshold INTEGER,
    cbQosREDCfgPktDropProb INTEGER,
    cbQosREDClassCfgThresholdUnit CbQosQueueUnitType,
    cbQosREDClassCfgMinThreshold CbQosQueueDepth,
    cbQosREDClassCfgMaxThreshold CbQosQueueDepth,
    cbQosREDClassCfgMinThresholdTime Gauge,
    cbQosREDClassCfgMaxThresholdTime Gauge
    }

cbQosREDValue OBJECT-TYPE
    SYNTAX INTEGER(0..63)
    ACCESS not-accessible
    STATUS mandatory
    DESCRIPTION
        "The IP precedence or IP DSCP of this entry."
    ::= { cbQosREDClassCfgEntry 1 }

cbQosREDCfgMinThreshold OBJECT-TYPE
    SYNTAX INTEGER(1..32768)
--  Units
--    Packets
    ACCESS read-only
    STATUS deprecated
    DESCRIPTION
        "Minimum threshold in number of packets. When the
        average queue length reaches this number, WRED begins 
        to drop packets with the specified IP precedence.
        This is deprecated by cbQosREDClassCfgMinThreshold."
    ::= { cbQosREDClassCfgEntry 2 }

cbQosREDCfgMaxThreshold OBJECT-TYPE
    SYNTAX INTEGER(1..32768)
--  Units
--    Packets
    ACCESS read-only
    STATUS deprecated
    DESCRIPTION
        "Maximum threshold in number of packets. When the
        average queue length exceeds this number, WRED drops 
        all packets with the specified IP precedence.
        This is deprecated by cbQosREDClassCfgMaxThreshold."
    ::= { cbQosREDClassCfgEntry 3 }

cbQosREDCfgPktDropProb OBJECT-TYPE
    SYNTAX INTEGER(1..65536)
    ACCESS read-only
    STATUS mandatory
    DESCRIPTION
        "Denominator for the fraction of packets dropped when
        the average queue depth is MaxDepthThreshold. For 
        example, if the denominator is 10, one out of every 10
        packets is dropped when the average queue is at the 
        MaxDepthThreshold."
    ::= { cbQosREDClassCfgEntry 4 }

cbQosREDClassCfgThresholdUnit OBJECT-TYPE
    SYNTAX CbQosQueueUnitType
--    Rsyntax INTEGER {
--        packets(1),
--        cells(2),
--        bytes(3),
--        ms(4),
--        us(5)
--        }
    ACCESS read-only
    STATUS mandatory
    DESCRIPTION
        "Represents the unit type to measure the RED thresholds.
        The objects covered are cbQosREDClassCfgMinThreshold
        and cbQosREDClassCfgMaxThreshold."
    ::= { cbQosREDClassCfgEntry 5 }

cbQosREDClassCfgMinThreshold OBJECT-TYPE
    SYNTAX CbQosQueueDepth
--    Rsyntax Gauge
    ACCESS read-only
    STATUS mandatory
    DESCRIPTION
        "The minimum WRED threshold value. When the average
        queue length reaches this number, WRED begins to 
        drop packets according to REDMechanism specificed
        in cbQosREDCfgDscpPrec."
    ::= { cbQosREDClassCfgEntry 6 }

cbQosREDClassCfgMaxThreshold OBJECT-TYPE
    SYNTAX CbQosQueueDepth
--    Rsyntax Gauge
    ACCESS read-only
    STATUS mandatory
    DESCRIPTION
        "The maximum WRED threshold value. When the average
        queue length exceeds this number, WRED drops all 
        packets according to REDMechanism specificed
        in cbQosREDCfgDscpPrec."
    ::= { cbQosREDClassCfgEntry 7 }

cbQosREDClassCfgMinThresholdTime OBJECT-TYPE
    SYNTAX Gauge
--  Units
--    milli-seconds
    ACCESS read-only
    STATUS mandatory
    DESCRIPTION
        "The minimum WRED threshold value specified in
        milli-seconds.  The milli-second value is internally
        converted to bytes by using the bandwidth that
        is available for the class."
    ::= { cbQosREDClassCfgEntry 8 }

cbQosREDClassCfgMaxThresholdTime OBJECT-TYPE
    SYNTAX Gauge
--  Units
--    milli-seconds
    ACCESS read-only
    STATUS mandatory
    DESCRIPTION
        "The maximum WRED threshold value specified in
        milli-seconds.  The milli-second value is internally
        converted to bytes by using the bandwidth that
        is available for the class."
    ::= { cbQosREDClassCfgEntry 9 }

cbQosPoliceCfgTable OBJECT-TYPE
    SYNTAX SEQUENCE OF CbQosPoliceCfgEntry
    ACCESS not-accessible
    STATUS mandatory
    DESCRIPTION
        "This table specifies Police Action configuration
        information."
    ::= { cbQosPoliceCfg 1 }

cbQosPoliceCfgEntry OBJECT-TYPE
    SYNTAX CbQosPoliceCfgEntry
    ACCESS not-accessible
    STATUS mandatory
    DESCRIPTION
        "Each entry in this table describes configuration information
        about a Police Action.  The table holds Policy 
        configuration parameters, such as rate, burst size, and 
        actions based on traffic rates.
        
        This table contains configuration information only,
        no statistics associated with it. Therefore, it is indexed
        by the cbQosConfigIndex."
    INDEX { cbQosConfigIndex }
    ::= { cbQosPoliceCfgTable 1 }

CbQosPoliceCfgEntry ::= SEQUENCE {
    cbQosPoliceCfgRate Gauge,
    cbQosPoliceCfgBurstSize Gauge,
    cbQosPoliceCfgExtBurstSize Gauge,
    cbQosPoliceCfgConformAction PoliceAction,
    cbQosPoliceCfgConformSetValue Gauge,
    cbQosPoliceCfgExceedAction PoliceAction,
    cbQosPoliceCfgExceedSetValue Gauge,
    cbQosPoliceCfgViolateAction PoliceAction,
    cbQosPoliceCfgViolateSetValue Gauge,
    cbQosPoliceCfgPir Gauge,
    cbQosPoliceCfgRate64 Unsigned64,
    cbQosPoliceCfgRateType CbQosRateType,
    cbQosPoliceCfgPercentRateValue Gauge,
    cbQosPoliceCfgPercentPirValue Gauge,
    cbQosPoliceCfgCellRate Gauge,
    cbQosPoliceCfgCellPir Gauge,
    cbQosPoliceCfgBurstCell Gauge,
    cbQosPoliceCfgExtBurstCell Gauge,
    cbQosPoliceCfgBurstTime Gauge,
    cbQosPoliceCfgExtBurstTime Gauge,
    cbQosPoliceCfgCdvt Gauge,
    cbQosPoliceCfgConformColor DisplayString,
    cbQosPoliceCfgExceedColor DisplayString
    }

cbQosPoliceCfgRate OBJECT-TYPE
    SYNTAX Gauge(8000..2000000000)
--  Units
--    bits/second
    ACCESS read-only
    STATUS mandatory
    DESCRIPTION
        "The committed policing rate. This is the sustained
        rate permitted by policing.
        
        If a committed policing rate greater than 2000000000
        is configurable on the system, then the configured
        rate is available in cbQosPoliceCfgRate64."
    ::= { cbQosPoliceCfgEntry 1 }

cbQosPoliceCfgBurstSize OBJECT-TYPE
    SYNTAX Gauge(1000..512000000)
--  Units
--    Octets
    ACCESS read-only
    STATUS mandatory
    DESCRIPTION
        "The amount of traffic, in bytes, in excess of the
        committed policing rate that will be permitted by 
        the policing feature."
    ::= { cbQosPoliceCfgEntry 2 }

cbQosPoliceCfgExtBurstSize OBJECT-TYPE
    SYNTAX Gauge(1000..512000000)
--  Units
--    Octets
    ACCESS read-only
    STATUS mandatory
    DESCRIPTION
        "The amount of traffic, in bytes, in excess of the
        burst limit, which may be conditionally permitted 
        by the policing feature. The probability that the 
        traffic is not permitted increases as the received 
        burst size increases."
    ::= { cbQosPoliceCfgEntry 3 }

cbQosPoliceCfgConformAction OBJECT-TYPE
    SYNTAX PoliceAction
--    Rsyntax INTEGER {
--        transmit(1),
--        setIpDSCP(2),
--        setIpPrecedence(3),
--        setQosGroup(4),
--        drop(5),
--        setMplsExp(6),
--        setAtmClp(7),
--        setFrDe(8),
--        setL2Cos(9),
--        setDiscardClass(10),
--        setMplsExpTopMost(11),
--        setIpDscpTunnel(12),
--        setIpPrecedenceTunnel(13),
--        setL2CosInner(14)
--        }
    ACCESS read-only
    STATUS deprecated
    DESCRIPTION
        "Action to be taken when the traffic is within the
        configured rate, that is, the traffic rate is 
        conforming.
        This object is deprecated and defined in 
        cbQosPoliceActionCfgTable."
    ::= { cbQosPoliceCfgEntry 4 }

cbQosPoliceCfgConformSetValue OBJECT-TYPE
    SYNTAX Gauge(1..99)
    ACCESS read-only
    STATUS deprecated
    DESCRIPTION
        "New packet attribute values for each packets that
        conforms to the configured Police rate.
        This object is deprecated and defined in 
        cbQosPoliceActionCfgTable."
    ::= { cbQosPoliceCfgEntry 5 }

cbQosPoliceCfgExceedAction OBJECT-TYPE
    SYNTAX PoliceAction
--    Rsyntax INTEGER {
--        transmit(1),
--        setIpDSCP(2),
--        setIpPrecedence(3),
--        setQosGroup(4),
--        drop(5),
--        setMplsExp(6),
--        setAtmClp(7),
--        setFrDe(8),
--        setL2Cos(9),
--        setDiscardClass(10),
--        setMplsExpTopMost(11),
--        setIpDscpTunnel(12),
--        setIpPrecedenceTunnel(13),
--        setL2CosInner(14)
--        }
    ACCESS read-only
    STATUS deprecated
    DESCRIPTION
        "Action to be taken when the traffic exceeds the
        configured rate, that is, the traffic is 
        non-conforming.
        This object is deprecated and defined in 
        cbQosPoliceActionCfgTable."
    ::= { cbQosPoliceCfgEntry 6 }

cbQosPoliceCfgExceedSetValue OBJECT-TYPE
    SYNTAX Gauge(1..99)
    ACCESS read-only
    STATUS deprecated
    DESCRIPTION
        "New packet attribute values for each packets that
        conforms to the configured Police rate.
        This object is deprecated and defined in 
        cbQosPoliceActionCfgTable."
    ::= { cbQosPoliceCfgEntry 7 }

cbQosPoliceCfgViolateAction OBJECT-TYPE
    SYNTAX PoliceAction
--    Rsyntax INTEGER {
--        transmit(1),
--        setIpDSCP(2),
--        setIpPrecedence(3),
--        setQosGroup(4),
--        drop(5),
--        setMplsExp(6),
--        setAtmClp(7),
--        setFrDe(8),
--        setL2Cos(9),
--        setDiscardClass(10),
--        setMplsExpTopMost(11),
--        setIpDscpTunnel(12),
--        setIpPrecedenceTunnel(13),
--        setL2CosInner(14)
--        }
    ACCESS read-only
    STATUS deprecated
    DESCRIPTION
        "Action to be taken when the traffic exceeds the
        conform and exceed token buckets.
        This object is deprecated and defined in 
        cbQosPoliceActionCfgTable."
    ::= { cbQosPoliceCfgEntry 8 }

cbQosPoliceCfgViolateSetValue OBJECT-TYPE
    SYNTAX Gauge(1..99)
    ACCESS read-only
    STATUS deprecated
    DESCRIPTION
        "New packet attribute values for each packets that
        conforms to the Police violate action. The packet
        attibute values depend on the action that is taken
        for the particular packet. For example, if the 
        action was to set the dscp value, this entry describes
        the value it is set to. 
        This object is deprecated and defined in 
        cbQosPoliceActionCfgTable."
    ::= { cbQosPoliceCfgEntry 9 }

cbQosPoliceCfgPir OBJECT-TYPE
    SYNTAX Gauge(8000..2000000000)
--  Units
--    bits/second
    ACCESS read-only
    STATUS mandatory
    DESCRIPTION
        "The committed policing rate. This is the peak
        rate permitted by two rate policing."
    ::= { cbQosPoliceCfgEntry 10 }

cbQosPoliceCfgRate64 OBJECT-TYPE
    SYNTAX --?? syntax is not convertable to SMIv1
           Unsigned64
--    Rsyntax Counter
--  Units
--    bits/second
    ACCESS read-only
    STATUS mandatory
    DESCRIPTION
        "The committed policing rate. This is the sustained
        rate permitted by policing."
    ::= { cbQosPoliceCfgEntry 11 }

cbQosPoliceCfgRateType OBJECT-TYPE
    SYNTAX CbQosRateType
--    Rsyntax INTEGER {
--        bps(1),
--        percentage(2),
--        cps(3)
--        }
    ACCESS read-only
    STATUS mandatory
    DESCRIPTION
        "The rate type that configured for CIR & PIR.
        1 means rates are configured in bps.
        2 means rates are configured in percentage.
        3 means rates are configured in cps."
    ::= { cbQosPoliceCfgEntry 12 }

cbQosPoliceCfgPercentRateValue OBJECT-TYPE
    SYNTAX Gauge(0..100)
--  Units
--    % of Interface Bandwidth
    ACCESS read-only
    STATUS mandatory
    DESCRIPTION
        "The committed policing rate in percentage.  Its value
        is valid only when cbQosPoliceCfgRateType equals to 2."
    ::= { cbQosPoliceCfgEntry 13 }

cbQosPoliceCfgPercentPirValue OBJECT-TYPE
    SYNTAX Gauge(0..100)
--  Units
--    % of Interface Bandwidth
    ACCESS read-only
    STATUS mandatory
    DESCRIPTION
        "The peak policing rate in percentage. Its value is
        valid only when cbQosPoliceCfgRateType equals to 2."
    ::= { cbQosPoliceCfgEntry 14 }

cbQosPoliceCfgCellRate OBJECT-TYPE
    SYNTAX Gauge
--  Units
--    cells/second
    ACCESS read-only
    STATUS mandatory
    DESCRIPTION
        "The committed policing rate in cells/second.  Its value
        is valid only when cbQosPoliceCfgRateType equals to 3."
    ::= { cbQosPoliceCfgEntry 15 }

cbQosPoliceCfgCellPir OBJECT-TYPE
    SYNTAX Gauge
--  Units
--    cells/second
    ACCESS read-only
    STATUS mandatory
    DESCRIPTION
        "The peak policing rate in cells/second.  Its value is
        valid only when cbQosPoliceCfgRateType equals to 3."
    ::= { cbQosPoliceCfgEntry 16 }

cbQosPoliceCfgBurstCell OBJECT-TYPE
    SYNTAX Gauge(0..9660377)
--  Units
--    Cells
    ACCESS read-only
    STATUS mandatory
    DESCRIPTION
        "The amount of traffic, in cells, in excess of the
        committed policing rate that will be permitted by
        the policing feature."
    ::= { cbQosPoliceCfgEntry 17 }

cbQosPoliceCfgExtBurstCell OBJECT-TYPE
    SYNTAX Gauge(0..9660377)
--  Units
--    Cells
    ACCESS read-only
    STATUS mandatory
    DESCRIPTION
        "The amount of traffic, in cells, in excess of the
        burst limit, which may be conditionally permitted
        by the policing feature. The probability that the
        traffic is not permitted increases as the received
        burst size increases."
    ::= { cbQosPoliceCfgEntry 18 }

cbQosPoliceCfgBurstTime OBJECT-TYPE
    SYNTAX Gauge(0..2000)
--  Units
--    milli-seconds
    ACCESS read-only
    STATUS mandatory
    DESCRIPTION
        "The amount of traffic time, in ms, in excess of the
        committed policing rate that will be permitted by
        the policing feature.  The milli-second value is
        internally converted to bytes by using the bandwidth
        that is available for the class."
    ::= { cbQosPoliceCfgEntry 19 }

cbQosPoliceCfgExtBurstTime OBJECT-TYPE
    SYNTAX Gauge(0..2000)
--  Units
--    milli-seconds
    ACCESS read-only
    STATUS mandatory
    DESCRIPTION
        "The amount of traffic time, in ms, in excess of the
        burst limit, which may be conditionally permitted
        by the policing feature. The probability that the
        traffic is not permitted increases as the received
        burst size increases.  The milli-second value is 
        internally converted to bytes by using the bandwidth
        that is available for the class."
    ::= { cbQosPoliceCfgEntry 20 }

cbQosPoliceCfgCdvt OBJECT-TYPE
    SYNTAX Gauge(0..1000000)
--  Units
--    micro-second
    ACCESS read-only
    STATUS mandatory
    DESCRIPTION
        "The ATM Cell Delay Variation Tolerance value."
    ::= { cbQosPoliceCfgEntry 21 }

cbQosPoliceCfgConformColor OBJECT-TYPE
    SYNTAX DisplayString
--    Rsyntax OCTET STRING(SIZE(0..255))
    ACCESS read-only
    STATUS mandatory
    DESCRIPTION
        "The Classmap name used in AF color-aware mode to
        specify the conform-color for the incoming packets
        which was marked by the previous node.
        
        At least conform-color must be specified.  If only 
        conform-color is specified, all other packets are
        assumed to be marked exceed.
        
        See RFC 2697, A Single Rate Three Color Marker.
        See RFC 2698, A Two Rate Three Color Marker."
    ::= { cbQosPoliceCfgEntry 22 }

cbQosPoliceCfgExceedColor OBJECT-TYPE
    SYNTAX DisplayString
--    Rsyntax OCTET STRING(SIZE(0..255))
    ACCESS read-only
    STATUS mandatory
    DESCRIPTION
        "The Classmap name used in AF color-aware mode to
        specify the exceed-color for the incoming packets
        which was marked by the previous node.
        
        If both conform-color and exceed-color are specified,
        all other packets are assumed to be marked violate.
        Violate-color configuration is not needed."
    ::= { cbQosPoliceCfgEntry 23 }

cbQosPoliceActionCfgTable OBJECT-TYPE
    SYNTAX SEQUENCE OF CbQosPoliceActionCfgEntry
    ACCESS not-accessible
    STATUS mandatory
    DESCRIPTION
        "This table specifies Police Action configuration
        information."
    ::= { cbQosPoliceActionCfg 1 }

cbQosPoliceActionCfgEntry OBJECT-TYPE
    SYNTAX CbQosPoliceActionCfgEntry
    ACCESS not-accessible
    STATUS mandatory
    DESCRIPTION
        "Each entry in this table describes configuration information
        about Actions for one Police.  The table holds Police 
        action specific configuration parameters.
        This table is a sub-table for cbQosPoliceCfgTable. There is
        a 1-to-1 association between one entry here and one entry in 
        cbQosPoliceCfgTable. 
        This table contains configuration information only,
        no statistics associated with it. 
        This table has two indices. The first is cbQosConfigIndex 
        which is drived directly from cbQosPoliceCfgTable to keep the
        1-to-1 mapping nature between two tables. 
        The second is cbQosPoliceActionCfgIndex used to reference 
        the actual actions configured. The maximum number of actions
        supported is determined by the system, which is 5 currently."
    INDEX { cbQosConfigIndex, cbQosPoliceActionCfgIndex }
    ::= { cbQosPoliceActionCfgTable 1 }

CbQosPoliceActionCfgEntry ::= SEQUENCE {
    cbQosPoliceActionCfgIndex Gauge,
    cbQosPoliceActionCfgConform PoliceAction,
    cbQosPoliceActionCfgConformSetValue Gauge,
    cbQosPoliceActionCfgExceed PoliceAction,
    cbQosPoliceActionCfgExceedSetValue Gauge,
    cbQosPoliceActionCfgViolate PoliceAction,
    cbQosPoliceActionCfgViolateSetValue Gauge
    }

cbQosPoliceActionCfgIndex OBJECT-TYPE
    SYNTAX Gauge
    ACCESS not-accessible
    STATUS mandatory
    DESCRIPTION
        "An arbitrary (system-assigned) index for police
        actions that are defined by a police configuration."
    ::= { cbQosPoliceActionCfgEntry 1 }

cbQosPoliceActionCfgConform OBJECT-TYPE
    SYNTAX PoliceAction
--    Rsyntax INTEGER {
--        transmit(1),
--        setIpDSCP(2),
--        setIpPrecedence(3),
--        setQosGroup(4),
--        drop(5),
--        setMplsExp(6),
--        setAtmClp(7),
--        setFrDe(8),
--        setL2Cos(9),
--        setDiscardClass(10),
--        setMplsExpTopMost(11),
--        setIpDscpTunnel(12),
--        setIpPrecedenceTunnel(13),
--        setL2CosInner(14)
--        }
    ACCESS read-only
    STATUS mandatory
    DESCRIPTION
        "Action to be taken when the traffic exceeds the
        conform and exceed token buckets."
    ::= { cbQosPoliceActionCfgEntry 2 }

cbQosPoliceActionCfgConformSetValue OBJECT-TYPE
    SYNTAX Gauge(0..99)
    ACCESS read-only
    STATUS mandatory
    DESCRIPTION
        "New packet attribute values for each packet set by
        police action defined in cbQosPoliceActionCfgConform.
        This object will be set to zero if the corresponding
        police action does not require a set value, such as 
        no action, drop action or transmit action."
    ::= { cbQosPoliceActionCfgEntry 3 }

cbQosPoliceActionCfgExceed OBJECT-TYPE
    SYNTAX PoliceAction
--    Rsyntax INTEGER {
--        transmit(1),
--        setIpDSCP(2),
--        setIpPrecedence(3),
--        setQosGroup(4),
--        drop(5),
--        setMplsExp(6),
--        setAtmClp(7),
--        setFrDe(8),
--        setL2Cos(9),
--        setDiscardClass(10),
--        setMplsExpTopMost(11),
--        setIpDscpTunnel(12),
--        setIpPrecedenceTunnel(13),
--        setL2CosInner(14)
--        }
    ACCESS read-only
    STATUS mandatory
    DESCRIPTION
        "Action to be taken when the traffic exceeds the
        conform and exceed token buckets."
    ::= { cbQosPoliceActionCfgEntry 4 }

cbQosPoliceActionCfgExceedSetValue OBJECT-TYPE
    SYNTAX Gauge(0..99)
    ACCESS read-only
    STATUS mandatory
    DESCRIPTION
        "New packet attribute values for each packet set by
        police action defined in cbQosPoliceActionCfgExceed.
        This object will be set to zero if the corresponding
        police action does not require a set value, such as 
        no action, drop action or transmit action."
    ::= { cbQosPoliceActionCfgEntry 5 }

cbQosPoliceActionCfgViolate OBJECT-TYPE
    SYNTAX PoliceAction
--    Rsyntax INTEGER {
--        transmit(1),
--        setIpDSCP(2),
--        setIpPrecedence(3),
--        setQosGroup(4),
--        drop(5),
--        setMplsExp(6),
--        setAtmClp(7),
--        setFrDe(8),
--        setL2Cos(9),
--        setDiscardClass(10),
--        setMplsExpTopMost(11),
--        setIpDscpTunnel(12),
--        setIpPrecedenceTunnel(13),
--        setL2CosInner(14)
--        }
    ACCESS read-only
    STATUS mandatory
    DESCRIPTION
        "Action to be taken when the traffic exceeds the
        conform and exceed token buckets."
    ::= { cbQosPoliceActionCfgEntry 6 }

cbQosPoliceActionCfgViolateSetValue OBJECT-TYPE
    SYNTAX Gauge(0..99)
    ACCESS read-only
    STATUS mandatory
    DESCRIPTION
        "New packet attribute values for each packet set by
        police action defined in cbQosPoliceActionCfgViolate.
        This object will be set to zero if the corresponding
        police action does not require a set value, such as 
        no action, drop action or transmit action."
    ::= { cbQosPoliceActionCfgEntry 7 }

cbQosTSCfgTable OBJECT-TYPE
    SYNTAX SEQUENCE OF CbQosTSCfgEntry
    ACCESS not-accessible
    STATUS mandatory
    DESCRIPTION
        "This table specifies traffic-shaping Action configuration
        information."
    ::= { cbQosTSCfg 1 }

cbQosTSCfgEntry OBJECT-TYPE
    SYNTAX CbQosTSCfgEntry
    ACCESS not-accessible
    STATUS mandatory
    DESCRIPTION
        "Each entry in this table describes configuration information
        about a traffic-shaping Action.  The table holds Traffic
        Shaping configuration parameters, such as rate, burst size, 
        and Shaping types.
        
        This table contains configuration information only,
        no statistics associated with it. Therefore, it is indexed
        by the cbQosConfigIndex."
    INDEX { cbQosConfigIndex }
    ::= { cbQosTSCfgTable 1 }

CbQosTSCfgEntry ::= SEQUENCE {
    cbQosTSCfgRate INTEGER,
    cbQosTSCfgBurstSize INTEGER,
    cbQosTSCfgExtBurstSize INTEGER,
    cbQosTSCfgAdaptiveEnabled TruthValue,
    cbQosTSCfgAdaptiveRate INTEGER,
    cbQosTSCfgLimitType TrafficShapingLimit,
    cbQosTSCfgRateType CbQosRateType,
    cbQosTSCfgPercentRateValue Gauge,
    cbQosTSCfgBurstTime Gauge,
    cbQosTSCfgExtBurstTime Gauge,
    cbQosTSCfgRate64 Unsigned64
    }

cbQosTSCfgRate OBJECT-TYPE
    SYNTAX INTEGER(8000..154400000)
--  Units
--    bits/second
    ACCESS read-only
    STATUS mandatory
    DESCRIPTION
        "The committed traffic-shaping rate.  This is the
        sustained rate permitted by the traffic-shaping."
    ::= { cbQosTSCfgEntry 1 }

cbQosTSCfgBurstSize OBJECT-TYPE
    SYNTAX INTEGER(256..154400000)
--  Units
--    bits
    ACCESS read-only
    STATUS mandatory
    DESCRIPTION
        "The amount of traffic, in bits, in excess of the
        committed traffic-shaping rate that will be
        instantaneously permitted by this feature."
    ::= { cbQosTSCfgEntry 2 }

cbQosTSCfgExtBurstSize OBJECT-TYPE
    SYNTAX INTEGER(0..154400000)
--  Units
--    bits
    ACCESS read-only
    STATUS mandatory
    DESCRIPTION
        "The amount of traffic, in bits, in excess of the
        burst limit, which may be conditionally permitted
        by traffic-shaping feature."
    ::= { cbQosTSCfgEntry 3 }

cbQosTSCfgAdaptiveEnabled OBJECT-TYPE
    SYNTAX TruthValue
--    Rsyntax INTEGER {
--        true(1),
--        false(2)
--        }
    ACCESS read-only
    STATUS mandatory
    DESCRIPTION
        "This object indicates is adaptive traffic-shaping
        has been enabled."
    ::= { cbQosTSCfgEntry 4 }

cbQosTSCfgAdaptiveRate OBJECT-TYPE
    SYNTAX INTEGER(8000..154400000)
--  Units
--    bits/second
    ACCESS read-only
    STATUS mandatory
    DESCRIPTION
        "This object represents the current adaptive traffic
        shaping rate."
    ::= { cbQosTSCfgEntry 5 }

cbQosTSCfgLimitType OBJECT-TYPE
    SYNTAX TrafficShapingLimit
--    Rsyntax INTEGER {
--        average(1),
--        peak(2)
--        }
    ACCESS read-only
    STATUS mandatory
    DESCRIPTION
        "This object indicates if traffic-shaping is limiting
        traffic based on the peak rate or the average rate."
    ::= { cbQosTSCfgEntry 6 }

cbQosTSCfgRateType OBJECT-TYPE
    SYNTAX CbQosRateType
--    Rsyntax INTEGER {
--        bps(1),
--        percentage(2),
--        cps(3)
--        }
    ACCESS read-only
    STATUS mandatory
    DESCRIPTION
        "The rate type that configured for traffic-shaping.
        1 means rate is configured in bps.
        2 means rate is configured in percentage."
    ::= { cbQosTSCfgEntry 7 }

cbQosTSCfgPercentRateValue OBJECT-TYPE
    SYNTAX Gauge(0..100)
--  Units
--    % of Interface Bandwidth
    ACCESS read-only
    STATUS mandatory
    DESCRIPTION
        "The committed traffic-shaping rate in percentage.
        Its value is valid only when cbQosTSCfgRateType 
        equals to 2."
    ::= { cbQosTSCfgEntry 8 }

cbQosTSCfgBurstTime OBJECT-TYPE
    SYNTAX Gauge(0..2000)
--  Units
--    milli-seconds
    ACCESS read-only
    STATUS mandatory
    DESCRIPTION
        "The amount of traffic, in ms, in excess of the
        committed traffic-shaping rate that will be
        instantaneously permitted by this feature.
        The milli-second value is internally converted to
        bits by using the bandwidth that is available for
        the class."
    ::= { cbQosTSCfgEntry 9 }

cbQosTSCfgExtBurstTime OBJECT-TYPE
    SYNTAX Gauge(0..2000)
--  Units
--    milli-seconds
    ACCESS read-only
    STATUS mandatory
    DESCRIPTION
        "The amount of traffic, in ms, in excess of the
        burst limit, which may be conditionnally permitted
        by traffic-shaping feature.
        The milli-second value is internally converted to
        bits by using the bandwidth that is available for
        the class."
    ::= { cbQosTSCfgEntry 10 }

cbQosTSCfgRate64 OBJECT-TYPE
    SYNTAX --?? syntax is not convertable to SMIv1
           Unsigned64
--    Rsyntax Counter64
--  Units
--    bits/second
    ACCESS read-only
    STATUS mandatory
    DESCRIPTION
        "The committed shape rate. This is the sustained
        rate permitted by shaping. This object represents 
        the 64 bit value of object cbQosTSCfgRate"
    ::= { cbQosTSCfgEntry 11 }

cbQosSetCfgTable OBJECT-TYPE
    SYNTAX SEQUENCE OF CbQosSetCfgEntry
    ACCESS not-accessible
    STATUS mandatory
    DESCRIPTION
        "This table specifies Packet Marking Action configuration
        information."
    ::= { cbQosSetCfg 1 }

cbQosSetCfgEntry OBJECT-TYPE
    SYNTAX CbQosSetCfgEntry
    ACCESS not-accessible
    STATUS mandatory
    DESCRIPTION
        "Each entry in this table describes configuration information
        about a Packet Marking Action.  The table holds Packet
        Marking configuration parameters, such as type of packet
        marking and values being set to.
        
        This table contains configuration information only,
        no statistics associated with it. Therefore, it is indexed
        by the cbQosConfigIndex."
    INDEX { cbQosConfigIndex }
    ::= { cbQosSetCfgTable 1 }

CbQosSetCfgEntry ::= SEQUENCE {
    cbQosSetCfgFeature SetFeatureType,
    cbQosSetCfgIpDSCPValue INTEGER,
    cbQosSetCfgIpPrecedenceValue INTEGER,
    cbQosSetCfgQosGroupValue INTEGER,
    cbQosSetCfgL2CosValue INTEGER,
    cbQosSetCfgMplsExpValue Gauge,
    cbQosSetCfgDiscardClassValue Gauge,
    cbQosSetCfgMplsExpTopMostValue Gauge,
    cbQosSetCfgSrpPriority Gauge,
    cbQosSetCfgFrFecnBecn Gauge
    }

cbQosSetCfgFeature OBJECT-TYPE
    SYNTAX SetFeatureType
--    Rsyntax OCTET STRING(SIZE(1..2))
--         BITS are:
--           ipDscp(0)
--           ipPrecedence(1)
--           qosGroupNumber(2)
--           frDeBit(3)
--           atmClpBit(4)
--           l2Cos(5)
--           mplsExp(6)
--           discardClass(7)
--           mplsExpTopMost(8)
--           srpPriority(9)
--           frFecnBecn(10)
--           ipDscpTunnel(11)
--           ipPrecedenceTunnel(12)
    ACCESS read-only
    STATUS mandatory
    DESCRIPTION
        "The bit-wise position of each packet marking feature."
    ::= { cbQosSetCfgEntry 1 }

cbQosSetCfgIpDSCPValue OBJECT-TYPE
    SYNTAX INTEGER(0..63)
    ACCESS read-only
    STATUS mandatory
    DESCRIPTION
        "The IP DSCP value at which the packet is being set
        by the packet marking feature."
    ::= { cbQosSetCfgEntry 2 }

cbQosSetCfgIpPrecedenceValue OBJECT-TYPE
    SYNTAX INTEGER(0..7)
    ACCESS read-only
    STATUS mandatory
    DESCRIPTION
        "The IP precedence value at which the packet is being
        set by the packet marking feature."
    ::= { cbQosSetCfgEntry 3 }

cbQosSetCfgQosGroupValue OBJECT-TYPE
    SYNTAX INTEGER(0..99)
    ACCESS read-only
    STATUS mandatory
    DESCRIPTION
        "The QoS Group number at which the packet is being
        set by the packet marking feature."
    ::= { cbQosSetCfgEntry 4 }

cbQosSetCfgL2CosValue OBJECT-TYPE
    SYNTAX INTEGER(0..7)
    ACCESS read-only
    STATUS mandatory
    DESCRIPTION
        "The Layer 2 Cos value at which the packet is being
        set by the packet marking feature."
    ::= { cbQosSetCfgEntry 5 }

cbQosSetCfgMplsExpValue OBJECT-TYPE
    SYNTAX Gauge(0..7)
    ACCESS read-only
    STATUS mandatory
    DESCRIPTION
        "The MPLS experimental value at which the packet
        is being set by the packet marking feature."
    ::= { cbQosSetCfgEntry 6 }

cbQosSetCfgDiscardClassValue OBJECT-TYPE
    SYNTAX Gauge(0..7)
    ACCESS read-only
    STATUS mandatory
    DESCRIPTION
        "The Discard Class value at which the packet
        is being set by the packet marking feature."
    ::= { cbQosSetCfgEntry 7 }

cbQosSetCfgMplsExpTopMostValue OBJECT-TYPE
    SYNTAX Gauge(0..7)
    ACCESS read-only
    STATUS mandatory
    DESCRIPTION
        "The MPLS experimental value on the topmost label
        at which the packet is being set by the packet marking
        feature."
    ::= { cbQosSetCfgEntry 8 }

cbQosSetCfgSrpPriority OBJECT-TYPE
    SYNTAX Gauge(0..7)
    ACCESS read-only
    STATUS mandatory
    DESCRIPTION
        "The SRP Priority value at which the packet is being set
        by the packet marking feature.  The higher the value the
        higher the priority.  SRP is a Cisco developed protocol.
        RFC 2892: The Cisco SRP MAC Layer Protocol."
    ::= { cbQosSetCfgEntry 9 }

cbQosSetCfgFrFecnBecn OBJECT-TYPE
    SYNTAX Gauge(0..99)
    ACCESS read-only
    STATUS mandatory
    DESCRIPTION
        "This is a configurable parameter in percentage of the
        queue size.  When the current queue size out of the
        queue limit is greater than this parameter, both 
        Frame Relay FECN and BECN bits will be set for
        Frame Relay congestion notification mechanism."
    ::= { cbQosSetCfgEntry 10 }

cbQosCMStatsTable OBJECT-TYPE
    SYNTAX SEQUENCE OF CbQosCMStatsEntry
    ACCESS not-accessible
    STATUS mandatory
    DESCRIPTION
        "This table specifies ClassMap related Statistical
        information."
    ::= { cbQosClassMapStats 1 }

cbQosCMStatsEntry OBJECT-TYPE
    SYNTAX CbQosCMStatsEntry
    ACCESS not-accessible
    STATUS mandatory
    DESCRIPTION
        "Each entry in this table describes the statistical
        information about ClassMap. ClassMap specific information
        you can find in this table are : pre/post policy pkt/byte
        counts, bit rates, drop pkt/bytes and no buffer drops.
        
        This table contains statistical information only,
        no configuration information associated with it. Therefore, 
        it is indexed by the instance specific IDs, such as 
        cbQosPolicyIndex and cbQosObjectsIndex."
    INDEX { cbQosPolicyIndex, cbQosObjectsIndex }
    ::= { cbQosCMStatsTable 1 }

CbQosCMStatsEntry ::= SEQUENCE {
    cbQosCMPrePolicyPktOverflow Counter,
    cbQosCMPrePolicyPkt Counter,
    cbQosCMPrePolicyPkt64 Counter,
    cbQosCMPrePolicyByteOverflow Counter,
    cbQosCMPrePolicyByte Counter,
    cbQosCMPrePolicyByte64 Counter,
    cbQosCMPrePolicyBitRate Gauge,
    cbQosCMPostPolicyByteOverflow Counter,
    cbQosCMPostPolicyByte Counter,
    cbQosCMPostPolicyByte64 Counter,
    cbQosCMPostPolicyBitRate Gauge,
    cbQosCMDropPktOverflow Counter,
    cbQosCMDropPkt Counter,
    cbQosCMDropPkt64 Counter,
    cbQosCMDropByteOverflow Counter,
    cbQosCMDropByte Counter,
    cbQosCMDropByte64 Counter,
    cbQosCMDropBitRate Gauge,
    cbQosCMNoBufDropPktOverflow Counter,
    cbQosCMNoBufDropPkt Counter,
    cbQosCMNoBufDropPkt64 Counter
    }

cbQosCMPrePolicyPktOverflow OBJECT-TYPE
    SYNTAX Counter
    ACCESS read-only
    STATUS mandatory
    DESCRIPTION
        "The upper 32 bits count of inbound packets prior to
        executing any QoS policies."
    ::= { cbQosCMStatsEntry 1 }

cbQosCMPrePolicyPkt OBJECT-TYPE
    SYNTAX Counter
    ACCESS read-only
    STATUS mandatory
    DESCRIPTION
        "The lower 32 bits count of inbound packets prior to
        executing any QoS policies."
    ::= { cbQosCMStatsEntry 2 }

cbQosCMPrePolicyPkt64 OBJECT-TYPE
    SYNTAX --?? syntax is not convertable to SMIv1
           Counter
    ACCESS read-only
    STATUS mandatory
    DESCRIPTION
        "The 64 bits count of inbound packets prior to executing
        any QoS policies."
    ::= { cbQosCMStatsEntry 3 }

cbQosCMPrePolicyByteOverflow OBJECT-TYPE
    SYNTAX Counter
    ACCESS read-only
    STATUS mandatory
    DESCRIPTION
        "The upper 32 bits count of inbound octets prior to
        executing any QoS policies."
    ::= { cbQosCMStatsEntry 4 }

cbQosCMPrePolicyByte OBJECT-TYPE
    SYNTAX Counter
    ACCESS read-only
    STATUS mandatory
    DESCRIPTION
        "The lower 32 bits count of inbound octets prior to
        executing any QoS policies."
    ::= { cbQosCMStatsEntry 5 }

cbQosCMPrePolicyByte64 OBJECT-TYPE
    SYNTAX --?? syntax is not convertable to SMIv1
           Counter
    ACCESS read-only
    STATUS mandatory
    DESCRIPTION
        "The 64 bits count of inbound octets prior to executing
        any QoS policies."
    ::= { cbQosCMStatsEntry 6 }

cbQosCMPrePolicyBitRate OBJECT-TYPE
    SYNTAX Gauge
--  Units
--    bits per second
    ACCESS read-only
    STATUS mandatory
    DESCRIPTION
        "The bit rate of the traffic prior to executing any QoS
        policies."
    ::= { cbQosCMStatsEntry 7 }

cbQosCMPostPolicyByteOverflow OBJECT-TYPE
    SYNTAX Counter
    ACCESS read-only
    STATUS mandatory
    DESCRIPTION
        "The upper 32 bits count of outbound octets after executing
        QoS policies."
    ::= { cbQosCMStatsEntry 8 }

cbQosCMPostPolicyByte OBJECT-TYPE
    SYNTAX Counter
    ACCESS read-only
    STATUS mandatory
    DESCRIPTION
        "The lower 32 bits count of outbound octets after executing
        QoS policies."
    ::= { cbQosCMStatsEntry 9 }

cbQosCMPostPolicyByte64 OBJECT-TYPE
    SYNTAX --?? syntax is not convertable to SMIv1
           Counter
    ACCESS read-only
    STATUS mandatory
    DESCRIPTION
        "The 64 bits count of outbound octets after executing
        QoS policies."
    ::= { cbQosCMStatsEntry 10 }

cbQosCMPostPolicyBitRate OBJECT-TYPE
    SYNTAX Gauge
--  Units
--    bits per second
    ACCESS read-only
    STATUS mandatory
    DESCRIPTION
        "The bit rate of the traffic after executing QoS
        policies."
    ::= { cbQosCMStatsEntry 11 }

cbQosCMDropPktOverflow OBJECT-TYPE
    SYNTAX Counter
    ACCESS read-only
    STATUS mandatory
    DESCRIPTION
        "The upper 32 bits counter of dropped pkts per class
        as the result of all features that can produce drops 
        (e.g., police, random detect, etc.)."
    ::= { cbQosCMStatsEntry 12 }

cbQosCMDropPkt OBJECT-TYPE
    SYNTAX Counter
    ACCESS read-only
    STATUS mandatory
    DESCRIPTION
        "The lower 32 bits counter of dropped pkts per class
        as the result of all features that can produce drops 
        (e.g., police, random detect, etc.)."
    ::= { cbQosCMStatsEntry 13 }

cbQosCMDropPkt64 OBJECT-TYPE
    SYNTAX --?? syntax is not convertable to SMIv1
           Counter
    ACCESS read-only
    STATUS mandatory
    DESCRIPTION
        "The 64 bits counter of dropped pkts per class as
        the result of all features that can produce drops 
         (e.g., police, random detect, etc.)."
    ::= { cbQosCMStatsEntry 14 }

cbQosCMDropByteOverflow OBJECT-TYPE
    SYNTAX Counter
    ACCESS read-only
    STATUS mandatory
    DESCRIPTION
        "The upper 32 bits counter of dropped bytes per class
        as the result of all features that can produce drops 
        (e.g., police, random detect, etc.)."
    ::= { cbQosCMStatsEntry 15 }

cbQosCMDropByte OBJECT-TYPE
    SYNTAX Counter
    ACCESS read-only
    STATUS mandatory
    DESCRIPTION
        "The lower 32 bits counter of dropped bytes per class
        as the result of all features that can produce drops 
        (e.g., police, random detect, etc.)."
    ::= { cbQosCMStatsEntry 16 }

cbQosCMDropByte64 OBJECT-TYPE
    SYNTAX --?? syntax is not convertable to SMIv1
           Counter
    ACCESS read-only
    STATUS mandatory
    DESCRIPTION
        "The 64 bits counter of dropped bytes per class as the
        result of all features that can produce drops 
         (e.g., police, random detect, etc.)."
    ::= { cbQosCMStatsEntry 17 }

cbQosCMDropBitRate OBJECT-TYPE
    SYNTAX Gauge
--  Units
--    bits per second
    ACCESS read-only
    STATUS mandatory
    DESCRIPTION
        "The bit rate of the drops per class as the result of
        all features that can produce drops 
        (e.g., police, random detect, etc.)."
    ::= { cbQosCMStatsEntry 18 }

cbQosCMNoBufDropPktOverflow OBJECT-TYPE
    SYNTAX Counter
    ACCESS read-only
    STATUS mandatory
    DESCRIPTION
        "The upper 32 bits drop packet count which occured
        due to a lack of SRAM buffers during output processing 
        on an interface."
    ::= { cbQosCMStatsEntry 19 }

cbQosCMNoBufDropPkt OBJECT-TYPE
    SYNTAX Counter
    ACCESS read-only
    STATUS mandatory
    DESCRIPTION
        "The lower 32 bits drop packet count which occured due
        to a lack of SRAM buffers during output processing on 
        an interface."
    ::= { cbQosCMStatsEntry 20 }

cbQosCMNoBufDropPkt64 OBJECT-TYPE
    SYNTAX --?? syntax is not convertable to SMIv1
           Counter
    ACCESS read-only
    STATUS mandatory
    DESCRIPTION
        "The 64 bits drop packet count which occured due to a
        lack of SRAM buffers during output processing on an 
        interface."
    ::= { cbQosCMStatsEntry 21 }

cbQosMatchStmtStatsTable OBJECT-TYPE
    SYNTAX SEQUENCE OF CbQosMatchStmtStatsEntry
    ACCESS not-accessible
    STATUS mandatory
    DESCRIPTION
        "This table specifies Match Statement related statistical
        information."
    ::= { cbQosMatchStmtStats 1 }

cbQosMatchStmtStatsEntry OBJECT-TYPE
    SYNTAX CbQosMatchStmtStatsEntry
    ACCESS not-accessible
    STATUS mandatory
    DESCRIPTION
        "Each entry in this table describes the statistical
        information about Match Statement. Match Statement specific 
        information you can find in this table are : 
        Pre policy pkt/byte counters, and bit rates.
        
        This table contains statistical information only,
        no configuration information associated with it. Therefore, 
        it is indexed by the instance specific IDs, such as 
        cbQosPolicyIndex and cbQosObjectsIndex."
    INDEX { cbQosPolicyIndex, cbQosObjectsIndex }
    ::= { cbQosMatchStmtStatsTable 1 }

CbQosMatchStmtStatsEntry ::= SEQUENCE {
    cbQosMatchPrePolicyPktOverflow Counter,
    cbQosMatchPrePolicyPkt Counter,
    cbQosMatchPrePolicyPkt64 Counter,
    cbQosMatchPrePolicyByteOverflow Counter,
    cbQosMatchPrePolicyByte Counter,
    cbQosMatchPrePolicyByte64 Counter,
    cbQosMatchPrePolicyBitRate Gauge
    }

cbQosMatchPrePolicyPktOverflow OBJECT-TYPE
    SYNTAX Counter
    ACCESS read-only
    STATUS mandatory
    DESCRIPTION
        "The upper 32 bits count of inbound packets prior to
        executing any QoS policies."
    ::= { cbQosMatchStmtStatsEntry 1 }

cbQosMatchPrePolicyPkt OBJECT-TYPE
    SYNTAX Counter
    ACCESS read-only
    STATUS mandatory
    DESCRIPTION
        "The lower 32 bits count of inbound packets prior to
        executing any QoS policies."
    ::= { cbQosMatchStmtStatsEntry 2 }

cbQosMatchPrePolicyPkt64 OBJECT-TYPE
    SYNTAX --?? syntax is not convertable to SMIv1
           Counter
    ACCESS read-only
    STATUS mandatory
    DESCRIPTION
        "The 64 bits count of inbound packets prior to executing
        any QoS policies."
    ::= { cbQosMatchStmtStatsEntry 3 }

cbQosMatchPrePolicyByteOverflow OBJECT-TYPE
    SYNTAX Counter
    ACCESS read-only
    STATUS mandatory
    DESCRIPTION
        "The upper 32 bits count of inbound octets prior to
        executing any QoS policies."
    ::= { cbQosMatchStmtStatsEntry 4 }

cbQosMatchPrePolicyByte OBJECT-TYPE
    SYNTAX Counter
    ACCESS read-only
    STATUS mandatory
    DESCRIPTION
        "The lower 32 bits count of inbound octets prior to
        executing any QoS policies."
    ::= { cbQosMatchStmtStatsEntry 5 }

cbQosMatchPrePolicyByte64 OBJECT-TYPE
    SYNTAX --?? syntax is not convertable to SMIv1
           Counter
    ACCESS read-only
    STATUS mandatory
    DESCRIPTION
        "The 64 bits count of inbound octets prior to executing
        any QoS policies."
    ::= { cbQosMatchStmtStatsEntry 6 }

cbQosMatchPrePolicyBitRate OBJECT-TYPE
    SYNTAX Gauge
--  Units
--    bits per second
    ACCESS read-only
    STATUS mandatory
    DESCRIPTION
        "The bit rate of the traffic prior to executing any QoS
        policies."
    ::= { cbQosMatchStmtStatsEntry 7 }

cbQosPoliceStatsTable OBJECT-TYPE
    SYNTAX SEQUENCE OF CbQosPoliceStatsEntry
    ACCESS not-accessible
    STATUS mandatory
    DESCRIPTION
        "This table specifies Police Action related Statistical
        information."
    ::= { cbQosPoliceStats 1 }

cbQosPoliceStatsEntry OBJECT-TYPE
    SYNTAX CbQosPoliceStatsEntry
    ACCESS not-accessible
    STATUS mandatory
    DESCRIPTION
        "Each entry in this table describes the statistical
        information about Police Action. Police Action specific 
        information you can find in this table are : 
        Conformed/Exceeded pkt/byte counters,  bit rates.
        
        This table contains statistical information only,
        no configuration information associated with it. 
        Therefore, it is indexed by the instance specific IDs, 
        such as cbQosPolicyIndex and cbQosObjectsIndex."
    INDEX { cbQosPolicyIndex, cbQosObjectsIndex }
    ::= { cbQosPoliceStatsTable 1 }

CbQosPoliceStatsEntry ::= SEQUENCE {
    cbQosPoliceConformedPktOverflow Counter,
    cbQosPoliceConformedPkt Counter,
    cbQosPoliceConformedPkt64 Counter,
    cbQosPoliceConformedByteOverflow Counter,
    cbQosPoliceConformedByte Counter,
    cbQosPoliceConformedByte64 Counter,
    cbQosPoliceConformedBitRate Gauge,
    cbQosPoliceExceededPktOverflow Counter,
    cbQosPoliceExceededPkt Counter,
    cbQosPoliceExceededPkt64 Counter,
    cbQosPoliceExceededByteOverflow Counter,
    cbQosPoliceExceededByte Counter,
    cbQosPoliceExceededByte64 Counter,
    cbQosPoliceExceededBitRate Gauge,
    cbQosPoliceViolatedPktOverflow Counter,
    cbQosPoliceViolatedPkt Counter,
    cbQosPoliceViolatedPkt64 Counter,
    cbQosPoliceViolatedByteOverflow Counter,
    cbQosPoliceViolatedByte Counter,
    cbQosPoliceViolatedByte64 Counter,
    cbQosPoliceViolatedBitRate Gauge
    }

cbQosPoliceConformedPktOverflow OBJECT-TYPE
    SYNTAX Counter
--  Units
--    Packets
    ACCESS read-only
    STATUS mandatory
    DESCRIPTION
        "The upper 32 bits count of packets treated as
        conforming by the policing feature."
    ::= { cbQosPoliceStatsEntry 1 }

cbQosPoliceConformedPkt OBJECT-TYPE
    SYNTAX Counter
--  Units
--    Packets
    ACCESS read-only
    STATUS mandatory
    DESCRIPTION
        "The lower 32 bits count of packets treated as
        conforming by the policing feature."
    ::= { cbQosPoliceStatsEntry 2 }

cbQosPoliceConformedPkt64 OBJECT-TYPE
    SYNTAX --?? syntax is not convertable to SMIv1
           Counter
--  Units
--    Packets
    ACCESS read-only
    STATUS mandatory
    DESCRIPTION
        "The 64 bits count of packets treated as conforming
        by the policing feature."
    ::= { cbQosPoliceStatsEntry 3 }

cbQosPoliceConformedByteOverflow OBJECT-TYPE
    SYNTAX Counter
--  Units
--    Octets
    ACCESS read-only
    STATUS mandatory
    DESCRIPTION
        "The upper 32 bits count of octets treated as
        conforming by the policing feature."
    ::= { cbQosPoliceStatsEntry 4 }

cbQosPoliceConformedByte OBJECT-TYPE
    SYNTAX Counter
--  Units
--    Octets
    ACCESS read-only
    STATUS mandatory
    DESCRIPTION
        "The lower 32 bits count of octets treated as
        conforming by the policing feature."
    ::= { cbQosPoliceStatsEntry 5 }

cbQosPoliceConformedByte64 OBJECT-TYPE
    SYNTAX --?? syntax is not convertable to SMIv1
           Counter
--  Units
--    Octets
    ACCESS read-only
    STATUS mandatory
    DESCRIPTION
        "The 64 bits count of octets treated as conforming
        by the policing feature."
    ::= { cbQosPoliceStatsEntry 6 }

cbQosPoliceConformedBitRate OBJECT-TYPE
    SYNTAX Gauge
--  Units
--    bits per second
    ACCESS read-only
    STATUS mandatory
    DESCRIPTION
        "The bit rate of conforming traffic."
    ::= { cbQosPoliceStatsEntry 7 }

cbQosPoliceExceededPktOverflow OBJECT-TYPE
    SYNTAX Counter
--  Units
--    Packets
    ACCESS read-only
    STATUS mandatory
    DESCRIPTION
        "The upper 32 bits count of packets treated as
        non-conforming by the policing feature."
    ::= { cbQosPoliceStatsEntry 8 }

cbQosPoliceExceededPkt OBJECT-TYPE
    SYNTAX Counter
--  Units
--    Packets
    ACCESS read-only
    STATUS mandatory
    DESCRIPTION
        "The 32 bits count of packets treated as
        non-conforming by the policing feature."
    ::= { cbQosPoliceStatsEntry 9 }

cbQosPoliceExceededPkt64 OBJECT-TYPE
    SYNTAX --?? syntax is not convertable to SMIv1
           Counter
--  Units
--    Packets
    ACCESS read-only
    STATUS mandatory
    DESCRIPTION
        "The 64 bits count of packets treated as
        non-conforming by the policing feature."
    ::= { cbQosPoliceStatsEntry 10 }

cbQosPoliceExceededByteOverflow OBJECT-TYPE
    SYNTAX Counter
--  Units
--    Octets
    ACCESS read-only
    STATUS mandatory
    DESCRIPTION
        "The upper 32 bits count of octets treated as
        non-conforming by the policing feature."
    ::= { cbQosPoliceStatsEntry 11 }

cbQosPoliceExceededByte OBJECT-TYPE
    SYNTAX Counter
--  Units
--    Octets
    ACCESS read-only
    STATUS mandatory
    DESCRIPTION
        "The lower 32 bits count of octets treated as
        non-conforming by the policing feature."
    ::= { cbQosPoliceStatsEntry 12 }

cbQosPoliceExceededByte64 OBJECT-TYPE
    SYNTAX --?? syntax is not convertable to SMIv1
           Counter
--  Units
--    Octets
    ACCESS read-only
    STATUS mandatory
    DESCRIPTION
        "The 64 bits count of octets treated as
        non-conforming by the policing feature."
    ::= { cbQosPoliceStatsEntry 13 }

cbQosPoliceExceededBitRate OBJECT-TYPE
    SYNTAX Gauge
--  Units
--    bits per second
    ACCESS read-only
    STATUS mandatory
    DESCRIPTION
        "The bit rate of the non-conforming traffic."
    ::= { cbQosPoliceStatsEntry 14 }

cbQosPoliceViolatedPktOverflow OBJECT-TYPE
    SYNTAX Counter
--  Units
--    Packets
    ACCESS read-only
    STATUS mandatory
    DESCRIPTION
        "The upper 32 bits count of packets treated as
        violated by the policing feature."
    ::= { cbQosPoliceStatsEntry 15 }

cbQosPoliceViolatedPkt OBJECT-TYPE
    SYNTAX Counter
--  Units
--    Packets
    ACCESS read-only
    STATUS mandatory
    DESCRIPTION
        "The 32 bits count of packets treated as
        violated by the policing feature."
    ::= { cbQosPoliceStatsEntry 16 }

cbQosPoliceViolatedPkt64 OBJECT-TYPE
    SYNTAX --?? syntax is not convertable to SMIv1
           Counter
--  Units
--    Packets
    ACCESS read-only
    STATUS mandatory
    DESCRIPTION
        "The 64 bits count of packets treated as
        violated by the policing feature."
    ::= { cbQosPoliceStatsEntry 17 }

cbQosPoliceViolatedByteOverflow OBJECT-TYPE
    SYNTAX Counter
--  Units
--    Octets
    ACCESS read-only
    STATUS mandatory
    DESCRIPTION
        "The upper 32 bits count of octets treated as
        violated by the policing feature."
    ::= { cbQosPoliceStatsEntry 18 }

cbQosPoliceViolatedByte OBJECT-TYPE
    SYNTAX Counter
--  Units
--    Octets
    ACCESS read-only
    STATUS mandatory
    DESCRIPTION
        "The lower 32 bits count of octets treated as
        violated by the policing feature."
    ::= { cbQosPoliceStatsEntry 19 }

cbQosPoliceViolatedByte64 OBJECT-TYPE
    SYNTAX --?? syntax is not convertable to SMIv1
           Counter
--  Units
--    Octets
    ACCESS read-only
    STATUS mandatory
    DESCRIPTION
        "The 64 bits count of octets treated as
        violated by the policing feature."
    ::= { cbQosPoliceStatsEntry 20 }

cbQosPoliceViolatedBitRate OBJECT-TYPE
    SYNTAX Gauge
--  Units
--    bits per second
    ACCESS read-only
    STATUS mandatory
    DESCRIPTION
        "The bit rate of the violating traffic."
    ::= { cbQosPoliceStatsEntry 21 }

cbQosQueueingStatsTable OBJECT-TYPE
    SYNTAX SEQUENCE OF CbQosQueueingStatsEntry
    ACCESS not-accessible
    STATUS mandatory
    DESCRIPTION
        "This table specifies Queueing Action related Statistical
        information."
    ::= { cbQosQueueingStats 1 }

cbQosQueueingStatsEntry OBJECT-TYPE
    SYNTAX CbQosQueueingStatsEntry
    ACCESS not-accessible
    STATUS mandatory
    DESCRIPTION
        "Each entry in this table describes the statistical
        information about queueing action. Queueing action specific 
        information you can find in this table are : 
        various Q depth, and discard pkt/byte counters.
        
        This table contains statistical information only,
        no configuration information associated with it. 
        Therefore, it is indexed by the instance specific IDs, 
        such as cbQosPolicyIndex and cbQosObjectsIndex."
    INDEX { cbQosPolicyIndex, cbQosObjectsIndex }
    ::= { cbQosQueueingStatsTable 1 }

CbQosQueueingStatsEntry ::= SEQUENCE {
    cbQosQueueingCurrentQDepth Gauge,
    cbQosQueueingMaxQDepth Gauge,
    cbQosQueueingDiscardByteOverflow Counter,
    cbQosQueueingDiscardByte Counter,
    cbQosQueueingDiscardByte64 Counter,
    cbQosQueueingDiscardPktOverflow Counter,
    cbQosQueueingDiscardPkt Counter,
    cbQosQueueingDiscardPkt64 Counter
    }

cbQosQueueingCurrentQDepth OBJECT-TYPE
    SYNTAX Gauge
--  Units
--    Octets
    ACCESS read-only
    STATUS mandatory
    DESCRIPTION
        "The current depth of the queue."
    ::= { cbQosQueueingStatsEntry 1 }

cbQosQueueingMaxQDepth OBJECT-TYPE
    SYNTAX Gauge
--  Units
--    Octets
    ACCESS read-only
    STATUS mandatory
    DESCRIPTION
        "The maximum depth of the queue."
    ::= { cbQosQueueingStatsEntry 2 }

cbQosQueueingDiscardByteOverflow OBJECT-TYPE
    SYNTAX Counter
--  Units
--    Octets
    ACCESS read-only
    STATUS mandatory
    DESCRIPTION
        "The upper 32 bit count of octets, associated with
        this class, that were dropped by queueing."
    ::= { cbQosQueueingStatsEntry 3 }

cbQosQueueingDiscardByte OBJECT-TYPE
    SYNTAX Counter
--  Units
--    Octets
    ACCESS read-only
    STATUS mandatory
    DESCRIPTION
        "The lower 32 bits count of octets, associated with
        this class, that were dropped by queueing."
    ::= { cbQosQueueingStatsEntry 4 }

cbQosQueueingDiscardByte64 OBJECT-TYPE
    SYNTAX --?? syntax is not convertable to SMIv1
           Counter
--  Units
--    Octets
    ACCESS read-only
    STATUS mandatory
    DESCRIPTION
        "The count of octets, associated with this class,
        that were dropped by queueing."
    ::= { cbQosQueueingStatsEntry 5 }

cbQosQueueingDiscardPktOverflow OBJECT-TYPE
    SYNTAX Counter
--  Units
--    Packets
    ACCESS read-only
    STATUS mandatory
    DESCRIPTION
        "The upper 32 bits count of packets, associated with
        this class, that were dropped by queueing."
    ::= { cbQosQueueingStatsEntry 6 }

cbQosQueueingDiscardPkt OBJECT-TYPE
    SYNTAX Counter
--  Units
--    Packets
    ACCESS read-only
    STATUS mandatory
    DESCRIPTION
        "The number of packets, associated with this class,
        that were dropped by queueing."
    ::= { cbQosQueueingStatsEntry 7 }

cbQosQueueingDiscardPkt64 OBJECT-TYPE
    SYNTAX --?? syntax is not convertable to SMIv1
           Counter
--  Units
--    Packets
    ACCESS read-only
    STATUS mandatory
    DESCRIPTION
        "The number of packets, associated with this class,
        that were dropped by queueing."
    ::= { cbQosQueueingStatsEntry 8 }

cbQosTSStatsTable OBJECT-TYPE
    SYNTAX SEQUENCE OF CbQosTSStatsEntry
    ACCESS not-accessible
    STATUS mandatory
    DESCRIPTION
        "This table specifies traffic-shaping Action related
        Statistical information."
    ::= { cbQosTSStats 1 }

cbQosTSStatsEntry OBJECT-TYPE
    SYNTAX CbQosTSStatsEntry
    ACCESS not-accessible
    STATUS mandatory
    DESCRIPTION
        "Each entry in this table describes the statistical
        information about traffic-shaping Action. Traffic-shaping 
        Action specific information you can find in this table are : 
        various delay/drop pkt/byte counters, state of feature,
        and Q size.
        
        This table contains statistical information only,
        no configuration information associated with it. 
        Therefore, it is indexed by the instance specific IDs, 
        such as cbQosPolicyIndex and cbQosObjectsIndex."
    INDEX { cbQosPolicyIndex, cbQosObjectsIndex }
    ::= { cbQosTSStatsTable 1 }

CbQosTSStatsEntry ::= SEQUENCE {
    cbQosTSStatsDelayedByteOverflow Counter,
    cbQosTSStatsDelayedByte Counter,
    cbQosTSStatsDelayedByte64 Counter,
    cbQosTSStatsDelayedPktOverflow Counter,
    cbQosTSStatsDelayedPkt Counter,
    cbQosTSStatsDelayedPkt64 Counter,
    cbQosTSStatsDropByteOverflow Counter,
    cbQosTSStatsDropByte Counter,
    cbQosTSStatsDropByte64 Counter,
    cbQosTSStatsDropPktOverflow Counter,
    cbQosTSStatsDropPkt Counter,
    cbQosTSStatsDropPkt64 Counter,
    cbQosTSStatsActive TruthValue,
    cbQosTSStatsCurrentQSize Gauge
    }

cbQosTSStatsDelayedByteOverflow OBJECT-TYPE
    SYNTAX Counter
--  Units
--    octets
    ACCESS read-only
    STATUS mandatory
    DESCRIPTION
        "This object represents the upper 32 bits counter of
        octets that have been delayed."
    ::= { cbQosTSStatsEntry 1 }

cbQosTSStatsDelayedByte OBJECT-TYPE
    SYNTAX Counter
--  Units
--    octets
    ACCESS read-only
    STATUS mandatory
    DESCRIPTION
        "This object represents the lower 32 bits counter of
        octets that have been delayed."
    ::= { cbQosTSStatsEntry 2 }

cbQosTSStatsDelayedByte64 OBJECT-TYPE
    SYNTAX --?? syntax is not convertable to SMIv1
           Counter
--  Units
--    octets
    ACCESS read-only
    STATUS mandatory
    DESCRIPTION
        "This object represents the 64 bits counter of
        octets that have been delayed."
    ::= { cbQosTSStatsEntry 3 }

cbQosTSStatsDelayedPktOverflow OBJECT-TYPE
    SYNTAX Counter
--  Units
--    packets
    ACCESS read-only
    STATUS mandatory
    DESCRIPTION
        "This object represents the upper 32 bits counter of
        packets that have been delayed."
    ::= { cbQosTSStatsEntry 4 }

cbQosTSStatsDelayedPkt OBJECT-TYPE
    SYNTAX Counter
--  Units
--    packets
    ACCESS read-only
    STATUS mandatory
    DESCRIPTION
        "This object represents the lower 32 bits counter of
        packets that have been delayed."
    ::= { cbQosTSStatsEntry 5 }

cbQosTSStatsDelayedPkt64 OBJECT-TYPE
    SYNTAX --?? syntax is not convertable to SMIv1
           Counter
--  Units
--    packets
    ACCESS read-only
    STATUS mandatory
    DESCRIPTION
        "This object represents the 64 bits counter of
        packets that have been delayed."
    ::= { cbQosTSStatsEntry 6 }

cbQosTSStatsDropByteOverflow OBJECT-TYPE
    SYNTAX Counter
--  Units
--    octets
    ACCESS read-only
    STATUS mandatory
    DESCRIPTION
        "This object represents the upper 32 bits counter of
        octets that have been dropped during shaping."
    ::= { cbQosTSStatsEntry 7 }

cbQosTSStatsDropByte OBJECT-TYPE
    SYNTAX Counter
--  Units
--    octets
    ACCESS read-only
    STATUS mandatory
    DESCRIPTION
        "This object represents the lower 32 bits counter of
        octets that have been dropped during shaping."
    ::= { cbQosTSStatsEntry 8 }

cbQosTSStatsDropByte64 OBJECT-TYPE
    SYNTAX --?? syntax is not convertable to SMIv1
           Counter
--  Units
--    octets
    ACCESS read-only
    STATUS mandatory
    DESCRIPTION
        "This object represents the 64 bits counter of
        octets that have been dropped during shaping."
    ::= { cbQosTSStatsEntry 9 }

cbQosTSStatsDropPktOverflow OBJECT-TYPE
    SYNTAX Counter
--  Units
--    packets
    ACCESS read-only
    STATUS mandatory
    DESCRIPTION
        "This object represents the upper 32 bits counter of
        packets that have been dropped during shaping."
    ::= { cbQosTSStatsEntry 10 }

cbQosTSStatsDropPkt OBJECT-TYPE
    SYNTAX Counter
--  Units
--    packets
    ACCESS read-only
    STATUS mandatory
    DESCRIPTION
        "This object represents the lower 32 bits counter of
        packets that have been dropped during shaping."
    ::= { cbQosTSStatsEntry 11 }

cbQosTSStatsDropPkt64 OBJECT-TYPE
    SYNTAX --?? syntax is not convertable to SMIv1
           Counter
--  Units
--    packets
    ACCESS read-only
    STATUS mandatory
    DESCRIPTION
        "This object represents the 64 bits counter of
        packets that have been dropped during shaping."
    ::= { cbQosTSStatsEntry 12 }

cbQosTSStatsActive OBJECT-TYPE
    SYNTAX TruthValue
--    Rsyntax INTEGER {
--        true(1),
--        false(2)
--        }
    ACCESS read-only
    STATUS mandatory
    DESCRIPTION
        "This object indicates the current traffic-shaping
        state. When traffic-shaping is enabled and the traffic 
        rate exceeds the shape rate, traffic-shaping
        is considered to be active.  Otherwise, it is 
        considered inactive."
    ::= { cbQosTSStatsEntry 13 }

cbQosTSStatsCurrentQSize OBJECT-TYPE
    SYNTAX Gauge
--  Units
--    packets
    ACCESS read-only
    STATUS mandatory
    DESCRIPTION
        "This object indicates the current traffic-shaping
        queue depth in packets."
    ::= { cbQosTSStatsEntry 14 }

cbQosREDClassStatsTable OBJECT-TYPE
    SYNTAX SEQUENCE OF CbQosREDClassStatsEntry
    ACCESS not-accessible
    STATUS mandatory
    DESCRIPTION
        "This table specifies per Precedence WRED Action related
        Statistical information."
    ::= { cbQosREDClassStats 1 }

cbQosREDClassStatsEntry OBJECT-TYPE
    SYNTAX CbQosREDClassStatsEntry
    ACCESS not-accessible
    STATUS mandatory
    DESCRIPTION
        "Each entry in this table describes the statistical
        information about per Precedence WRED Action. per Precedence
        WRED Action specific information you can find in this table 
        are : Random pkt/byte counters, and Tail drop pkt/byte 
        counters.
        
        This table contains per Precedence/dscp based statistical 
        information only, no configuration information associated 
        with it.  Therefore, it is indexed by the instance specific 
        IDs, and a per Precedence identifier: 
        cbQosPolicyIndex, cbQosObjectsIndex and cbQosREDValue."
    INDEX { cbQosPolicyIndex, cbQosObjectsIndex, cbQosREDValue }
    ::= { cbQosREDClassStatsTable 1 }

CbQosREDClassStatsEntry ::= SEQUENCE {
    cbQosREDRandomDropPktOverflow Counter,
    cbQosREDRandomDropPkt Counter,
    cbQosREDRandomDropPkt64 Counter,
    cbQosREDRandomDropByteOverflow Counter,
    cbQosREDRandomDropByte Counter,
    cbQosREDRandomDropByte64 Counter,
    cbQosREDTailDropPktOverflow Counter,
    cbQosREDTailDropPkt Counter,
    cbQosREDTailDropPkt64 Counter,
    cbQosREDTailDropByteOverflow Counter,
    cbQosREDTailDropByte Counter,
    cbQosREDTailDropByte64 Counter,
    cbQosREDTransmitPktOverflow Counter,
    cbQosREDTransmitPkt Counter,
    cbQosREDTransmitPkt64 Counter,
    cbQosREDTransmitByteOverflow Counter,
    cbQosREDTransmitByte Counter,
    cbQosREDTransmitByte64 Counter,
    cbQosREDECNMarkPktOverflow Counter,
    cbQosREDECNMarkPkt Counter,
    cbQosREDECNMarkPkt64 Counter,
    cbQosREDECNMarkByteOverflow Counter,
    cbQosREDECNMarkByte Counter,
    cbQosREDECNMarkByte64 Counter,
    cbQosREDMeanQSizeUnits CbQosQueueUnitType,
    cbQosREDMeanQSize CbQosQueueDepth
    }

cbQosREDRandomDropPktOverflow OBJECT-TYPE
    SYNTAX Counter
--  Units
--    Packets
    ACCESS read-only
    STATUS mandatory
    DESCRIPTION
        "The upper 32 bits count of packets dropped when the
        number of packets in the associated queue was greater
        than the minimum threshold and less than the
        maximum threshold."
    ::= { cbQosREDClassStatsEntry 1 }

cbQosREDRandomDropPkt OBJECT-TYPE
    SYNTAX Counter
--  Units
--    Packets
    ACCESS read-only
    STATUS mandatory
    DESCRIPTION
        "The lower 32 bits count of packets dropped when
        the number of packets in the associated queue was 
        greater than the minimum threshold and less than the
        maximum threshold."
    ::= { cbQosREDClassStatsEntry 2 }

cbQosREDRandomDropPkt64 OBJECT-TYPE
    SYNTAX --?? syntax is not convertable to SMIv1
           Counter
--  Units
--    Packets
    ACCESS read-only
    STATUS mandatory
    DESCRIPTION
        "The 64 bits count of packets dropped when the number
        of packets in the associated queue was greater 
        than the minimum threshold and less than the
        maximum threshold."
    ::= { cbQosREDClassStatsEntry 3 }

cbQosREDRandomDropByteOverflow OBJECT-TYPE
    SYNTAX Counter
--  Units
--    Octets
    ACCESS read-only
    STATUS mandatory
    DESCRIPTION
        "The upper 32 bits count of bytes dropped when the
        number of packets in the associated queue was greater
        than the minimum threshold and less than the
        maximum threshold."
    ::= { cbQosREDClassStatsEntry 4 }

cbQosREDRandomDropByte OBJECT-TYPE
    SYNTAX Counter
--  Units
--    Octets
    ACCESS read-only
    STATUS mandatory
    DESCRIPTION
        "The lower 32 bits count of bytes dropped when
        the number of packets in the associated queue was 
        greater than the minimum threshold and less than the
        maximum threshold."
    ::= { cbQosREDClassStatsEntry 5 }

cbQosREDRandomDropByte64 OBJECT-TYPE
    SYNTAX --?? syntax is not convertable to SMIv1
           Counter
--  Units
--    Octets
    ACCESS read-only
    STATUS mandatory
    DESCRIPTION
        "The 64 bits count of bytes dropped when the number of
        packets in the associated queue was greater
        than the minimum threshold and less than the
        maximum threshold."
    ::= { cbQosREDClassStatsEntry 6 }

cbQosREDTailDropPktOverflow OBJECT-TYPE
    SYNTAX Counter
--  Units
--    Packets
    ACCESS read-only
    STATUS mandatory
    DESCRIPTION
        "The upper 32 bits count of packets dropped when the
        number of packets in the associated queue was greater
        than the maximum threshold."
    ::= { cbQosREDClassStatsEntry 7 }

cbQosREDTailDropPkt OBJECT-TYPE
    SYNTAX Counter
--  Units
--    Packets
    ACCESS read-only
    STATUS mandatory
    DESCRIPTION
        "The lower 32 bits count of packets dropped when the
        number of packets in the associated queue was greater
        than the maximum threshold."
    ::= { cbQosREDClassStatsEntry 8 }

cbQosREDTailDropPkt64 OBJECT-TYPE
    SYNTAX --?? syntax is not convertable to SMIv1
           Counter
--  Units
--    Packets
    ACCESS read-only
    STATUS mandatory
    DESCRIPTION
        "The 64 bits count of packets dropped when the number
        of packets in the associated queue was greater
        than the maximum threshold."
    ::= { cbQosREDClassStatsEntry 9 }

cbQosREDTailDropByteOverflow OBJECT-TYPE
    SYNTAX Counter
--  Units
--    Octets
    ACCESS read-only
    STATUS mandatory
    DESCRIPTION
        "The upper 32 bits count of bytes dropped when the
        number of packets in the associated queue was greater
        than the maximum threshold."
    ::= { cbQosREDClassStatsEntry 10 }

cbQosREDTailDropByte OBJECT-TYPE
    SYNTAX Counter
--  Units
--    Octets
    ACCESS read-only
    STATUS mandatory
    DESCRIPTION
        "The lower 32 bits count of bytes dropped when the
        number of packets in the associated queue was greater
        than the maximum threshold."
    ::= { cbQosREDClassStatsEntry 11 }

cbQosREDTailDropByte64 OBJECT-TYPE
    SYNTAX --?? syntax is not convertable to SMIv1
           Counter
--  Units
--    Octets
    ACCESS read-only
    STATUS mandatory
    DESCRIPTION
        "The 64 bits count of bytes dropped when the number of
        packets in the associated queue was greater
        than the maximum threshold."
    ::= { cbQosREDClassStatsEntry 12 }

cbQosREDTransmitPktOverflow OBJECT-TYPE
    SYNTAX Counter
--  Units
--    Packets
    ACCESS read-only
    STATUS mandatory
    DESCRIPTION
        "The upper 32 bits count of bytes transmitted."
    ::= { cbQosREDClassStatsEntry 13 }

cbQosREDTransmitPkt OBJECT-TYPE
    SYNTAX Counter
--  Units
--    Packets
    ACCESS read-only
    STATUS mandatory
    DESCRIPTION
        "The lower 32 bits count of bytes trasmitted."
    ::= { cbQosREDClassStatsEntry 14 }

cbQosREDTransmitPkt64 OBJECT-TYPE
    SYNTAX --?? syntax is not convertable to SMIv1
           Counter
--  Units
--    Packets
    ACCESS read-only
    STATUS mandatory
    DESCRIPTION
        "The 64 bits count of packets transmitted."
    ::= { cbQosREDClassStatsEntry 15 }

cbQosREDTransmitByteOverflow OBJECT-TYPE
    SYNTAX Counter
--  Units
--    Octets
    ACCESS read-only
    STATUS mandatory
    DESCRIPTION
        "The upper 32 bits count of octets transmitted."
    ::= { cbQosREDClassStatsEntry 16 }

cbQosREDTransmitByte OBJECT-TYPE
    SYNTAX Counter
--  Units
--    Octets
    ACCESS read-only
    STATUS mandatory
    DESCRIPTION
        "The lower 32 bits count of octets trasmitted."
    ::= { cbQosREDClassStatsEntry 17 }

cbQosREDTransmitByte64 OBJECT-TYPE
    SYNTAX --?? syntax is not convertable to SMIv1
           Counter
--  Units
--    Octets
    ACCESS read-only
    STATUS mandatory
    DESCRIPTION
        "The 64 bits count of octets transmitted."
    ::= { cbQosREDClassStatsEntry 18 }

cbQosREDECNMarkPktOverflow OBJECT-TYPE
    SYNTAX Counter
--  Units
--    Packets
    ACCESS read-only
    STATUS mandatory
    DESCRIPTION
        "The upper 32 bits count of packets ecn marked when the
        number of packets in the associated queue was greater
        than the minimum threshold and less than the
        maximum threshold."
    ::= { cbQosREDClassStatsEntry 19 }

cbQosREDECNMarkPkt OBJECT-TYPE
    SYNTAX Counter
--  Units
--    Packets
    ACCESS read-only
    STATUS mandatory
    DESCRIPTION
        "The lower 32 bits count of packets ecn marked when
        the number of packets in the associated queue was 
        greater than the minimum threshold and less than the
        maximum threshold."
    ::= { cbQosREDClassStatsEntry 20 }

cbQosREDECNMarkPkt64 OBJECT-TYPE
    SYNTAX --?? syntax is not convertable to SMIv1
           Counter
--  Units
--    Packets
    ACCESS read-only
    STATUS mandatory
    DESCRIPTION
        "The 64 bits count of packets ecn marked when the
        number of packets in the associated queue was 
        greater than the minimum threshold and less than 
        the maximum threshold."
    ::= { cbQosREDClassStatsEntry 21 }

cbQosREDECNMarkByteOverflow OBJECT-TYPE
    SYNTAX Counter
--  Units
--    Octets
    ACCESS read-only
    STATUS mandatory
    DESCRIPTION
        "The upper 32 bits count of bytes ecn marked when
        the number of packets in the associated queue was 
        greater than the minimum threshold and less than the
        maximum threshold."
    ::= { cbQosREDClassStatsEntry 22 }

cbQosREDECNMarkByte OBJECT-TYPE
    SYNTAX Counter
--  Units
--    Octets
    ACCESS read-only
    STATUS mandatory
    DESCRIPTION
        "The lower 32 bits count of bytes ecn marked when
        the number of packets in the associated queue was 
        greater than the minimum threshold and less than the
        maximum threshold."
    ::= { cbQosREDClassStatsEntry 23 }

cbQosREDECNMarkByte64 OBJECT-TYPE
    SYNTAX --?? syntax is not convertable to SMIv1
           Counter
--  Units
--    Octets
    ACCESS read-only
    STATUS mandatory
    DESCRIPTION
        "The 64 bits count of bytes ecn marked when the
        number of packets in the associated queue was 
        greater than the minimum threshold and less than the
        maximum threshold."
    ::= { cbQosREDClassStatsEntry 24 }

cbQosREDMeanQSizeUnits OBJECT-TYPE
    SYNTAX CbQosQueueUnitType
--    Rsyntax INTEGER {
--        packets(1),
--        cells(2),
--        bytes(3),
--        ms(4),
--        us(5)
--        }
    ACCESS read-only
    STATUS mandatory
    DESCRIPTION
        "Represents the unit type of cbQosREDMeanQSize
        object."
    ::= { cbQosREDClassStatsEntry 25 }

cbQosREDMeanQSize OBJECT-TYPE
    SYNTAX CbQosQueueDepth
--    Rsyntax Gauge
    ACCESS read-only
    STATUS mandatory
    DESCRIPTION
        "The average queue size computed and used by the
        WRED algorithm."
    ::= { cbQosREDClassStatsEntry 26 }

cbQosIPHCCfgTable OBJECT-TYPE
    SYNTAX SEQUENCE OF CbQosIPHCCfgEntry
    ACCESS not-accessible
    STATUS mandatory
    DESCRIPTION
        "This table specifies IP Header Compression
        configuration information."
    ::= { cbQosIPHCCfg 1 }

cbQosIPHCCfgEntry OBJECT-TYPE
    SYNTAX CbQosIPHCCfgEntry
    ACCESS not-accessible
    STATUS mandatory
    DESCRIPTION
        "Each entry in this table describes configuration
        information about IP Header compression. This
        includes the compression option of UDP/RTP header,
        TCP header or both.
        
        This table contains configuration information only,
        no statistics associated with it. Therefore, it is
        indexed by cbQosConfigIndex."
    INDEX { cbQosConfigIndex }
    ::= { cbQosIPHCCfgTable 1 }

CbQosIPHCCfgEntry ::= SEQUENCE {
    cbQosIPHCCfgOption IPHCOption
    }

cbQosIPHCCfgOption OBJECT-TYPE
    SYNTAX IPHCOption
--    Rsyntax INTEGER {
--        rtp(1),
--        tcp(2),
--        bothRtpTcp(3)
--        }
    ACCESS read-only
    STATUS mandatory
    DESCRIPTION
        "The configured IP header compression option.
        The value is defined by IPHCOption."
    ::= { cbQosIPHCCfgEntry 1 }

cbQosIPHCStatsTable OBJECT-TYPE
    SYNTAX SEQUENCE OF CbQosIPHCStatsEntry
    ACCESS not-accessible
    STATUS mandatory
    DESCRIPTION
        "This table specifies IP Header Compression
        statistical information."
    ::= { cbQosIPHCStats 1 }

cbQosIPHCStatsEntry OBJECT-TYPE
    SYNTAX CbQosIPHCStatsEntry
    ACCESS not-accessible
    STATUS mandatory
    DESCRIPTION
        "Each entry in this table describes statistical
        information about IP Header compression.
        
        This table contains statistical information only,
        no configuration information associated with it.
        Therefore, it is indexed by the instance specific IDs,
        namely cbQosPolicyIndex and cbQosObjectsIndex."
    INDEX { cbQosPolicyIndex, cbQosObjectsIndex }
    ::= { cbQosIPHCStatsTable 1 }

CbQosIPHCStatsEntry ::= SEQUENCE {
    cbQosIPHCRtpSentPktOverflow Counter,
    cbQosIPHCRtpSentPkt Counter,
    cbQosIPHCRtpSentPkt64 Counter,
    cbQosIPHCRtpCmprsOutPktOverflow Counter,
    cbQosIPHCRtpCmprsOutPkt Counter,
    cbQosIPHCRtpCmprsOutPkt64 Counter,
    cbQosIPHCRtpSavedByteOverflow Counter,
    cbQosIPHCRtpSavedByte Counter,
    cbQosIPHCRtpSavedByte64 Counter,
    cbQosIPHCRtpSentByteOverflow Counter,
    cbQosIPHCRtpSentByte Counter,
    cbQosIPHCRtpSentByte64 Counter,
    cbQosIPHCRtpSentByteRate Gauge,
    cbQosIPHCTcpSentPktOverflow Counter,
    cbQosIPHCTcpSentPkt Counter,
    cbQosIPHCTcpSentPkt64 Counter,
    cbQosIPHCTcpCmprsOutPktOverflow Counter,
    cbQosIPHCTcpCmprsOutPkt Counter,
    cbQosIPHCTcpCmprsOutPkt64 Counter,
    cbQosIPHCTcpSavedByteOverflow Counter,
    cbQosIPHCTcpSavedByte Counter,
    cbQosIPHCTcpSavedByte64 Counter,
    cbQosIPHCTcpSentByteOverflow Counter,
    cbQosIPHCTcpSentByte Counter,
    cbQosIPHCTcpSentByte64 Counter,
    cbQosIPHCTcpSentByteRate Gauge
    }

cbQosIPHCRtpSentPktOverflow OBJECT-TYPE
    SYNTAX Counter
--  Units
--    Packets
    ACCESS read-only
    STATUS mandatory
    DESCRIPTION
        "The upper 32 bits count of outbound UDP/RTP packets."
    ::= { cbQosIPHCStatsEntry 1 }

cbQosIPHCRtpSentPkt OBJECT-TYPE
    SYNTAX Counter
--  Units
--    Packets
    ACCESS read-only
    STATUS mandatory
    DESCRIPTION
        "The lower 32 bits count of outbound UDP/RTP packets."
    ::= { cbQosIPHCStatsEntry 2 }

cbQosIPHCRtpSentPkt64 OBJECT-TYPE
    SYNTAX --?? syntax is not convertable to SMIv1
           Counter
--  Units
--    Packets
    ACCESS read-only
    STATUS mandatory
    DESCRIPTION
        "The 64 bits count of outbound UDP/RTP packets."
    ::= { cbQosIPHCStatsEntry 3 }

cbQosIPHCRtpCmprsOutPktOverflow OBJECT-TYPE
    SYNTAX Counter
--  Units
--    Packets
    ACCESS read-only
    STATUS mandatory
    DESCRIPTION
        "The upper 32 bits count of outbound compressed
        UDP/RTP packets."
    ::= { cbQosIPHCStatsEntry 4 }

cbQosIPHCRtpCmprsOutPkt OBJECT-TYPE
    SYNTAX Counter
--  Units
--    Packets
    ACCESS read-only
    STATUS mandatory
    DESCRIPTION
        "The lower 32 bits count of outbound compressed
        UDP/RTP packets."
    ::= { cbQosIPHCStatsEntry 5 }

cbQosIPHCRtpCmprsOutPkt64 OBJECT-TYPE
    SYNTAX --?? syntax is not convertable to SMIv1
           Counter
--  Units
--    Packets
    ACCESS read-only
    STATUS mandatory
    DESCRIPTION
        "The 64 bits count of outbound compressed
        UDP/RTP packets."
    ::= { cbQosIPHCStatsEntry 6 }

cbQosIPHCRtpSavedByteOverflow OBJECT-TYPE
    SYNTAX Counter
--  Units
--    Octets
    ACCESS read-only
    STATUS mandatory
    DESCRIPTION
        "The upper 32 bits count of UDP/RTP bytes that
        saved due to IPHC."
    ::= { cbQosIPHCStatsEntry 7 }

cbQosIPHCRtpSavedByte OBJECT-TYPE
    SYNTAX Counter
--  Units
--    Octets
    ACCESS read-only
    STATUS mandatory
    DESCRIPTION
        "The lower 32 bits count of UDP/RTP bytes that
        saved due to IPHC."
    ::= { cbQosIPHCStatsEntry 8 }

cbQosIPHCRtpSavedByte64 OBJECT-TYPE
    SYNTAX --?? syntax is not convertable to SMIv1
           Counter
--  Units
--    Octets
    ACCESS read-only
    STATUS mandatory
    DESCRIPTION
        "The 64 bits count of UDP/RTP bytes that saved
        due to IPHC."
    ::= { cbQosIPHCStatsEntry 9 }

cbQosIPHCRtpSentByteOverflow OBJECT-TYPE
    SYNTAX Counter
--  Units
--    Octets
    ACCESS read-only
    STATUS mandatory
    DESCRIPTION
        "The upper 32 bits count of outbound UDP/RTP
        bytes."
    ::= { cbQosIPHCStatsEntry 10 }

cbQosIPHCRtpSentByte OBJECT-TYPE
    SYNTAX Counter
--  Units
--    Octets
    ACCESS read-only
    STATUS mandatory
    DESCRIPTION
        "The lower 32 bits count of outbound UDP/RTP
        bytes."
    ::= { cbQosIPHCStatsEntry 11 }

cbQosIPHCRtpSentByte64 OBJECT-TYPE
    SYNTAX --?? syntax is not convertable to SMIv1
           Counter
--  Units
--    Octets
    ACCESS read-only
    STATUS mandatory
    DESCRIPTION
        "The 64 bits count of outbound UDP/RTP bytes."
    ::= { cbQosIPHCStatsEntry 12 }

cbQosIPHCRtpSentByteRate OBJECT-TYPE
    SYNTAX Gauge
--  Units
--    Octets per second
    ACCESS read-only
    STATUS mandatory
    DESCRIPTION
        "The 32 bits count of outbound UDP/RTP byte rate."
    ::= { cbQosIPHCStatsEntry 13 }

cbQosIPHCTcpSentPktOverflow OBJECT-TYPE
    SYNTAX Counter
--  Units
--    Packets
    ACCESS read-only
    STATUS mandatory
    DESCRIPTION
        "The upper 32 bits count of outbound TCP packets."
    ::= { cbQosIPHCStatsEntry 14 }

cbQosIPHCTcpSentPkt OBJECT-TYPE
    SYNTAX Counter
--  Units
--    Packets
    ACCESS read-only
    STATUS mandatory
    DESCRIPTION
        "The lower 32 bits count of outbound TCP packets."
    ::= { cbQosIPHCStatsEntry 15 }

cbQosIPHCTcpSentPkt64 OBJECT-TYPE
    SYNTAX --?? syntax is not convertable to SMIv1
           Counter
--  Units
--    Packets
    ACCESS read-only
    STATUS mandatory
    DESCRIPTION
        "The 64 bits count of outbound TCP packets."
    ::= { cbQosIPHCStatsEntry 16 }

cbQosIPHCTcpCmprsOutPktOverflow OBJECT-TYPE
    SYNTAX Counter
--  Units
--    Packets
    ACCESS read-only
    STATUS mandatory
    DESCRIPTION
        "The upper 32 bits count of outbound compressed
        TCP packets."
    ::= { cbQosIPHCStatsEntry 17 }

cbQosIPHCTcpCmprsOutPkt OBJECT-TYPE
    SYNTAX Counter
--  Units
--    Packets
    ACCESS read-only
    STATUS mandatory
    DESCRIPTION
        "The lower 32 bits count of outbound compressed
        TCP packets."
    ::= { cbQosIPHCStatsEntry 18 }

cbQosIPHCTcpCmprsOutPkt64 OBJECT-TYPE
    SYNTAX --?? syntax is not convertable to SMIv1
           Counter
--  Units
--    Packets
    ACCESS read-only
    STATUS mandatory
    DESCRIPTION
        "The 64 bits count of outbound compressed TCP
        packets."
    ::= { cbQosIPHCStatsEntry 19 }

cbQosIPHCTcpSavedByteOverflow OBJECT-TYPE
    SYNTAX Counter
--  Units
--    Octets
    ACCESS read-only
    STATUS mandatory
    DESCRIPTION
        "The upper 32 bits count of TCP bytes that saved
        due to IPHC."
    ::= { cbQosIPHCStatsEntry 20 }

cbQosIPHCTcpSavedByte OBJECT-TYPE
    SYNTAX Counter
--  Units
--    Octets
    ACCESS read-only
    STATUS mandatory
    DESCRIPTION
        "The lower 32 bits count of TCP bytes that saved
        due to IPHC."
    ::= { cbQosIPHCStatsEntry 21 }

cbQosIPHCTcpSavedByte64 OBJECT-TYPE
    SYNTAX --?? syntax is not convertable to SMIv1
           Counter
--  Units
--    Octets
    ACCESS read-only
    STATUS mandatory
    DESCRIPTION
        "The 64 bits count of TCP bytes that saved due
        to IPHC."
    ::= { cbQosIPHCStatsEntry 22 }

cbQosIPHCTcpSentByteOverflow OBJECT-TYPE
    SYNTAX Counter
--  Units
--    Octets
    ACCESS read-only
    STATUS mandatory
    DESCRIPTION
        "The upper 32 bits count of outbound TCP bytes."
    ::= { cbQosIPHCStatsEntry 23 }

cbQosIPHCTcpSentByte OBJECT-TYPE
    SYNTAX Counter
--  Units
--    Octets
    ACCESS read-only
    STATUS mandatory
    DESCRIPTION
        "The lower 32 bits count of outbound TCP bytes."
    ::= { cbQosIPHCStatsEntry 24 }

cbQosIPHCTcpSentByte64 OBJECT-TYPE
    SYNTAX --?? syntax is not convertable to SMIv1
           Counter
--  Units
--    Octets
    ACCESS read-only
    STATUS mandatory
    DESCRIPTION
        "The 64 bits count of outbound TCP bytes."
    ::= { cbQosIPHCStatsEntry 25 }

cbQosIPHCTcpSentByteRate OBJECT-TYPE
    SYNTAX Gauge
--  Units
--    Octets per second
    ACCESS read-only
    STATUS mandatory
    DESCRIPTION
        "The 32 bits count of outbound TCP byte rate."
    ::= { cbQosIPHCStatsEntry 26 }

cbQosSetStatsTable OBJECT-TYPE
    SYNTAX SEQUENCE OF CbQosSetStatsEntry
    ACCESS not-accessible
    STATUS mandatory
    DESCRIPTION
        "This table specifies packet marking statistical
        information."
    ::= { cbQosSetStats 1 }

cbQosSetStatsEntry OBJECT-TYPE
    SYNTAX CbQosSetStatsEntry
    ACCESS not-accessible
    STATUS mandatory
    DESCRIPTION
        "Each entry in this table describes the packets that
        marked by each marking type.
        
        This table contains statistical information only,
        no configuration information associated with it.
        Therefore, it is indexed by the instance specific
        IDs, namely cbQosPolicyIndex and cbQosObjectsIndex."
    INDEX { cbQosPolicyIndex, cbQosObjectsIndex }
    ::= { cbQosSetStatsTable 1 }

CbQosSetStatsEntry ::= SEQUENCE {
    cbQosSetDscpPkt64 Counter,
    cbQosSetPrecedencePkt64 Counter,
    cbQosSetQosGroupPkt64 Counter,
    cbQosSetFrDePkt64 Counter,
    cbQosSetAtmClpPkt64 Counter,
    cbQosSetL2CosPkt64 Counter,
    cbQosSetMplsExpImpositionPkt64 Counter,
    cbQosSetDiscardClassPkt64 Counter,
    cbQosSetMplsExpTopMostPkt64 Counter,
    cbQosSetSrpPriorityPkt64 Counter,
    cbQosSetFrFecnBecnPkt64 Counter,
    cbQosSetDscpTunnelPkt64 Counter,
    cbQosSetPrecedenceTunnelPkt64 Counter
    }

cbQosSetDscpPkt64 OBJECT-TYPE
    SYNTAX --?? syntax is not convertable to SMIv1
           Counter
--  Units
--    Packets
    ACCESS read-only
    STATUS mandatory
    DESCRIPTION
        "The 64 bits count of packets whose DSCP field is
        marked by Set feature."
    ::= { cbQosSetStatsEntry 1 }

cbQosSetPrecedencePkt64 OBJECT-TYPE
    SYNTAX --?? syntax is not convertable to SMIv1
           Counter
--  Units
--    Packets
    ACCESS read-only
    STATUS mandatory
    DESCRIPTION
        "The 64 bits count of packets whose Precedence field is
        marked by Set feature."
    ::= { cbQosSetStatsEntry 2 }

cbQosSetQosGroupPkt64 OBJECT-TYPE
    SYNTAX --?? syntax is not convertable to SMIv1
           Counter
--  Units
--    Packets
    ACCESS read-only
    STATUS mandatory
    DESCRIPTION
        "The 64 bits count of packets whose Qos Group field is
        marked by Set feature."
    ::= { cbQosSetStatsEntry 3 }

cbQosSetFrDePkt64 OBJECT-TYPE
    SYNTAX --?? syntax is not convertable to SMIv1
           Counter
--  Units
--    Packets
    ACCESS read-only
    STATUS mandatory
    DESCRIPTION
        "The 64 bits count of packets whose Frame Relay DE Bit
        is marked by Set feature."
    ::= { cbQosSetStatsEntry 4 }

cbQosSetAtmClpPkt64 OBJECT-TYPE
    SYNTAX --?? syntax is not convertable to SMIv1
           Counter
--  Units
--    Packets
    ACCESS read-only
    STATUS mandatory
    DESCRIPTION
        "The 64 bits count of packets whose ATM CLP Bit is
        marked by Set feature."
    ::= { cbQosSetStatsEntry 5 }

cbQosSetL2CosPkt64 OBJECT-TYPE
    SYNTAX --?? syntax is not convertable to SMIv1
           Counter
--  Units
--    Packets
    ACCESS read-only
    STATUS mandatory
    DESCRIPTION
        "The 64 bits count of packets whose Layer 2 Cos field is
        marked by Set feature."
    ::= { cbQosSetStatsEntry 6 }

cbQosSetMplsExpImpositionPkt64 OBJECT-TYPE
    SYNTAX --?? syntax is not convertable to SMIv1
           Counter
--  Units
--    Packets
    ACCESS read-only
    STATUS mandatory
    DESCRIPTION
        "The 64 bits count of packets whose MPLS Experimental
        Imposition field is marked by Set feature."
    ::= { cbQosSetStatsEntry 7 }

cbQosSetDiscardClassPkt64 OBJECT-TYPE
    SYNTAX --?? syntax is not convertable to SMIv1
           Counter
--  Units
--    Packets
    ACCESS read-only
    STATUS mandatory
    DESCRIPTION
        "The 64 bits count of packets whose Discard Class field
        is marked by Set feature."
    ::= { cbQosSetStatsEntry 8 }

cbQosSetMplsExpTopMostPkt64 OBJECT-TYPE
    SYNTAX --?? syntax is not convertable to SMIv1
           Counter
--  Units
--    Packets
    ACCESS read-only
    STATUS mandatory
    DESCRIPTION
        "The 64 bits count of packets whose MPLS Experimental
        TopMost field is marked by Set feature."
    ::= { cbQosSetStatsEntry 9 }

cbQosSetSrpPriorityPkt64 OBJECT-TYPE
    SYNTAX --?? syntax is not convertable to SMIv1
           Counter
--  Units
--    Packets
    ACCESS read-only
    STATUS mandatory
    DESCRIPTION
        "The 64 bits count of packets whose SRP Priority field
        is marked by Set feature."
    ::= { cbQosSetStatsEntry 10 }

cbQosSetFrFecnBecnPkt64 OBJECT-TYPE
    SYNTAX --?? syntax is not convertable to SMIv1
           Counter
--  Units
--    Packets
    ACCESS read-only
    STATUS mandatory
    DESCRIPTION
        "The 64 bits count of packets whose Frame Relay FECN
        BECN field is marked by Set feature."
    ::= { cbQosSetStatsEntry 11 }

cbQosSetDscpTunnelPkt64 OBJECT-TYPE
    SYNTAX --?? syntax is not convertable to SMIv1
           Counter
--  Units
--    Packets
    ACCESS read-only
    STATUS mandatory
    DESCRIPTION
        "The 64 bits count of packets whose DSCP Tunnel field is
        marked by Set feature."
    ::= { cbQosSetStatsEntry 12 }

cbQosSetPrecedenceTunnelPkt64 OBJECT-TYPE
    SYNTAX --?? syntax is not convertable to SMIv1
           Counter
--  Units
--    Packets
    ACCESS read-only
    STATUS mandatory
    DESCRIPTION
        "The 64 bits count of packets whose Precedence Tunnel
        field is marked by Set feature."
    ::= { cbQosSetStatsEntry 13 }

cbQosPoliceColorStatsTable OBJECT-TYPE
    SYNTAX SEQUENCE OF CbQosPoliceColorStatsEntry
    ACCESS not-accessible
    STATUS mandatory
    DESCRIPTION
        "This table specifies Police Action related Statistical
        information for two rate color aware marker."
    ::= { cbQosPoliceColorStats 1 }

cbQosPoliceColorStatsEntry OBJECT-TYPE
    SYNTAX CbQosPoliceColorStatsEntry
    ACCESS not-accessible
    STATUS mandatory
    DESCRIPTION
        "Each entry in this table describes the statistical
        information about Police Action for Two Rate Color
        Aware Marker.
        
        This table contains statistical information only,
        no configuration information associated with it.
        Therefore, it is indexed by the instance specific IDs,
        such as cbQosPolicyIndex and cbQosObjectsIndex."
    INDEX { cbQosPolicyIndex, cbQosObjectsIndex }
    ::= { cbQosPoliceColorStatsTable 1 }

CbQosPoliceColorStatsEntry ::= SEQUENCE {
    cbQosPoliceCfmColorCfmPkt64 Counter,
    cbQosPoliceCfmColorCfmByte64 Counter,
    cbQosPoliceCfmColorExdPkt64 Counter,
    cbQosPoliceCfmColorExdByte64 Counter,
    cbQosPoliceCfmColorVltPkt64 Counter,
    cbQosPoliceCfmColorVltByte64 Counter,
    cbQosPoliceExdColorExdPkt64 Counter,
    cbQosPoliceExdColorExdByte64 Counter,
    cbQosPoliceExdColorVltPkt64 Counter,
    cbQosPoliceExdColorVltByte64 Counter,
    cbQosPoliceVltColorVltPkt64 Counter,
    cbQosPoliceVltColorVltByte64 Counter
    }

cbQosPoliceCfmColorCfmPkt64 OBJECT-TYPE
    SYNTAX --?? syntax is not convertable to SMIv1
           Counter
--  Units
--    Packets
    ACCESS read-only
    STATUS mandatory
    DESCRIPTION
        "The 64 bits count of packets which are marked as
        Conform-Color by previous node and treated as
        conforming by the policing feature on this node."
    ::= { cbQosPoliceColorStatsEntry 1 }

cbQosPoliceCfmColorCfmByte64 OBJECT-TYPE
    SYNTAX --?? syntax is not convertable to SMIv1
           Counter
--  Units
--    Octets
    ACCESS read-only
    STATUS mandatory
    DESCRIPTION
        "The 64 bits count of bytes which are marked as
        Conform-Color by previous node and treated as
        conforming by the policing feature on this node."
    ::= { cbQosPoliceColorStatsEntry 2 }

cbQosPoliceCfmColorExdPkt64 OBJECT-TYPE
    SYNTAX --?? syntax is not convertable to SMIv1
           Counter
--  Units
--    Packets
    ACCESS read-only
    STATUS mandatory
    DESCRIPTION
        "The 64 bits count of packets which are marked as
        Conform-Color by previous node and treated as
        exceeding by the policing feature on this node."
    ::= { cbQosPoliceColorStatsEntry 3 }

cbQosPoliceCfmColorExdByte64 OBJECT-TYPE
    SYNTAX --?? syntax is not convertable to SMIv1
           Counter
--  Units
--    Octets
    ACCESS read-only
    STATUS mandatory
    DESCRIPTION
        "The 64 bits count of bytes which are marked as
        Conform-Color by previous node and treated as
        exceeding by the policing feature on this node."
    ::= { cbQosPoliceColorStatsEntry 4 }

cbQosPoliceCfmColorVltPkt64 OBJECT-TYPE
    SYNTAX --?? syntax is not convertable to SMIv1
           Counter
--  Units
--    Packets
    ACCESS read-only
    STATUS mandatory
    DESCRIPTION
        "The 64 bits count of packets which are marked as
        Conform-Color by previous node and treated as
        violating by the policing feature on this node."
    ::= { cbQosPoliceColorStatsEntry 5 }

cbQosPoliceCfmColorVltByte64 OBJECT-TYPE
    SYNTAX --?? syntax is not convertable to SMIv1
           Counter
--  Units
--    Octets
    ACCESS read-only
    STATUS mandatory
    DESCRIPTION
        "The 64 bits count of bytes which are marked as
        Conform-Color by previous node and treated as
        violating by the policing feature on this node."
    ::= { cbQosPoliceColorStatsEntry 6 }

cbQosPoliceExdColorExdPkt64 OBJECT-TYPE
    SYNTAX --?? syntax is not convertable to SMIv1
           Counter
--  Units
--    Packets
    ACCESS read-only
    STATUS mandatory
    DESCRIPTION
        "The 64 bits count of packets which are marked as
        Exceed-Color by previous node and treated as
        exceeding by the policing feature on this node."
    ::= { cbQosPoliceColorStatsEntry 7 }

cbQosPoliceExdColorExdByte64 OBJECT-TYPE
    SYNTAX --?? syntax is not convertable to SMIv1
           Counter
--  Units
--    Octets
    ACCESS read-only
    STATUS mandatory
    DESCRIPTION
        "The 64 bits count of bytes which are marked as
        Exceed-Color by previous node and treated as
        exceeding by the policing feature on this node."
    ::= { cbQosPoliceColorStatsEntry 8 }

cbQosPoliceExdColorVltPkt64 OBJECT-TYPE
    SYNTAX --?? syntax is not convertable to SMIv1
           Counter
--  Units
--    Packets
    ACCESS read-only
    STATUS mandatory
    DESCRIPTION
        "The 64 bits count of packets which are marked as
        Exceed-Color by previous node and treated as
        violating by the policing feature on this node."
    ::= { cbQosPoliceColorStatsEntry 9 }

cbQosPoliceExdColorVltByte64 OBJECT-TYPE
    SYNTAX --?? syntax is not convertable to SMIv1
           Counter
--  Units
--    Octets
    ACCESS read-only
    STATUS mandatory
    DESCRIPTION
        "The 64 bits count of bytes which are marked as
        Exceed-Color by previous node and treated as
        violating by the policing feature on this node."
    ::= { cbQosPoliceColorStatsEntry 10 }

cbQosPoliceVltColorVltPkt64 OBJECT-TYPE
    SYNTAX --?? syntax is not convertable to SMIv1
           Counter
--  Units
--    Packets
    ACCESS read-only
    STATUS mandatory
    DESCRIPTION
        "The 64 bits count of packets which are marked as
        Violate-Color by previous node and treated as
        violating by the policing feature on this node."
    ::= { cbQosPoliceColorStatsEntry 11 }

cbQosPoliceVltColorVltByte64 OBJECT-TYPE
    SYNTAX --?? syntax is not convertable to SMIv1
           Counter
--  Units
--    Octets
    ACCESS read-only
    STATUS mandatory
    DESCRIPTION
        "The 64 bits count of bytes which are marked as
        Violate-Color by previous node and treated as
        violating by the policing feature on this node."
    ::= { cbQosPoliceColorStatsEntry 12 }

cbQosTableMapCfgTable OBJECT-TYPE
    SYNTAX SEQUENCE OF CbQosTableMapCfgEntry
    ACCESS not-accessible
    STATUS mandatory
    DESCRIPTION
        "This table specifies Table Map basic configuration
        information."
    ::= { cbQosTableMapCfg 1 }

cbQosTableMapCfgEntry OBJECT-TYPE
    SYNTAX CbQosTableMapCfgEntry
    ACCESS not-accessible
    STATUS mandatory
    DESCRIPTION
        "Each entry in this table describes configuration
        information about a tablemap name, behavior and default
        value.  Each cbQosTableMapCfgName is a unique character
        string in QOS.  This table contains configuration
        information only, no statistics associated with it."
    INDEX { cbQosTableMapCfgIndex }
    ::= { cbQosTableMapCfgTable 1 }

CbQosTableMapCfgEntry ::= SEQUENCE {
    cbQosTableMapCfgIndex Gauge,
    cbQosTableMapCfgName DisplayString,
    cbQosTableMapCfgBehavior INTEGER,
    cbQosTableMapCfgDftValue Gauge
    }

cbQosTableMapCfgIndex OBJECT-TYPE
    SYNTAX Gauge
    ACCESS not-accessible
    STATUS mandatory
    DESCRIPTION
        "An arbitrary (system-assigned) index for tablemap."
    ::= { cbQosTableMapCfgEntry 1 }

cbQosTableMapCfgName OBJECT-TYPE
    SYNTAX DisplayString
--    Rsyntax OCTET STRING(SIZE(0..255))
    ACCESS read-only
    STATUS mandatory
    DESCRIPTION
        "Name of the tablemap."
    ::= { cbQosTableMapCfgEntry 2 }

cbQosTableMapCfgBehavior OBJECT-TYPE
    SYNTAX INTEGER {
        value(1),
        copy(2),
        ignore(3)
        }
    ACCESS read-only
    STATUS mandatory
    DESCRIPTION
        "The behavior of a tablemap.
        value(1)    Always set to-value to be a configurable
                    default value <0-99> which is defined in
                    cbQosTableMapCfgDftValue.
        
        copy(2)     Always copy from-value to to-value in case
                    the from-value is not found in the tablemap.
                    This is the default behavior for a tablemap.
        
        ignore(3)   Ignore to set to-value when from-value
                    is not found in the tablemap."
    ::= { cbQosTableMapCfgEntry 3 }

cbQosTableMapCfgDftValue OBJECT-TYPE
    SYNTAX Gauge(0..99)
    ACCESS read-only
    STATUS mandatory
    DESCRIPTION
        "The configurable default value used when
        cbQosTableMapCfgBehavior is value(1)."
    ::= { cbQosTableMapCfgEntry 4 }

cbQosTableMapValueCfgTable OBJECT-TYPE
    SYNTAX SEQUENCE OF CbQosTableMapValueCfgEntry
    ACCESS not-accessible
    STATUS mandatory
    DESCRIPTION
        "This table specifies the from-value to to-value
        conversion pairs for a tablemap."
    ::= { cbQosTableMapValueCfg 1 }

cbQosTableMapValueCfgEntry OBJECT-TYPE
    SYNTAX CbQosTableMapValueCfgEntry
    ACCESS not-accessible
    STATUS mandatory
    DESCRIPTION
        "Each entry in this table specifies a from-value to
        to-value conversion pair for a given tablemap.
        This table contains configuration information only,
        no statistics associated with it."
    INDEX { cbQosTableMapCfgIndex, cbQosTableMapValueCfgFrom }
    ::= { cbQosTableMapValueCfgTable 1 }

CbQosTableMapValueCfgEntry ::= SEQUENCE {
    cbQosTableMapValueCfgFrom Gauge,
    cbQosTableMapValueCfgTo Gauge
    }

cbQosTableMapValueCfgFrom OBJECT-TYPE
    SYNTAX Gauge
    ACCESS not-accessible
    STATUS mandatory
    DESCRIPTION
        "This is the from-value in the tablemap.  If
        cbQosTableMapCfgBehavior equals to either copy(2) or
        ignore(3), when the content in the from-type(e.g.,
        cbQosTMSetIpDscpFromType) equals to this value, the
        value in the to-type(e.g., IpDscp) will be set to
        cbQosTableMapValueCfgTo.  Each tablemap can configure
        multiple from-value/to-value pairs."
    ::= { cbQosTableMapValueCfgEntry 1 }

cbQosTableMapValueCfgTo OBJECT-TYPE
    SYNTAX Gauge
    ACCESS read-only
    STATUS mandatory
    DESCRIPTION
        "This is the to-value in the tablemap.  Its usage is
        described in cbQosTableMapValueCfgFrom."
    ::= { cbQosTableMapValueCfgEntry 2 }

cbQosTableMapSetCfgTable OBJECT-TYPE
    SYNTAX SEQUENCE OF CbQosTableMapSetCfgEntry
    ACCESS not-accessible
    STATUS mandatory
    DESCRIPTION
        "This table specifies enhanced packet marking
        configuration using a pre-defined tablemap."
    ::= { cbQosTableMapSetCfg 1 }

cbQosTableMapSetCfgEntry OBJECT-TYPE
    SYNTAX CbQosTableMapSetCfgEntry
    ACCESS not-accessible
    STATUS mandatory
    DESCRIPTION
        "Each entry in this table describes configuration
        information for an Enhanced Packet Marking Action.
        The enhanced packet marking action uses a pre-configured
        table-map to do the from-value to to-value conversion.
        The packet marking to-type and from-type relationship
        can be established by using the table-map.
        Following is an example:
        cbQosTMSetIpDscpFromType == qosGroup(3)
        cbQosTMSetIpDscpMapName == 'MyTableMap',
        it means that table-map 'MyTableMap' will be used to
        convert the QosGroup value and the converted value will
        be used to set IpDSCP.
        
        cbQosConfigIndex is drived directly from
        cbQosSetCfgTable to keep the 1-to-1 mapping between
        two tables.  This table contains configuration
        information only, no statistics associated with it."
    INDEX { cbQosConfigIndex }
    ::= { cbQosTableMapSetCfgTable 1 }

CbQosTableMapSetCfgEntry ::= SEQUENCE {
    cbQosTMSetIpDscpFromType CbQosTMSetType,
    cbQosTMSetIpDscpMapName DisplayString,
    cbQosTMSetIpPrecedenceFromType CbQosTMSetType,
    cbQosTMSetIpPrecedenceMapName DisplayString,
    cbQosTMSetQosGroupFromType CbQosTMSetType,
    cbQosTMSetQosGroupMapName DisplayString,
    cbQosTMSetL2CosFromType CbQosTMSetType,
    cbQosTMSetL2CosMapName DisplayString,
    cbQosTMSetMplsExpImpFromType CbQosTMSetType,
    cbQosTMSetMplsExpImpMapName DisplayString,
    cbQosTMSetMplsExpTopFromType CbQosTMSetType,
    cbQosTMSetMplsExpTopMapName DisplayString
    }

cbQosTMSetIpDscpFromType OBJECT-TYPE
    SYNTAX CbQosTMSetType
--    Rsyntax INTEGER {
--        ?? enum value of zero may cause problems
--        none(0),
--        ipDscp(1),
--        ipPrecedence(2),
--        qosGroup(3),
--        l2Cos(4),
--        mplsExpImp(5),
--        mplsExpTop(6)
--        }
    ACCESS read-only
    STATUS mandatory
    DESCRIPTION
        "The packet marking type whose value will be converted
        to a to-value based on a pre-configured table-map.  The
        to-value will then be used to set IpDSCP."
    ::= { cbQosTableMapSetCfgEntry 1 }

cbQosTMSetIpDscpMapName OBJECT-TYPE
    SYNTAX DisplayString
--    Rsyntax OCTET STRING(SIZE(0..255))
    ACCESS read-only
    STATUS mandatory
    DESCRIPTION
        "The name of a pre-configured table-map used to convert
        and set IpDSCP value."
    ::= { cbQosTableMapSetCfgEntry 2 }

cbQosTMSetIpPrecedenceFromType OBJECT-TYPE
    SYNTAX CbQosTMSetType
--    Rsyntax INTEGER {
--        ?? enum value of zero may cause problems
--        none(0),
--        ipDscp(1),
--        ipPrecedence(2),
--        qosGroup(3),
--        l2Cos(4),
--        mplsExpImp(5),
--        mplsExpTop(6)
--        }
    ACCESS read-only
    STATUS mandatory
    DESCRIPTION
        "The packet marking type whose value will be converted
        to a to-value based on a pre-configured table-map.  The
        to-value will then be used to set IpPrecedence."
    ::= { cbQosTableMapSetCfgEntry 3 }

cbQosTMSetIpPrecedenceMapName OBJECT-TYPE
    SYNTAX DisplayString
--    Rsyntax OCTET STRING(SIZE(0..255))
    ACCESS read-only
    STATUS mandatory
    DESCRIPTION
        "The name of a pre-configured table-map used to convert
        and set IpPrecedence value."
    ::= { cbQosTableMapSetCfgEntry 4 }

cbQosTMSetQosGroupFromType OBJECT-TYPE
    SYNTAX CbQosTMSetType
--    Rsyntax INTEGER {
--        ?? enum value of zero may cause problems
--        none(0),
--        ipDscp(1),
--        ipPrecedence(2),
--        qosGroup(3),
--        l2Cos(4),
--        mplsExpImp(5),
--        mplsExpTop(6)
--        }
    ACCESS read-only
    STATUS mandatory
    DESCRIPTION
        "The packet marking type whose value will be converted
        to a to-value based on a pre-configured table-map.  The
        to-value will then be used to set QosGroup."
    ::= { cbQosTableMapSetCfgEntry 5 }

cbQosTMSetQosGroupMapName OBJECT-TYPE
    SYNTAX DisplayString
--    Rsyntax OCTET STRING(SIZE(0..255))
    ACCESS read-only
    STATUS mandatory
    DESCRIPTION
        "The name of a pre-configured table-map used to convert
        and set QosGroup value."
    ::= { cbQosTableMapSetCfgEntry 6 }

cbQosTMSetL2CosFromType OBJECT-TYPE
    SYNTAX CbQosTMSetType
--    Rsyntax INTEGER {
--        ?? enum value of zero may cause problems
--        none(0),
--        ipDscp(1),
--        ipPrecedence(2),
--        qosGroup(3),
--        l2Cos(4),
--        mplsExpImp(5),
--        mplsExpTop(6)
--        }
    ACCESS read-only
    STATUS mandatory
    DESCRIPTION
        "The packet marking type whose value will be converted
        to a to-value based on a pre-configured table-map.  The
        to-value will then be used to set L2Cos."
    ::= { cbQosTableMapSetCfgEntry 7 }

cbQosTMSetL2CosMapName OBJECT-TYPE
    SYNTAX DisplayString
--    Rsyntax OCTET STRING(SIZE(0..255))
    ACCESS read-only
    STATUS mandatory
    DESCRIPTION
        "The name of a pre-configured table-map used to convert
        and set L2Cos value."
    ::= { cbQosTableMapSetCfgEntry 8 }

cbQosTMSetMplsExpImpFromType OBJECT-TYPE
    SYNTAX CbQosTMSetType
--    Rsyntax INTEGER {
--        ?? enum value of zero may cause problems
--        none(0),
--        ipDscp(1),
--        ipPrecedence(2),
--        qosGroup(3),
--        l2Cos(4),
--        mplsExpImp(5),
--        mplsExpTop(6)
--        }
    ACCESS read-only
    STATUS mandatory
    DESCRIPTION
        "The packet marking type whose value will be converted
        to a to-value based on a pre-configured table-map.  The
        to-value will then be used to set MplsExpImposition."
    ::= { cbQosTableMapSetCfgEntry 9 }

cbQosTMSetMplsExpImpMapName OBJECT-TYPE
    SYNTAX DisplayString
--    Rsyntax OCTET STRING(SIZE(0..255))
    ACCESS read-only
    STATUS mandatory
    DESCRIPTION
        "The name of a pre-configured table-map used to convert
        and set MplsExpImposition value."
    ::= { cbQosTableMapSetCfgEntry 10 }

cbQosTMSetMplsExpTopFromType OBJECT-TYPE
    SYNTAX CbQosTMSetType
--    Rsyntax INTEGER {
--        ?? enum value of zero may cause problems
--        none(0),
--        ipDscp(1),
--        ipPrecedence(2),
--        qosGroup(3),
--        l2Cos(4),
--        mplsExpImp(5),
--        mplsExpTop(6)
--        }
    ACCESS read-only
    STATUS mandatory
    DESCRIPTION
        "The packet marking type whose value will be converted
        to a to-value based on a pre-configured table-map.  The
        to-value will then be used to set MplsExpTopMost."
    ::= { cbQosTableMapSetCfgEntry 11 }

cbQosTMSetMplsExpTopMapName OBJECT-TYPE
    SYNTAX DisplayString
--    Rsyntax OCTET STRING(SIZE(0..255))
    ACCESS read-only
    STATUS mandatory
    DESCRIPTION
        "The name of a pre-configured table-map used to convert
        and set MplsExpTopMost value."
    ::= { cbQosTableMapSetCfgEntry 12 }

cbQosEBCfgTable OBJECT-TYPE
    SYNTAX SEQUENCE OF CbQosEBCfgEntry
    ACCESS not-accessible
    STATUS mandatory
    DESCRIPTION
        "This table specifies Estimate Bandwidth related
        configuration information."
    ::= { cbQosEBCfg 1 }

cbQosEBCfgEntry OBJECT-TYPE
    SYNTAX CbQosEBCfgEntry
    ACCESS not-accessible
    STATUS mandatory
    DESCRIPTION
        "Each entry in this table describes configuration
        information about Estimate Bandwidth. It includes: 
        drop target, delay target and delay threshold.
        
        This table contains configuration information only.
        It is indexed by the cbQosConfigIndex."
    INDEX { cbQosConfigIndex }
    ::= { cbQosEBCfgTable 1 }

CbQosEBCfgEntry ::= SEQUENCE {
    cbQosEBCfgMechanism CbQosEBType,
    cbQosEBCfgDropTarget Gauge,
    cbQosEBCfgDelayTarget Gauge,
    cbQosEBCfgDelayThreshold Gauge
    }

cbQosEBCfgMechanism OBJECT-TYPE
    SYNTAX CbQosEBType
--    Rsyntax INTEGER {
--        ?? enum value of zero may cause problems
--        typeNone(0),
--        typeCorvil(1)
--        }
    ACCESS read-only
    STATUS mandatory
    DESCRIPTION
        "Bandwidth estimate algorithm type."
    ::= { cbQosEBCfgEntry 1 }

cbQosEBCfgDropTarget OBJECT-TYPE
    SYNTAX Gauge(50..1000000)
--  Units
--    packets
    ACCESS read-only
    STATUS mandatory
    DESCRIPTION
        "One-in-Number target indicating that no more than
        one packet in (this) number will be dropped."
    ::= { cbQosEBCfgEntry 2 }

cbQosEBCfgDelayTarget OBJECT-TYPE
    SYNTAX Gauge(50..1000000)
--  Units
--    packets
    ACCESS read-only
    STATUS mandatory
    DESCRIPTION
        "One-in-Number target indicating that no more than
        one packet in (this) number will exceed the delay 
        threshold specified by cbQosEBCfgDelayThreshold."
    ::= { cbQosEBCfgEntry 3 }

cbQosEBCfgDelayThreshold OBJECT-TYPE
    SYNTAX Gauge(16..1000)
--  Units
--    millisecond
    ACCESS read-only
    STATUS mandatory
    DESCRIPTION
        "The time in milliseconds for the delay threshold."
    ::= { cbQosEBCfgEntry 4 }

cbQosEBStatsTable OBJECT-TYPE
    SYNTAX SEQUENCE OF CbQosEBStatsEntry
    ACCESS not-accessible
    STATUS mandatory
    DESCRIPTION
        "This table specifies Estimate Bandwidth related
        statistical information."
    ::= { cbQosEBStats 1 }

cbQosEBStatsEntry OBJECT-TYPE
    SYNTAX CbQosEBStatsEntry
    ACCESS not-accessible
    STATUS mandatory
    DESCRIPTION
        "Each entry in this table describes Estimate Bandwidth
        related statistical information."
    INDEX { cbQosPolicyIndex, cbQosObjectsIndex }
    ::= { cbQosEBStatsTable 1 }

CbQosEBStatsEntry ::= SEQUENCE {
    cbQosEBStatsCorvilEBValue Gauge,
    cbQosEBStatsCorvilEBStatus TruthValue,
    cbQosEBStatsCorvilCTD CbQosEBCtd
    }

cbQosEBStatsCorvilEBValue OBJECT-TYPE
    SYNTAX Gauge
--  Units
--    kbps
    ACCESS read-only
    STATUS mandatory
    DESCRIPTION
        "The current Corvil EB bandwidth value."
    ::= { cbQosEBStatsEntry 1 }

cbQosEBStatsCorvilEBStatus OBJECT-TYPE
    SYNTAX TruthValue
--    Rsyntax INTEGER {
--        true(1),
--        false(2)
--        }
    ACCESS read-only
    STATUS mandatory
    DESCRIPTION
        "Boolean to indicate if Corvil EB is ready.
        true  - Bandwidth estimate is available.
        false - Bandwidth estimate is not available."
    ::= { cbQosEBStatsEntry 2 }

cbQosEBStatsCorvilCTD OBJECT-TYPE
    SYNTAX CbQosEBCtd
--    Rsyntax OCTET STRING
    ACCESS read-only
    STATUS mandatory
    DESCRIPTION
        "The Corvil CTD value defined by CbQosEBCtd."
    ::= { cbQosEBStatsEntry 3 }

cbQosServicePolicyGroup OBJECT IDENTIFIER ::= { ciscocbQosMIBGroups 1 }
-- OBJECT-GROUP
--  Status
--    deprecated
--  Descr
--    Required objects to provide CB QoS objects configuration
--    information.
--  objects
--    cbQosIfType, cbQosPolicyDirection, cbQosIfIndex, cbQosFrDLCI, 
--    cbQosAtmVPI, cbQosAtmVCI

cbQosInterfacePolicyGroup OBJECT IDENTIFIER ::= { ciscocbQosMIBGroups 2 }
-- OBJECT-GROUP
--  Status
--    mandatory
--  Descr
--    Required objects to provide CB QoS objects configuration
--    information.
--  objects
--    cbQosIFPolicyIndex

cbQosFrameRelayVCPolicyGroup OBJECT IDENTIFIER ::= { ciscocbQosMIBGroups 3 }
-- OBJECT-GROUP
--  Status
--    mandatory
--  Descr
--    Required objects to provide CB QoS objects configuration
--    information.
--  objects
--    cbQosFRPolicyIndex

cbQosATMPVCPolicyGroup OBJECT IDENTIFIER ::= { ciscocbQosMIBGroups 4 }
-- OBJECT-GROUP
--  Status
--    mandatory
--  Descr
--    Required objects to provide CB QoS objects configuration
--    information.
--  objects
--    cbQosATMPolicyIndex

cbQosObjectsGroup OBJECT IDENTIFIER ::= { ciscocbQosMIBGroups 5 }
-- OBJECT-GROUP
--  Status
--    mandatory
--  Descr
--    Required objects to provide CB QoS objects configuration
--    information.
--  objects
--    cbQosConfigIndex, cbQosObjectsType, cbQosParentObjectsIndex

cbQosPolicyMapCfgGroup OBJECT IDENTIFIER ::= { ciscocbQosMIBGroups 6 }
-- OBJECT-GROUP
--  Status
--    mandatory
--  Descr
--    Required objects to provide CB QoS objects configuration
--    information.
--  objects
--    cbQosPolicyMapName, cbQosPolicyMapDesc

cbQosClassMapCfgGroup OBJECT IDENTIFIER ::= { ciscocbQosMIBGroups 7 }
-- OBJECT-GROUP
--  Status
--    mandatory
--  Descr
--    Required objects to provide CB QoS objects configuration
--    information.
--  objects
--    cbQosCMName, cbQosCMDesc, cbQosCMInfo

cbQosMatchStmtCfgGroup OBJECT IDENTIFIER ::= { ciscocbQosMIBGroups 8 }
-- OBJECT-GROUP
--  Status
--    mandatory
--  Descr
--    Required objects to provide CB QoS objects configuration
--    information.
--  objects
--    cbQosMatchStmtName, cbQosMatchStmtInfo

cbQosQueueingCfgGroup OBJECT IDENTIFIER ::= { ciscocbQosMIBGroups 9 }
-- OBJECT-GROUP
--  Status
--    deprecated
--  Descr
--    Required objects to provide CB QoS objects configuration
--    information.
--  objects
--    cbQosQueueingCfgBandwidth, cbQosQueueingCfgBandwidthUnits, 
--    cbQosQueueingCfgFlowEnabled, cbQosQueueingCfgPriorityEnabled, 
--    cbQosQueueingCfgAggregateQSize, 
--    cbQosQueueingCfgIndividualQSize, 
--    cbQosQueueingCfgPrioBurstSize

cbQosREDCfgGroup OBJECT IDENTIFIER ::= { ciscocbQosMIBGroups 10 }
-- OBJECT-GROUP
--  Status
--    deprecated
--  Descr
--    Required objects to provide CB QoS objects configuration
--    information.
--  objects
--    cbQosREDCfgExponWeight, cbQosREDCfgMeanQsize

cbQosREDClassCfgGroup OBJECT IDENTIFIER ::= { ciscocbQosMIBGroups 11 }
-- OBJECT-GROUP
--  Status
--    deprecated
--  Descr
--    Required objects to provide CB QoS objects configuration
--    information.
--  objects
--    cbQosREDCfgMinThreshold, cbQosREDCfgMaxThreshold, 
--    cbQosREDCfgPktDropProb

cbQosPoliceCfgGroup OBJECT IDENTIFIER ::= { ciscocbQosMIBGroups 12 }
-- OBJECT-GROUP
--  Status
--    deprecated
--  Descr
--    Required objects to provide CB QoS objects configuration
--    information.
--  objects
--    cbQosPoliceCfgRate, cbQosPoliceCfgBurstSize, 
--    cbQosPoliceCfgExtBurstSize, cbQosPoliceCfgConformAction, 
--    cbQosPoliceCfgConformSetValue, cbQosPoliceCfgExceedAction, 
--    cbQosPoliceCfgExceedSetValue, cbQosPoliceCfgPir

cbQosTSCfgGroup OBJECT IDENTIFIER ::= { ciscocbQosMIBGroups 13 }
-- OBJECT-GROUP
--  Status
--    mandatory
--  Descr
--    Required objects to provide CB QoS objects configuration
--    information.
--  objects
--    cbQosTSCfgRate, cbQosTSCfgBurstSize, cbQosTSCfgExtBurstSize, 
--    cbQosTSCfgAdaptiveEnabled, cbQosTSCfgAdaptiveRate, 
--    cbQosTSCfgLimitType

cbQosSetCfgGroup OBJECT IDENTIFIER ::= { ciscocbQosMIBGroups 14 }
-- OBJECT-GROUP
--  Status
--    deprecated
--  Descr
--    Required objects to provide CB QoS objects configuration
--    information.
--  objects
--    cbQosSetCfgFeature, cbQosSetCfgIpDSCPValue, 
--    cbQosSetCfgIpPrecedenceValue, cbQosSetCfgQosGroupValue, 
--    cbQosSetCfgL2CosValue, cbQosSetCfgMplsExpValue, 
--    cbQosSetCfgDiscardClassValue

cbQosClassMapStatsGroup OBJECT IDENTIFIER ::= { ciscocbQosMIBGroups 15 }
-- OBJECT-GROUP
--  Status
--    mandatory
--  Descr
--    Required objects to provide CB QoS objects configuration
--    information.
--  objects
--    cbQosCMPrePolicyPktOverflow, cbQosCMPrePolicyPkt, 
--    cbQosCMPrePolicyPkt64, cbQosCMPrePolicyByteOverflow, 
--    cbQosCMPrePolicyByte, cbQosCMPrePolicyByte64, 
--    cbQosCMPrePolicyBitRate, cbQosCMPostPolicyByteOverflow, 
--    cbQosCMPostPolicyByte, cbQosCMPostPolicyByte64, 
--    cbQosCMPostPolicyBitRate, cbQosCMDropPktOverflow, 
--    cbQosCMDropPkt, cbQosCMDropPkt64, cbQosCMDropByteOverflow, 
--    cbQosCMDropByte, cbQosCMDropByte64, cbQosCMDropBitRate

cbQosNoBufferDropGroup OBJECT IDENTIFIER ::= { ciscocbQosMIBGroups 16 }
-- OBJECT-GROUP
--  Status
--    mandatory
--  Descr
--    Optional objects to provide CB QoS summary statistics.
--  objects
--    cbQosCMNoBufDropPktOverflow, cbQosCMNoBufDropPkt, 
--    cbQosCMNoBufDropPkt64

cbQosQueueingDynamicQNumberGroup OBJECT IDENTIFIER ::= { ciscocbQosMIBGroups 17 }
-- OBJECT-GROUP
--  Status
--    mandatory
--  Descr
--    Optional objects to provide CB QoS Queueing information.
--  objects
--    cbQosQueueingCfgDynamicQNumber

cbQosTrafficShapingDelayCountersGroup OBJECT IDENTIFIER ::= { ciscocbQosMIBGroups 18 }
-- OBJECT-GROUP
--  Status
--    mandatory
--  Descr
--    Optional objects to provide CB QoS traffic-shaping
--    information.
--  objects
--    cbQosTSStatsDelayedByteOverflow, cbQosTSStatsDelayedByte, 
--    cbQosTSStatsDelayedByte64, cbQosTSStatsDelayedPktOverflow, 
--    cbQosTSStatsDelayedPkt, cbQosTSStatsDelayedPkt64, 
--    cbQosTSStatsActive

cbQosMatchStmtStatsGroup OBJECT IDENTIFIER ::= { ciscocbQosMIBGroups 19 }
-- OBJECT-GROUP
--  Status
--    mandatory
--  Descr
--    Required objects to provide CB QoS objects configuration
--    information.
--  objects
--    cbQosMatchPrePolicyPktOverflow, cbQosMatchPrePolicyPkt, 
--    cbQosMatchPrePolicyPkt64, cbQosMatchPrePolicyByteOverflow, 
--    cbQosMatchPrePolicyByte, cbQosMatchPrePolicyByte64, 
--    cbQosMatchPrePolicyBitRate

cbQosPoliceStatsGroup OBJECT IDENTIFIER ::= { ciscocbQosMIBGroups 20 }
-- OBJECT-GROUP
--  Status
--    mandatory
--  Descr
--    Required objects to provide CB QoS objects configuration
--    information.
--  objects
--    cbQosPoliceConformedPktOverflow, cbQosPoliceConformedPkt, 
--    cbQosPoliceConformedPkt64, cbQosPoliceConformedByteOverflow, 
--    cbQosPoliceConformedByte, cbQosPoliceConformedByte64, 
--    cbQosPoliceConformedBitRate, cbQosPoliceExceededPktOverflow, 
--    cbQosPoliceExceededPkt, cbQosPoliceExceededPkt64, 
--    cbQosPoliceExceededByteOverflow, cbQosPoliceExceededByte, 
--    cbQosPoliceExceededByte64, cbQosPoliceExceededBitRate

cbQosQueueingStatsGroup OBJECT IDENTIFIER ::= { ciscocbQosMIBGroups 21 }
-- OBJECT-GROUP
--  Status
--    mandatory
--  Descr
--    Required objects to provide CB QoS objects configuration
--    information.
--  objects
--    cbQosQueueingCurrentQDepth, cbQosQueueingMaxQDepth, 
--    cbQosQueueingDiscardByteOverflow, cbQosQueueingDiscardByte, 
--    cbQosQueueingDiscardByte64, cbQosQueueingDiscardPktOverflow, 
--    cbQosQueueingDiscardPkt, cbQosQueueingDiscardPkt64

cbQosTSStatsGroup OBJECT IDENTIFIER ::= { ciscocbQosMIBGroups 22 }
-- OBJECT-GROUP
--  Status
--    mandatory
--  Descr
--    Required objects to provide CB QoS objects configuration
--    information.
--  objects
--    cbQosTSStatsDropByteOverflow, cbQosTSStatsDropByte, 
--    cbQosTSStatsDropByte64, cbQosTSStatsDropPktOverflow, 
--    cbQosTSStatsDropPkt, cbQosTSStatsDropPkt64, 
--    cbQosTSStatsCurrentQSize

cbQosREDClassStatsGroup OBJECT IDENTIFIER ::= { ciscocbQosMIBGroups 23 }
-- OBJECT-GROUP
--  Status
--    mandatory
--  Descr
--    Required objects to provide CB QoS objects configuration
--    information.
--  objects
--    cbQosREDRandomDropPktOverflow, cbQosREDRandomDropPkt, 
--    cbQosREDRandomDropPkt64, cbQosREDRandomDropByteOverflow, 
--    cbQosREDRandomDropByte, cbQosREDRandomDropByte64, 
--    cbQosREDTailDropPktOverflow, cbQosREDTailDropPkt, 
--    cbQosREDTailDropPkt64, cbQosREDTailDropByteOverflow, 
--    cbQosREDTailDropByte, cbQosREDTailDropByte64, 
--    cbQosREDMeanQSizeUnits, cbQosREDMeanQSize

cbQosREDClassXmitCountersGroup OBJECT IDENTIFIER ::= { ciscocbQosMIBGroups 24 }
-- OBJECT-GROUP
--  Status
--    mandatory
--  Descr
--    Optional objects to provide CB QoS objects configuration
--    information.
--  objects
--    cbQosREDTransmitPktOverflow, cbQosREDTransmitPkt, 
--    cbQosREDTransmitPkt64, cbQosREDTransmitByteOverflow, 
--    cbQosREDTransmitByte, cbQosREDTransmitByte64

cbQosAFPoliceStatsGroup OBJECT IDENTIFIER ::= { ciscocbQosMIBGroups 25 }
-- OBJECT-GROUP
--  Status
--    mandatory
--  Descr
--    Optional objects to provide CB QoS objects configuration
--    information.
--  objects
--    cbQosPoliceViolatedPktOverflow, cbQosPoliceViolatedPkt, 
--    cbQosPoliceViolatedPkt64, cbQosPoliceViolatedByteOverflow, 
--    cbQosPoliceViolatedByte, cbQosPoliceViolatedByte64, 
--    cbQosPoliceViolatedBitRate

cbQosAFPoliceCfgGroup OBJECT IDENTIFIER ::= { ciscocbQosMIBGroups 26 }
-- OBJECT-GROUP
--  Status
--    deprecated
--  Descr
--    Optional objects to provide CB QoS objects configuration
--    information.
--  objects
--    cbQosPoliceCfgViolateAction, cbQosPoliceCfgViolateSetValue

cbQosREDDscpCfgGroup OBJECT IDENTIFIER ::= { ciscocbQosMIBGroups 27 }
-- OBJECT-GROUP
--  Status
--    mandatory
--  Descr
--    Required objects to provide CB QoS objects configuration
--    information.
--  objects
--    cbQosREDCfgDscpPrec

cbQosNewSetCfgGroup OBJECT IDENTIFIER ::= { ciscocbQosMIBGroups 28 }
-- OBJECT-GROUP
--  Status
--    mandatory
--  Descr
--    Optional objects to provide CB QoS objects configuration
--    information.
--  objects
--    cbQosSetCfgL2CosValue

cbQosQueueingCfgGroupRev1 OBJECT IDENTIFIER ::= { ciscocbQosMIBGroups 29 }
-- OBJECT-GROUP
--  Status
--    mandatory
--  Descr
--    Required objects to provide CB QoS objects configuration
--    information.
--  objects
--    cbQosQueueingCfgBandwidth, cbQosQueueingCfgBandwidthUnits, 
--    cbQosQueueingCfgFlowEnabled, cbQosQueueingCfgPriorityEnabled, 
--    cbQosQueueingCfgIndividualQSize, 
--    cbQosQueueingCfgPrioBurstSize, cbQosQueueingCfgQLimitUnits, 
--    cbQosQueueingCfgAggregateQLimit

cbQosREDCfgGroupRev1 OBJECT IDENTIFIER ::= { ciscocbQosMIBGroups 30 }
-- OBJECT-GROUP
--  Status
--    mandatory
--  Descr
--    Required objects to provide CB QoS objects configuration
--    information.
--  objects
--    cbQosREDCfgExponWeight

cbQosREDClassCfgGroupRev1 OBJECT IDENTIFIER ::= { ciscocbQosMIBGroups 31 }
-- OBJECT-GROUP
--  Status
--    mandatory
--  Descr
--    Required objects to provide CB QoS objects configuration
--    information.
--  objects
--    cbQosREDCfgPktDropProb, cbQosREDClassCfgThresholdUnit, 
--    cbQosREDClassCfgMinThreshold, cbQosREDClassCfgMaxThreshold

cbQosPoliceCfgGroupRev1 OBJECT IDENTIFIER ::= { ciscocbQosMIBGroups 32 }
-- OBJECT-GROUP
--  Status
--    deprecated
--  Descr
--    Required objects to provide CB QoS objects configuration
--    information.
--  objects
--    cbQosPoliceCfgRate, cbQosPoliceCfgBurstSize, 
--    cbQosPoliceCfgExtBurstSize, cbQosPoliceCfgPir

cbQosPoliceActionCfgGroup OBJECT IDENTIFIER ::= { ciscocbQosMIBGroups 33 }
-- OBJECT-GROUP
--  Status
--    mandatory
--  Descr
--    Required objects to provide CB QoS objects configuration
--    information.
--  objects
--    cbQosPoliceActionCfgConform, 
--    cbQosPoliceActionCfgConformSetValue, 
--    cbQosPoliceActionCfgExceed, 
--    cbQosPoliceActionCfgExceedSetValue

cbQosAFPoliceViolateCfgGroup OBJECT IDENTIFIER ::= { ciscocbQosMIBGroups 34 }
-- OBJECT-GROUP
--  Status
--    mandatory
--  Descr
--    Optional objects to provide CB QoS objects configuration
--    information.
--  objects
--    cbQosPoliceActionCfgViolate, 
--    cbQosPoliceActionCfgViolateSetValue

cbQosREDECNCfgGroup OBJECT IDENTIFIER ::= { ciscocbQosMIBGroups 35 }
-- OBJECT-GROUP
--  Status
--    mandatory
--  Descr
--    Optional objects to provide CB QoS objects configuration
--    information.
--  objects
--    cbQosREDCfgECNEnabled

cbQosREDClassECNMarkCountersGroup OBJECT IDENTIFIER ::= { ciscocbQosMIBGroups 36 }
-- OBJECT-GROUP
--  Status
--    mandatory
--  Descr
--    Optional objects to provide CB QoS objects configuration
--    information.
--  objects
--    cbQosREDECNMarkPktOverflow, cbQosREDECNMarkPkt, 
--    cbQosREDECNMarkPkt64, cbQosREDECNMarkByteOverflow, 
--    cbQosREDECNMarkByte, cbQosREDECNMarkByte64

cbQosPoliceCfgExtGroup OBJECT IDENTIFIER ::= { ciscocbQosMIBGroups 37 }
-- OBJECT-GROUP
--  Status
--    mandatory
--  Descr
--    Optional objects to provide the information of the
--    committed policing rate that is greater than the
--    maximum value reportable by cbQosPoliceCfgRate.
--  objects
--    cbQosPoliceCfgRate64

cbQosSetCfgGroupRev1 OBJECT IDENTIFIER ::= { ciscocbQosMIBGroups 38 }
-- OBJECT-GROUP
--  Status
--    mandatory
--  Descr
--    Required objects to provide CB QoS objects configuration
--    information for SET/Marking feature.
--  objects
--    cbQosSetCfgFeature, cbQosSetCfgIpDSCPValue, 
--    cbQosSetCfgIpPrecedenceValue, cbQosSetCfgQosGroupValue

cbQosSetCfgMplsImpositionGroup OBJECT IDENTIFIER ::= { ciscocbQosMIBGroups 39 }
-- OBJECT-GROUP
--  Status
--    mandatory
--  Descr
--    Optional object to provide CB QoS objects configuration
--    information for SET/Marking feature.
--  objects
--    cbQosSetCfgMplsExpValue

cbQosSetCfgDiscardClassGroup OBJECT IDENTIFIER ::= { ciscocbQosMIBGroups 40 }
-- OBJECT-GROUP
--  Status
--    mandatory
--  Descr
--    Optional object to provide CB QoS objects configuration
--    information for SET/Marking feature.
--  objects
--    cbQosSetCfgDiscardClassValue

cbQosSetCfgMPLSTopMostGroup OBJECT IDENTIFIER ::= { ciscocbQosMIBGroups 41 }
-- OBJECT-GROUP
--  Status
--    mandatory
--  Descr
--    Optional object to provide CB QoS objects configuration
--    information for SET/Marking feature.
--  objects
--    cbQosSetCfgMplsExpTopMostValue

cbQosPoliceCfgGroupRev2 OBJECT IDENTIFIER ::= { ciscocbQosMIBGroups 42 }
-- OBJECT-GROUP
--  Status
--    mandatory
--  Descr
--    Required objects to provide CB QoS objects configuration
--    information for POLICE feature.
--  objects
--    cbQosPoliceCfgRate, cbQosPoliceCfgBurstSize, 
--    cbQosPoliceCfgExtBurstSize

cbQosPoliceCfgPirGroup OBJECT IDENTIFIER ::= { ciscocbQosMIBGroups 43 }
-- OBJECT-GROUP
--  Status
--    mandatory
--  Descr
--    Optional objects to provide CB QoS policing PIR rate.
--  objects
--    cbQosPoliceCfgPir

cbQosPoliceCfgPercentGroup OBJECT IDENTIFIER ::= { ciscocbQosMIBGroups 44 }
-- OBJECT-GROUP
--  Status
--    mandatory
--  Descr
--    Optional objects to provide CB QoS policing CIR and PIR
--    rates in percentage.
--  objects
--    cbQosPoliceCfgRateType, cbQosPoliceCfgPercentRateValue, 
--    cbQosPoliceCfgPercentPirValue

cbQosTSCfgPercentGroup OBJECT IDENTIFIER ::= { ciscocbQosMIBGroups 45 }
-- OBJECT-GROUP
--  Status
--    mandatory
--  Descr
--    Optional objects to provide CB QoS committed
--    traffic-shaping rate in percentage.
--  objects
--    cbQosTSCfgRateType, cbQosTSCfgPercentRateValue

cbQosIPHCCfgGroup OBJECT IDENTIFIER ::= { ciscocbQosMIBGroups 46 }
-- OBJECT-GROUP
--  Status
--    mandatory
--  Descr
--    Optional object to provide CB QoS IP header compression
--    configuration information.
--  objects
--    cbQosIPHCCfgOption

cbQosIPHCStatsGroup OBJECT IDENTIFIER ::= { ciscocbQosMIBGroups 47 }
-- OBJECT-GROUP
--  Status
--    mandatory
--  Descr
--    Optional objects to provide CB QoS IP header compression
--    statistic information.
--  objects
--    cbQosIPHCRtpSentPktOverflow, cbQosIPHCRtpSentPkt, 
--    cbQosIPHCRtpSentPkt64, cbQosIPHCRtpCmprsOutPktOverflow, 
--    cbQosIPHCRtpCmprsOutPkt, cbQosIPHCRtpCmprsOutPkt64, 
--    cbQosIPHCRtpSavedByteOverflow, cbQosIPHCRtpSavedByte, 
--    cbQosIPHCRtpSavedByte64, cbQosIPHCRtpSentByteOverflow, 
--    cbQosIPHCRtpSentByte, cbQosIPHCRtpSentByte64, 
--    cbQosIPHCRtpSentByteRate, cbQosIPHCTcpSentPktOverflow, 
--    cbQosIPHCTcpSentPkt, cbQosIPHCTcpSentPkt64, 
--    cbQosIPHCTcpCmprsOutPktOverflow, cbQosIPHCTcpCmprsOutPkt, 
--    cbQosIPHCTcpCmprsOutPkt64, cbQosIPHCTcpSavedByteOverflow, 
--    cbQosIPHCTcpSavedByte, cbQosIPHCTcpSavedByte64, 
--    cbQosIPHCTcpSentByteOverflow, cbQosIPHCTcpSentByte, 
--    cbQosIPHCTcpSentByte64, cbQosIPHCTcpSentByteRate

cbQosServicePolicyGroupRev1 OBJECT IDENTIFIER ::= { ciscocbQosMIBGroups 48 }
-- OBJECT-GROUP
--  Status
--    mandatory
--  Descr
--    Required objects to provide CB QoS objects configuration
--    information. This group deprecates 
--    cbQosServicePolicyGroup.
--  objects
--    cbQosIfType, cbQosPolicyDirection, cbQosIfIndex, cbQosFrDLCI, 
--    cbQosAtmVPI, cbQosAtmVCI, cbQosEntityIndex

cbQosQueueingCfgQLimitTimeGroup OBJECT IDENTIFIER ::= { ciscocbQosMIBGroups 49 }
-- OBJECT-GROUP
--  Status
--    mandatory
--  Descr
--    Optional object to provide Aggregate Queue time based
--    Limit configuration information.
--  objects
--    cbQosQueueingCfgAggrQLimitTime

cbQosREDCfgThresholdTimeGroup OBJECT IDENTIFIER ::= { ciscocbQosMIBGroups 50 }
-- OBJECT-GROUP
--  Status
--    mandatory
--  Descr
--    Optional objects to provide WRED time based threshold
--    Limit configuration information.
--  objects
--    cbQosREDClassCfgMinThresholdTime, 
--    cbQosREDClassCfgMaxThresholdTime

cbQosPoliceCfgCellGroup OBJECT IDENTIFIER ::= { ciscocbQosMIBGroups 51 }
-- OBJECT-GROUP
--  Status
--    mandatory
--  Descr
--    Optional objects to provide CB QoS policing cell based
--    rate configuration information.
--  objects
--    cbQosPoliceCfgCellRate, cbQosPoliceCfgCellPir, 
--    cbQosPoliceCfgBurstCell, cbQosPoliceCfgExtBurstCell

cbQosPoliceCfgTimeGroup OBJECT IDENTIFIER ::= { ciscocbQosMIBGroups 52 }
-- OBJECT-GROUP
--  Status
--    mandatory
--  Descr
--    Optional objects to provide CB QoS policing time based
--    burst size configuration information.
--  objects
--    cbQosPoliceCfgBurstTime, cbQosPoliceCfgExtBurstTime

cbQosPoliceCfgCdvtGroup OBJECT IDENTIFIER ::= { ciscocbQosMIBGroups 53 }
-- OBJECT-GROUP
--  Status
--    mandatory
--  Descr
--    Optional objects to provide CB QoS policing ATM CDVT
--    configuration information.
--  objects
--    cbQosPoliceCfgCdvt

cbQosPoliceCfgColorGroup OBJECT IDENTIFIER ::= { ciscocbQosMIBGroups 54 }
-- OBJECT-GROUP
--  Status
--    mandatory
--  Descr
--    Optional objects to provide CB QoS policing color aware
--    configuration information.
--  objects
--    cbQosPoliceCfgConformColor, cbQosPoliceCfgExceedColor

cbQosTSCfgTimeGroup OBJECT IDENTIFIER ::= { ciscocbQosMIBGroups 55 }
-- OBJECT-GROUP
--  Status
--    mandatory
--  Descr
--    Optional objects to provide CB QoS traffic-shaping
--    time based burst size configuration information.
--  objects
--    cbQosTSCfgBurstTime, cbQosTSCfgExtBurstTime

cbQosSetCfgSrpPriorityGroup OBJECT IDENTIFIER ::= { ciscocbQosMIBGroups 56 }
-- OBJECT-GROUP
--  Status
--    mandatory
--  Descr
--    Optional object to provide CB QoS SET SRP Priority
--    configuration information.
--  objects
--    cbQosSetCfgSrpPriority

cbQosSetCfgFrFecnBecnGroup OBJECT IDENTIFIER ::= { ciscocbQosMIBGroups 57 }
-- OBJECT-GROUP
--  Status
--    mandatory
--  Descr
--    Optional object to provide CB QoS SET Frame Relay
--    FECN BECN configuration information.
--  objects
--    cbQosSetCfgFrFecnBecn

cbQosSetStatsGroup OBJECT IDENTIFIER ::= { ciscocbQosMIBGroups 58 }
-- OBJECT-GROUP
--  Status
--    mandatory
--  Descr
--    Optional objects to provide CB QoS SET statistical
--    information.
--  objects
--    cbQosSetDscpPkt64, cbQosSetPrecedencePkt64, 
--    cbQosSetQosGroupPkt64, cbQosSetFrDePkt64, cbQosSetAtmClpPkt64, 
--    cbQosSetL2CosPkt64, cbQosSetMplsExpImpositionPkt64, 
--    cbQosSetDiscardClassPkt64, cbQosSetMplsExpTopMostPkt64, 
--    cbQosSetSrpPriorityPkt64, cbQosSetFrFecnBecnPkt64, 
--    cbQosSetDscpTunnelPkt64, cbQosSetPrecedenceTunnelPkt64

cbQosPoliceColorStatsGroup OBJECT IDENTIFIER ::= { ciscocbQosMIBGroups 59 }
-- OBJECT-GROUP
--  Status
--    mandatory
--  Descr
--    Optional objects to provide CB QoS Assured Forwarding
--    Policing Color Aware statistical information.
--  objects
--    cbQosPoliceCfmColorCfmPkt64, cbQosPoliceCfmColorCfmByte64, 
--    cbQosPoliceCfmColorExdPkt64, cbQosPoliceCfmColorExdByte64, 
--    cbQosPoliceCfmColorVltPkt64, cbQosPoliceCfmColorVltByte64, 
--    cbQosPoliceExdColorExdPkt64, cbQosPoliceExdColorExdByte64, 
--    cbQosPoliceExdColorVltPkt64, cbQosPoliceExdColorVltByte64, 
--    cbQosPoliceVltColorVltPkt64, cbQosPoliceVltColorVltByte64

cbQosTableMapCfgGroup OBJECT IDENTIFIER ::= { ciscocbQosMIBGroups 60 }
-- OBJECT-GROUP
--  Status
--    mandatory
--  Descr
--    Optional objects to provide CB QoS Enhanced Packet
--    Marking configuration information.
--  objects
--    cbQosTableMapCfgName, cbQosTableMapCfgBehavior, 
--    cbQosTableMapCfgDftValue, cbQosTableMapValueCfgTo, 
--    cbQosTMSetIpDscpFromType, cbQosTMSetIpDscpMapName, 
--    cbQosTMSetIpPrecedenceFromType, cbQosTMSetIpPrecedenceMapName, 
--    cbQosTMSetQosGroupFromType, cbQosTMSetQosGroupMapName, 
--    cbQosTMSetL2CosFromType, cbQosTMSetL2CosMapName, 
--    cbQosTMSetMplsExpImpFromType, cbQosTMSetMplsExpImpMapName, 
--    cbQosTMSetMplsExpTopFromType, cbQosTMSetMplsExpTopMapName

cbQosEBCfgGroup OBJECT IDENTIFIER ::= { ciscocbQosMIBGroups 61 }
-- OBJECT-GROUP
--  Status
--    mandatory
--  Descr
--    Optional objects to provide Estimate Bandwidth
--    configuration information.
--  objects
--    cbQosEBCfgMechanism, cbQosEBCfgDropTarget, 
--    cbQosEBCfgDelayTarget, cbQosEBCfgDelayThreshold

cbQosEBStatsGroup OBJECT IDENTIFIER ::= { ciscocbQosMIBGroups 62 }
-- OBJECT-GROUP
--  Status
--    mandatory
--  Descr
--    Optional objects to provide Estimate Bandwidth
--    status information.
--  objects
--    cbQosEBStatsCorvilEBValue, cbQosEBStatsCorvilEBStatus, 
--    cbQosEBStatsCorvilCTD

cbQosServicePolicyExtGroup OBJECT IDENTIFIER ::= { ciscocbQosMIBGroups 63 }
-- OBJECT-GROUP
--  Status
--    mandatory
--  Descr
--    Optional objects to provide more information about a
--    particular service policy instance.
--  objects
--    cbQosVlanIndex

cbQosMeasureIPSLACfgGroup OBJECT IDENTIFIER ::= { ciscocbQosMIBGroups 64 }
-- OBJECT-GROUP
--  Status
--    mandatory
--  Descr
--    Optional objects to configure IPSLA measure action.
--  objects
--    cbQosMeasureIPSLACfgGroupIndex, cbQosMeasureIPSLACfgGroupName

cbQosTSCfgExtGroup OBJECT IDENTIFIER ::= { ciscocbQosMIBGroups 65 }
-- OBJECT-GROUP
--  Status
--    mandatory
--  Descr
--    Objects to provide the information of the
--    committed shaping rate that is greater than the
--    maximum value reportable by cbQosTSCfgRate.
--  objects
--    cbQosTSCfgRate64

ciscocbQosMIBCompliance OBJECT IDENTIFIER ::= { ciscocbQosMIBCompliances 1 }
-- MODULE-COMPLIANCE
--  Status
--    deprecated
--  Descr
--    The compliance statement for entities that implement
--    class-based QoS on a Cisco router.
--  Module
--    >>current<<
--   MandGroup
--    cbQosServicePolicyGroup
--   MandGroup
--    cbQosObjectsGroup
--   MandGroup
--    cbQosPolicyMapCfgGroup
--   MandGroup
--    cbQosClassMapCfgGroup
--   MandGroup
--    cbQosMatchStmtCfgGroup
--   MandGroup
--    cbQosQueueingCfgGroup
--   MandGroup
--    cbQosREDCfgGroup
--   MandGroup
--    cbQosREDClassCfgGroup
--   MandGroup
--    cbQosPoliceCfgGroup
--   MandGroup
--    cbQosTSCfgGroup
--   MandGroup
--    cbQosSetCfgGroup
--   MandGroup
--    cbQosClassMapStatsGroup
--   MandGroup
--    cbQosMatchStmtStatsGroup
--   MandGroup
--    cbQosPoliceStatsGroup
--   MandGroup
--    cbQosQueueingStatsGroup
--   MandGroup
--    cbQosTSStatsGroup
--   MandGroup
--    cbQosREDClassStatsGroup
--   OptGroup
--    cbQosInterfacePolicyGroup
--   OptGroup
--    cbQosFrameRelayVCPolicyGroup
--   OptGroup
--    cbQosATMPVCPolicyGroup
--   OptGroup
--    cbQosNoBufferDropGroup
--   OptGroup
--    cbQosQueueingDynamicQNumberGroup
--   OptGroup
--    cbQosTrafficShapingDelayCountersGroup

ciscocbQosMIBComplianceRev1 OBJECT IDENTIFIER ::= { ciscocbQosMIBCompliances 2 }
-- MODULE-COMPLIANCE
--  Status
--    deprecated
--  Descr
--    The compliance statement for entities that implement
--    class-based QoS on a Cisco router. This compliance module
--    deprecates ciscocbQosMIBCompliance.
--  Module
--    >>current<<
--   MandGroup
--    cbQosServicePolicyGroup
--   MandGroup
--    cbQosObjectsGroup
--   MandGroup
--    cbQosPolicyMapCfgGroup
--   MandGroup
--    cbQosClassMapCfgGroup
--   MandGroup
--    cbQosMatchStmtCfgGroup
--   MandGroup
--    cbQosQueueingCfgGroupRev1
--   MandGroup
--    cbQosREDCfgGroupRev1
--   MandGroup
--    cbQosREDClassCfgGroupRev1
--   MandGroup
--    cbQosPoliceCfgGroupRev1
--   MandGroup
--    cbQosTSCfgGroup
--   MandGroup
--    cbQosSetCfgGroup
--   MandGroup
--    cbQosClassMapStatsGroup
--   MandGroup
--    cbQosMatchStmtStatsGroup
--   MandGroup
--    cbQosPoliceStatsGroup
--   MandGroup
--    cbQosQueueingStatsGroup
--   MandGroup
--    cbQosTSStatsGroup
--   MandGroup
--    cbQosREDClassStatsGroup
--   OptGroup
--    cbQosInterfacePolicyGroup
--   OptGroup
--    cbQosFrameRelayVCPolicyGroup
--   OptGroup
--    cbQosATMPVCPolicyGroup
--   OptGroup
--    cbQosNoBufferDropGroup
--   OptGroup
--    cbQosQueueingDynamicQNumberGroup
--   OptGroup
--    cbQosTrafficShapingDelayCountersGroup

ciscocbQosMIBComplianceRev2 OBJECT IDENTIFIER ::= { ciscocbQosMIBCompliances 3 }
-- MODULE-COMPLIANCE
--  Status
--    deprecated
--  Descr
--    The compliance statement for entities that implement
--    class-based QoS on a Cisco router. This compliance module
--    deprecates ciscocbQosMIBComplianceRev1.
--  Module
--    >>current<<
--   MandGroup
--    cbQosServicePolicyGroup
--   MandGroup
--    cbQosObjectsGroup
--   MandGroup
--    cbQosPolicyMapCfgGroup
--   MandGroup
--    cbQosClassMapCfgGroup
--   MandGroup
--    cbQosMatchStmtCfgGroup
--   MandGroup
--    cbQosQueueingCfgGroupRev1
--   MandGroup
--    cbQosREDCfgGroupRev1
--   MandGroup
--    cbQosREDClassCfgGroupRev1
--   MandGroup
--    cbQosPoliceCfgGroupRev2
--   MandGroup
--    cbQosTSCfgGroup
--   MandGroup
--    cbQosSetCfgGroupRev1
--   MandGroup
--    cbQosClassMapStatsGroup
--   MandGroup
--    cbQosMatchStmtStatsGroup
--   MandGroup
--    cbQosPoliceStatsGroup
--   MandGroup
--    cbQosQueueingStatsGroup
--   MandGroup
--    cbQosTSStatsGroup
--   MandGroup
--    cbQosREDClassStatsGroup
--   OptGroup
--    cbQosInterfacePolicyGroup
--   OptGroup
--    cbQosFrameRelayVCPolicyGroup
--   OptGroup
--    cbQosATMPVCPolicyGroup
--   OptGroup
--    cbQosNoBufferDropGroup
--   OptGroup
--    cbQosQueueingDynamicQNumberGroup
--   OptGroup
--    cbQosREDClassXmitCountersGroup
--   OptGroup
--    cbQosREDECNCfgGroup
--   OptGroup
--    cbQosREDClassECNMarkCountersGroup
--   OptGroup
--    cbQosAFPoliceStatsGroup
--   OptGroup
--    cbQosPoliceCfgPirGroup
--   OptGroup
--    cbQosPoliceCfgExtGroup
--   OptGroup
--    cbQosPoliceActionCfgGroup
--   OptGroup
--    cbQosAFPoliceViolateCfgGroup
--   OptGroup
--    cbQosPoliceCfgPercentGroup
--   OptGroup
--    cbQosTrafficShapingDelayCountersGroup
--   OptGroup
--    cbQosTSCfgPercentGroup
--   OptGroup
--    cbQosNewSetCfgGroup
--   OptGroup
--    cbQosSetCfgMplsImpositionGroup
--   OptGroup
--    cbQosSetCfgDiscardClassGroup
--   OptGroup
--    cbQosSetCfgMPLSTopMostGroup
--   OptGroup
--    cbQosIPHCCfgGroup
--   OptGroup
--    cbQosIPHCStatsGroup

ciscocbQosMIBComplianceRev3 OBJECT IDENTIFIER ::= { ciscocbQosMIBCompliances 4 }
-- MODULE-COMPLIANCE
--  Status
--    mandatory
--  Descr
--    The compliance statement for entities that implement
--    class-based QoS on a Cisco router. This compliance module
--    deprecates ciscocbQosMIBComplianceRev2.
--  Module
--    >>current<<
--   MandGroup
--    cbQosServicePolicyGroupRev1
--   MandGroup
--    cbQosObjectsGroup
--   MandGroup
--    cbQosPolicyMapCfgGroup
--   MandGroup
--    cbQosClassMapCfgGroup
--   MandGroup
--    cbQosMatchStmtCfgGroup
--   MandGroup
--    cbQosQueueingCfgGroupRev1
--   MandGroup
--    cbQosREDDscpCfgGroup
--   MandGroup
--    cbQosREDCfgGroupRev1
--   MandGroup
--    cbQosREDClassCfgGroupRev1
--   MandGroup
--    cbQosPoliceCfgGroupRev2
--   MandGroup
--    cbQosTSCfgGroup
--   MandGroup
--    cbQosSetCfgGroupRev1
--   MandGroup
--    cbQosClassMapStatsGroup
--   MandGroup
--    cbQosMatchStmtStatsGroup
--   MandGroup
--    cbQosPoliceStatsGroup
--   MandGroup
--    cbQosQueueingStatsGroup
--   MandGroup
--    cbQosTSStatsGroup
--   MandGroup
--    cbQosREDClassStatsGroup
--   OptGroup
--    cbQosInterfacePolicyGroup
--   OptGroup
--    cbQosFrameRelayVCPolicyGroup
--   OptGroup
--    cbQosATMPVCPolicyGroup
--   OptGroup
--    cbQosNoBufferDropGroup
--   OptGroup
--    cbQosQueueingDynamicQNumberGroup
--   OptGroup
--    cbQosREDClassXmitCountersGroup
--   OptGroup
--    cbQosREDECNCfgGroup
--   OptGroup
--    cbQosREDClassECNMarkCountersGroup
--   OptGroup
--    cbQosAFPoliceStatsGroup
--   OptGroup
--    cbQosPoliceCfgPirGroup
--   OptGroup
--    cbQosPoliceCfgExtGroup
--   OptGroup
--    cbQosPoliceActionCfgGroup
--   OptGroup
--    cbQosAFPoliceViolateCfgGroup
--   OptGroup
--    cbQosPoliceCfgPercentGroup
--   OptGroup
--    cbQosTrafficShapingDelayCountersGroup
--   OptGroup
--    cbQosTSCfgPercentGroup
--   OptGroup
--    cbQosNewSetCfgGroup
--   OptGroup
--    cbQosSetCfgMplsImpositionGroup
--   OptGroup
--    cbQosSetCfgDiscardClassGroup
--   OptGroup
--    cbQosSetCfgMPLSTopMostGroup
--   OptGroup
--    cbQosIPHCCfgGroup
--   OptGroup
--    cbQosIPHCStatsGroup
--   OptGroup
--    cbQosQueueingCfgQLimitTimeGroup
--   OptGroup
--    cbQosREDCfgThresholdTimeGroup
--   OptGroup
--    cbQosPoliceCfgCellGroup
--   OptGroup
--    cbQosPoliceCfgTimeGroup
--   OptGroup
--    cbQosPoliceCfgCdvtGroup
--   OptGroup
--    cbQosPoliceCfgColorGroup
--   OptGroup
--    cbQosTSCfgTimeGroup
--   OptGroup
--    cbQosSetCfgSrpPriorityGroup
--   OptGroup
--    cbQosSetCfgFrFecnBecnGroup
--   OptGroup
--    cbQosSetStatsGroup
--   OptGroup
--    cbQosPoliceColorStatsGroup
--   OptGroup
--    cbQosTableMapCfgGroup
--   OptGroup
--    cbQosEBCfgGroup
--   OptGroup
--    cbQosEBStatsGroup

ciscocbQosMIBComplianceRev4 OBJECT IDENTIFIER ::= { ciscocbQosMIBCompliances 5 }
-- MODULE-COMPLIANCE
--  Status
--    deprecated
--  Descr
--    The compliance statement for entities that implement
--    class-based QoS on a Cisco router. This compliance module
--    deprecates ciscocbQosMIBComplianceRev2.
--  Module
--    >>current<<
--   MandGroup
--    cbQosServicePolicyGroupRev1
--   MandGroup
--    cbQosObjectsGroup
--   MandGroup
--    cbQosPolicyMapCfgGroup
--   MandGroup
--    cbQosClassMapCfgGroup
--   MandGroup
--    cbQosMatchStmtCfgGroup
--   MandGroup
--    cbQosQueueingCfgGroupRev1
--   MandGroup
--    cbQosREDDscpCfgGroup
--   MandGroup
--    cbQosREDCfgGroupRev1
--   MandGroup
--    cbQosREDClassCfgGroupRev1
--   MandGroup
--    cbQosPoliceCfgGroupRev2
--   MandGroup
--    cbQosTSCfgGroup
--   MandGroup
--    cbQosSetCfgGroupRev1
--   MandGroup
--    cbQosClassMapStatsGroup
--   MandGroup
--    cbQosMatchStmtStatsGroup
--   MandGroup
--    cbQosPoliceStatsGroup
--   MandGroup
--    cbQosQueueingStatsGroup
--   MandGroup
--    cbQosTSStatsGroup
--   MandGroup
--    cbQosREDClassStatsGroup
--   OptGroup
--    cbQosInterfacePolicyGroup
--   OptGroup
--    cbQosFrameRelayVCPolicyGroup
--   OptGroup
--    cbQosATMPVCPolicyGroup
--   OptGroup
--    cbQosNoBufferDropGroup
--   OptGroup
--    cbQosQueueingDynamicQNumberGroup
--   OptGroup
--    cbQosREDClassXmitCountersGroup
--   OptGroup
--    cbQosREDECNCfgGroup
--   OptGroup
--    cbQosREDClassECNMarkCountersGroup
--   OptGroup
--    cbQosAFPoliceStatsGroup
--   OptGroup
--    cbQosPoliceCfgPirGroup
--   OptGroup
--    cbQosPoliceCfgExtGroup
--   OptGroup
--    cbQosPoliceActionCfgGroup
--   OptGroup
--    cbQosAFPoliceViolateCfgGroup
--   OptGroup
--    cbQosPoliceCfgPercentGroup
--   OptGroup
--    cbQosTrafficShapingDelayCountersGroup
--   OptGroup
--    cbQosTSCfgPercentGroup
--   OptGroup
--    cbQosNewSetCfgGroup
--   OptGroup
--    cbQosSetCfgMplsImpositionGroup
--   OptGroup
--    cbQosSetCfgDiscardClassGroup
--   OptGroup
--    cbQosSetCfgMPLSTopMostGroup
--   OptGroup
--    cbQosIPHCCfgGroup
--   OptGroup
--    cbQosIPHCStatsGroup
--   OptGroup
--    cbQosQueueingCfgQLimitTimeGroup
--   OptGroup
--    cbQosREDCfgThresholdTimeGroup
--   OptGroup
--    cbQosPoliceCfgCellGroup
--   OptGroup
--    cbQosPoliceCfgTimeGroup
--   OptGroup
--    cbQosPoliceCfgCdvtGroup
--   OptGroup
--    cbQosPoliceCfgColorGroup
--   OptGroup
--    cbQosTSCfgTimeGroup
--   OptGroup
--    cbQosSetCfgSrpPriorityGroup
--   OptGroup
--    cbQosSetCfgFrFecnBecnGroup
--   OptGroup
--    cbQosSetStatsGroup
--   OptGroup
--    cbQosPoliceColorStatsGroup
--   OptGroup
--    cbQosTableMapCfgGroup
--   OptGroup
--    cbQosEBCfgGroup
--   OptGroup
--    cbQosEBStatsGroup
--   OptGroup
--    cbQosMeasureIPSLACfgGroup

ciscocbQosMIBComplianceRev5 OBJECT IDENTIFIER ::= { ciscocbQosMIBCompliances 6 }
-- MODULE-COMPLIANCE
--  Status
--    deprecated
--  Descr
--    The compliance statement for entities that implement
--    class-based QoS on a Cisco router. This compliance module
--    deprecates ciscocbQosMIBComplianceRev4.
--  Module
--    >>current<<
--   MandGroup
--    cbQosServicePolicyGroupRev1
--   MandGroup
--    cbQosObjectsGroup
--   MandGroup
--    cbQosPolicyMapCfgGroup
--   MandGroup
--    cbQosClassMapCfgGroup
--   MandGroup
--    cbQosMatchStmtCfgGroup
--   MandGroup
--    cbQosQueueingCfgGroupRev1
--   MandGroup
--    cbQosREDDscpCfgGroup
--   MandGroup
--    cbQosREDCfgGroupRev1
--   MandGroup
--    cbQosREDClassCfgGroupRev1
--   MandGroup
--    cbQosPoliceCfgGroupRev2
--   MandGroup
--    cbQosTSCfgGroup
--   MandGroup
--    cbQosSetCfgGroupRev1
--   MandGroup
--    cbQosClassMapStatsGroup
--   MandGroup
--    cbQosMatchStmtStatsGroup
--   MandGroup
--    cbQosPoliceStatsGroup
--   MandGroup
--    cbQosQueueingStatsGroup
--   MandGroup
--    cbQosTSStatsGroup
--   MandGroup
--    cbQosREDClassStatsGroup
--   OptGroup
--    cbQosInterfacePolicyGroup
--   OptGroup
--    cbQosFrameRelayVCPolicyGroup
--   OptGroup
--    cbQosATMPVCPolicyGroup
--   OptGroup
--    cbQosNoBufferDropGroup
--   OptGroup
--    cbQosQueueingDynamicQNumberGroup
--   OptGroup
--    cbQosREDClassXmitCountersGroup
--   OptGroup
--    cbQosREDECNCfgGroup
--   OptGroup
--    cbQosREDClassECNMarkCountersGroup
--   OptGroup
--    cbQosAFPoliceStatsGroup
--   OptGroup
--    cbQosPoliceCfgPirGroup
--   OptGroup
--    cbQosPoliceCfgExtGroup
--   OptGroup
--    cbQosPoliceActionCfgGroup
--   OptGroup
--    cbQosAFPoliceViolateCfgGroup
--   OptGroup
--    cbQosPoliceCfgPercentGroup
--   OptGroup
--    cbQosTrafficShapingDelayCountersGroup
--   OptGroup
--    cbQosTSCfgPercentGroup
--   OptGroup
--    cbQosNewSetCfgGroup
--   OptGroup
--    cbQosSetCfgMplsImpositionGroup
--   OptGroup
--    cbQosSetCfgDiscardClassGroup
--   OptGroup
--    cbQosSetCfgMPLSTopMostGroup
--   OptGroup
--    cbQosIPHCCfgGroup
--   OptGroup
--    cbQosIPHCStatsGroup
--   OptGroup
--    cbQosQueueingCfgQLimitTimeGroup
--   OptGroup
--    cbQosREDCfgThresholdTimeGroup
--   OptGroup
--    cbQosPoliceCfgCellGroup
--   OptGroup
--    cbQosPoliceCfgTimeGroup
--   OptGroup
--    cbQosPoliceCfgCdvtGroup
--   OptGroup
--    cbQosPoliceCfgColorGroup
--   OptGroup
--    cbQosTSCfgTimeGroup
--   OptGroup
--    cbQosSetCfgSrpPriorityGroup
--   OptGroup
--    cbQosSetCfgFrFecnBecnGroup
--   OptGroup
--    cbQosSetStatsGroup
--   OptGroup
--    cbQosPoliceColorStatsGroup
--   OptGroup
--    cbQosTableMapCfgGroup
--   OptGroup
--    cbQosEBCfgGroup
--   OptGroup
--    cbQosEBStatsGroup
--   OptGroup
--    cbQosMeasureIPSLACfgGroup
--   OptGroup
--    cbQosTSCfgExtGroup


END
