INFORMANT-OS DEFINITIONS ::= BEGIN

IMPORTS
    MODULE-IDENTITY, OBJECT-IDENTITY, OBJECT-TYPE, Gauge32, Integer32, Counter64
        FROM SNMPv2-SMI
    DateAndTime, TruthValue
        FROM SNMPv2-TC
    informant,WtcsDisplayString
        FROM WTCS;

wmiOperatingSystem MODULE-IDENTITY
    LAST-UPDATED "200912110102Z"
    ORGANIZATION "Informant Systems, Inc."
    CONTACT-INFO
            "Garth Williams
             11135-23A Ave
             Edmonton, AB  T6J4W5  Canada
             Tel: +1 780 434 4113
             E-mail: garth.williams@wtcs.org"
    DESCRIPTION
            "The MIB module for informant operating system WMI entities."
    REVISION      "200912110102Z"
    DESCRIPTION
            "Added OID 999 which gives the version of this
             agent."
    REVISION      "200708312129Z"
    DESCRIPTION
            "Modified ospsKernelModeTime, ospsOtherOperationCount,
             ospsOtherTransferCount, ospsReadOperationCount,
             ospsReadTransferCount, ospsUserModeTime, ospsWriteOperationCount,
             ospsWriteTransferCount, ostdElapsedTime, ostdKernelModeTime,
             ostdUserModeTime to be Counter64 rather than WtcsDisplayString."
    REVISION      "200706052228Z"
    DESCRIPTION
            "Added new Win32_ComputerSystem and Win32_WinSAT entries
             which are new to Windows Vista. Refer to
             http://www.microsoft.com/technet/scriptcenter/hubs/vista.mspx
             for more information on the new WMI objects in Vista."
    REVISION      "200605242227Z"
    DESCRIPTION
            "Added the wmiEventLog OID branch to status the Windows
            Event Log."
    REVISION      "200503191850Z"
    DESCRIPTION
            "Added the win32Shutdown and win32CreateProcess OIDs. These
            values can only be written to and cannot be read. Also
            modified the ossvcState so that the Windows service can be
            stopped, started, paused, and resumed through SNMP."
    REVISION      "200411032133Z"
    DESCRIPTION
            "The initial revision of this MIB module."
    ::= { informant 22 }

wmiDesktop OBJECT-IDENTITY
    STATUS     current
    DESCRIPTION
        "The Desktop subcategory groups classes that represent objects that
        define a specific desktop configuration."
    ::= { wmiOperatingSystem 1 }

win32DesktopTable OBJECT-TYPE
    SYNTAX     SEQUENCE OF Win32DesktopEntry
    MAX-ACCESS not-accessible
    STATUS     current
    DESCRIPTION
        "The Win32_Desktop WMI class represents the common characteristics
        of a user's desktop. The properties of this class can be modified
        by the user to customize the desktop."
    ::= { wmiDesktop 1 }

win32DesktopEntry OBJECT-TYPE
    SYNTAX     Win32DesktopEntry
    MAX-ACCESS not-accessible
    STATUS     current
    DESCRIPTION
        "None"
    INDEX      { osdtIndex }
    ::= { win32DesktopTable 1 }

Win32DesktopEntry ::= SEQUENCE {
    osdtIndex Integer32,
    osdtBorderWidth  Gauge32,
    osdtCaption  WtcsDisplayString,
    osdtCoolSwitch  TruthValue,
    osdtCursorBlinkRate  Gauge32,
    osdtDescription  WtcsDisplayString,
    osdtDragFullWindows  TruthValue,
    osdtGridGranularity  Gauge32,
    osdtIconSpacing  Gauge32,
    osdtIconTitleFaceName  WtcsDisplayString,
    osdtIconTitleSize  Gauge32,
    osdtIconTitleWrap  TruthValue,
    osdtName  WtcsDisplayString,
    osdtPattern  WtcsDisplayString,
    osdtScreenSaverActive  TruthValue,
    osdtScreenSaverExecutable  WtcsDisplayString,
    osdtScreenSaverSecure  TruthValue,
    osdtScreenSaverTimeout  Gauge32,
    osdtSettingID  WtcsDisplayString,
    osdtWallpaper  WtcsDisplayString,
    osdtWallpaperStretched  TruthValue,
    osdtWallpaperTiled  TruthValue
}

osdtIndex OBJECT-TYPE
    SYNTAX     Integer32 (1..2147483647)
    MAX-ACCESS read-only
    STATUS     current
    DESCRIPTION
        "The value of this object uniquely identifies the instance entry
        for this class."
    ::= { win32DesktopEntry 1 }

osdtBorderWidth  OBJECT-TYPE
    SYNTAX     Gauge32
    MAX-ACCESS read-only
    STATUS     current
    DESCRIPTION
        "Width of the borders around all windows with adjustable borders.
        Example: 3"
    ::= { win32DesktopEntry 2 }

osdtCaption  OBJECT-TYPE
    SYNTAX     WtcsDisplayString
    MAX-ACCESS read-only
    STATUS     current
    DESCRIPTION
        "Short description (one-line string) of the CIM_Setting object."
    ::= { win32DesktopEntry 3 }

osdtCoolSwitch  OBJECT-TYPE
    SYNTAX     TruthValue
    MAX-ACCESS read-only
    STATUS     current
    DESCRIPTION
        "Fast task switching is turned on. Fast task switching allows the
        user to switch between windows using the ALT+TAB keyboard
        combination."
    ::= { win32DesktopEntry 4 }

osdtCursorBlinkRate  OBJECT-TYPE
    SYNTAX     Gauge32
    UNITS "Milliseconds"
    MAX-ACCESS read-only
    STATUS     current
    DESCRIPTION
        "Length of time between successive cursor blinks.
        Example: 530"
    ::= { win32DesktopEntry 5 }

osdtDescription  OBJECT-TYPE
    SYNTAX     WtcsDisplayString
    MAX-ACCESS read-only
    STATUS     current
    DESCRIPTION
        "Description of the CIM_Setting object."
    ::= { win32DesktopEntry 6 }

osdtDragFullWindows  OBJECT-TYPE
    SYNTAX     TruthValue
    MAX-ACCESS read-only
    STATUS     current
    DESCRIPTION
        "Contents of a window are shown when a user moves the window."
    ::= { win32DesktopEntry 7 }

osdtGridGranularity  OBJECT-TYPE
    SYNTAX     Gauge32
    UNITS "8 Pixels"
    MAX-ACCESS read-only
    STATUS     current
    DESCRIPTION
        "Spacing of the grid that windows are bound to on the desktop. This
        makes organizing windows easier. The spacing is usually fine enough
        that the user does not notice it.
        Example: 1"
    ::= { win32DesktopEntry 8 }

osdtIconSpacing  OBJECT-TYPE
    SYNTAX     Gauge32
    UNITS "Pixels"
    MAX-ACCESS read-only
    STATUS     current
    DESCRIPTION
        "Spacing between icons.
        Example: 75"
    ::= { win32DesktopEntry 9 }

osdtIconTitleFaceName  OBJECT-TYPE
    SYNTAX     WtcsDisplayString
    MAX-ACCESS read-only
    STATUS     current
    DESCRIPTION
        "Font used for the names of the icons.
        Example: 'MS San Serif'"
    ::= { win32DesktopEntry 10 }

osdtIconTitleSize  OBJECT-TYPE
    SYNTAX     Gauge32
    UNITS "Point"
    MAX-ACCESS read-only
    STATUS     current
    DESCRIPTION
        "Icon font size.
        Example: 9"
    ::= { win32DesktopEntry 11 }

osdtIconTitleWrap  OBJECT-TYPE
    SYNTAX     TruthValue
    MAX-ACCESS read-only
    STATUS     current
    DESCRIPTION
        "Icon's title text wraps to the next line."
    ::= { win32DesktopEntry 12 }

osdtName  OBJECT-TYPE
    SYNTAX     WtcsDisplayString
    MAX-ACCESS read-only
    STATUS     current
    DESCRIPTION
        "Name that identifies the current desktop profile.
        Example: 'MainProf'"
    ::= { win32DesktopEntry 13 }

osdtPattern  OBJECT-TYPE
    SYNTAX     WtcsDisplayString
    MAX-ACCESS read-only
    STATUS     current
    DESCRIPTION
        "Name of the pattern used as the background for the desktop."
    ::= { win32DesktopEntry 14 }

osdtScreenSaverActive  OBJECT-TYPE
    SYNTAX     TruthValue
    MAX-ACCESS read-only
    STATUS     current
    DESCRIPTION
        "Screen saver is active."
    ::= { win32DesktopEntry 15 }

osdtScreenSaverExecutable  OBJECT-TYPE
    SYNTAX     WtcsDisplayString
    MAX-ACCESS read-only
    STATUS     current
    DESCRIPTION
        "Name of the current screen saver executable file.
        Example: 'LOGON.SCR'"
    ::= { win32DesktopEntry 16 }

osdtScreenSaverSecure  OBJECT-TYPE
    SYNTAX     TruthValue
    MAX-ACCESS read-only
    STATUS     current
    DESCRIPTION
        "Password is enabled for the screen saver."
    ::= { win32DesktopEntry 17 }

osdtScreenSaverTimeout  OBJECT-TYPE
    SYNTAX     Gauge32
    UNITS "Seconds"
    MAX-ACCESS read-only
    STATUS     current
    DESCRIPTION
        "Amount of time that passes before the screen saver starts."
    ::= { win32DesktopEntry 18 }

osdtSettingID  OBJECT-TYPE
    SYNTAX     WtcsDisplayString
    MAX-ACCESS read-only
    STATUS     current
    DESCRIPTION
        "Identifier by which the CIM_Setting object is known."
    ::= { win32DesktopEntry 19 }

osdtWallpaper  OBJECT-TYPE
    SYNTAX     WtcsDisplayString
    MAX-ACCESS read-only
    STATUS     current
    DESCRIPTION
        "File name for the wallpaper design on the background of the
        desktop.
        Example: 'WINNT.BMP'"
    ::= { win32DesktopEntry 20 }

osdtWallpaperStretched  OBJECT-TYPE
    SYNTAX     TruthValue
    MAX-ACCESS read-only
    STATUS     current
    DESCRIPTION
        "Wallpaper is stretched to fill the entire screen. Microsoft Plus!
        must be installed before this option is available. If FALSE, the
        wallpaper retains its original dimensions on the desktop
        background."
    ::= { win32DesktopEntry 21 }

osdtWallpaperTiled  OBJECT-TYPE
    SYNTAX     TruthValue
    MAX-ACCESS read-only
    STATUS     current
    DESCRIPTION
        "Wallpaper is tiled or centered."
    ::= { win32DesktopEntry 22 }

win32EnvironmentTable OBJECT-TYPE
    SYNTAX     SEQUENCE OF Win32EnvironmentEntry
    MAX-ACCESS not-accessible
    STATUS     current
    DESCRIPTION
        "The Win32_Environment WMI class represents an environment or
        system environment setting on a Windows computer system."
    ::= { wmiDesktop 2 }

win32EnvironmentEntry OBJECT-TYPE
    SYNTAX     Win32EnvironmentEntry
    MAX-ACCESS not-accessible
    STATUS     current
    DESCRIPTION
        "None"
    INDEX      { osevIndex }
    ::= { win32EnvironmentTable 1 }

Win32EnvironmentEntry ::= SEQUENCE {
    osevIndex Integer32,
    osevCaption  WtcsDisplayString,
    osevDescription  WtcsDisplayString,
    osevInstallDate  DateAndTime,
    osevName  WtcsDisplayString,
    osevStatus  INTEGER,
    osevSystemVariable  TruthValue,
    osevUserName  WtcsDisplayString,
    osevVariableValue  WtcsDisplayString
}

osevIndex OBJECT-TYPE
    SYNTAX     Integer32 (1..2147483647)
    MAX-ACCESS read-only
    STATUS     current
    DESCRIPTION
        "The value of this object uniquely identifies the instance entry
        for this class."
    ::= { win32EnvironmentEntry 1 }

osevCaption  OBJECT-TYPE
    SYNTAX     WtcsDisplayString
    MAX-ACCESS read-only
    STATUS     current
    DESCRIPTION
        "Short description (one-line string) of the object."
    ::= { win32EnvironmentEntry 2 }

osevDescription  OBJECT-TYPE
    SYNTAX     WtcsDisplayString
    MAX-ACCESS read-only
    STATUS     current
    DESCRIPTION
        "Description of the object."
    ::= { win32EnvironmentEntry 3 }

osevInstallDate  OBJECT-TYPE
    SYNTAX     DateAndTime
    MAX-ACCESS read-only
    STATUS     current
    DESCRIPTION
        "Object was installed. This property does not need a value to
        indicate that the object is installed."
    ::= { win32EnvironmentEntry 4 }

osevName  OBJECT-TYPE
    SYNTAX     WtcsDisplayString
    MAX-ACCESS read-only
    STATUS     current
    DESCRIPTION
        "Character string specifying the name of a Windows environment
        variable. By specifying the name of a variable that does not yet
        exist, an application creates a new environment variable.
        Example: 'Path'"
    ::= { win32EnvironmentEntry 5 }

osevStatus  OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is on-line,
        yet the managed element is neither 'OK' nor in one
        of the other states."
    ::= { win32EnvironmentEntry 6 }

osevSystemVariable  OBJECT-TYPE
    SYNTAX     TruthValue
    MAX-ACCESS read-only
    STATUS     current
    DESCRIPTION
        "Indicating whether the variable is a system
        variable. A system variable is set by the operating
        system, and is independent from user environment
        settings."
    ::= { win32EnvironmentEntry 7 }

osevUserName  OBJECT-TYPE
    SYNTAX     WtcsDisplayString (SIZE (0..260))
    MAX-ACCESS read-only
    STATUS     current
    DESCRIPTION
        "Name of the owner of the environment setting. It
        is set to <SYSTEM> for settings that are specific
        to the Windows system (as opposed to a specific
        user) and <DEFAULT> for default user settings.
        Example: 'Jsmith'"
    ::= { win32EnvironmentEntry 8 }

osevVariableValue  OBJECT-TYPE
    SYNTAX     WtcsDisplayString
    MAX-ACCESS read-only
    STATUS     current
    DESCRIPTION
        "Placeholder variable of a Windows environment
        variable. Information like the file system
        directory can change from computer to computer. The
        operating system substitutes placeholders for
        these.
        Example: '%SystemRoot%'"
    ::= { win32EnvironmentEntry 9 }

win32TimeZoneTable OBJECT-TYPE
    SYNTAX     SEQUENCE OF Win32TimeZoneEntry
    MAX-ACCESS not-accessible
    STATUS     current
    DESCRIPTION
        "The Win32_TimeZone WMI class represents the time
        zone information for a Windows system, which
        includes changes needed for the daylight saving
        time transition."
    ::= { wmiDesktop 3 }

win32TimeZoneEntry OBJECT-TYPE
    SYNTAX     Win32TimeZoneEntry
    MAX-ACCESS not-accessible
    STATUS     current
    DESCRIPTION
        "None"
    INDEX      { ostzIndex }
    ::= { win32TimeZoneTable 1 }

Win32TimeZoneEntry ::= SEQUENCE {
    ostzIndex Integer32,
    ostzBias  Integer32,
    ostzCaption  WtcsDisplayString,
    ostzDaylightBias  Integer32,
    ostzDaylightDay  Gauge32,
    ostzDaylightDayOfWeek  INTEGER,
    ostzDaylightHour  Gauge32,
    ostzDaylightMillisecond  Gauge32,
    ostzDaylightMinute  Gauge32,
    ostzDaylightMonth  INTEGER,
    ostzDaylightName  WtcsDisplayString,
    ostzDaylightSecond  Gauge32,
    ostzDaylightYear  Gauge32,
    ostzDescription  WtcsDisplayString,
    ostzSettingID  WtcsDisplayString,
    ostzStandardBias  Gauge32,
    ostzStandardDay  Gauge32,
    ostzStandardDayOfWeek  INTEGER,
    ostzStandardHour  Gauge32,
    ostzStandardMillisecond  Gauge32,
    ostzStandardMinute  Gauge32,
    ostzStandardMonth  INTEGER,
    ostzStandardName  WtcsDisplayString,
    ostzStandardSecond  Gauge32,
    ostzStandardYear  Gauge32
}

ostzIndex OBJECT-TYPE
    SYNTAX     Integer32 (1..2147483647)
    MAX-ACCESS read-only
    STATUS     current
    DESCRIPTION
        "The value of this object uniquely identifies the
        instance entry for this class."
    ::= { win32TimeZoneEntry 1 }

ostzBias  OBJECT-TYPE
    SYNTAX     Integer32
    UNITS "Minutes"
    MAX-ACCESS read-only
    STATUS     current
    DESCRIPTION
        "Current bias for local time translation. The bias
        is the difference between Universal Time Coordinate
        (UTC) and local time. All translations between UTC
        and local time are based on the following formula:
        UTC = local time + bias. This property is
        required."
    ::= { win32TimeZoneEntry 2 }

ostzCaption  OBJECT-TYPE
    SYNTAX     WtcsDisplayString
    MAX-ACCESS read-only
    STATUS     current
    DESCRIPTION
        "Short description of the CIM_Setting object a
        one-line string."
    ::= { win32TimeZoneEntry 3 }

ostzDaylightBias  OBJECT-TYPE
    SYNTAX     Integer32
    UNITS "Minutes"
    MAX-ACCESS read-only
    STATUS     current
    DESCRIPTION
        "Bias value to be used during local time
        translations that occur during daylight time. This
        property is ignored if a value for the DaylightDay
        property is not supplied. The value of this
        property is added to the Bias property to form the
        bias used during daylight time. In most time zones,
        the value of this property is -60."
    ::= { win32TimeZoneEntry 4 }

ostzDaylightDay  OBJECT-TYPE
    SYNTAX     Gauge32
    MAX-ACCESS read-only
    STATUS     current
    DESCRIPTION
        "DaylightDayOfWeek of the DaylightMonth when the
        transition from standard time to daylight saving
        time occurs on this operating system.
        Example: If the transition day (DaylightDayOfWeek)
        occurs on a Sunday then the value '1' indicates the
        first Sunday of the DaylightMonth, '2' indicates
        the second Sunday and so on. The value '5'
        indicates the last DaylightDayOfWeek in the month."
    ::= { win32TimeZoneEntry 5 }

ostzDaylightDayOfWeek  OBJECT-TYPE
    SYNTAX     INTEGER {
        sunday(1),
        monday(2),
        tuesday(3),
        wednesday(4),
        thursday(5),
        friday(6),
        saturday(7)
    }
    MAX-ACCESS read-only
    STATUS     current
    DESCRIPTION
        "Day of the week when the transition from standard
        time to daylight saving time occurs on an operating
        system."
    ::= { win32TimeZoneEntry 6 }

ostzDaylightHour  OBJECT-TYPE
    SYNTAX     Gauge32
    MAX-ACCESS read-only
    STATUS     current
    DESCRIPTION
        "Hour of the day when the transition from standard
        time to daylight saving time occurs on an operating
        system.
        Example: 2"
    ::= { win32TimeZoneEntry 7 }

ostzDaylightMillisecond  OBJECT-TYPE
    SYNTAX     Gauge32
    MAX-ACCESS read-only
    STATUS     current
    DESCRIPTION
        "Millisecond of the DaylightSecond when the
        transition from standard time to daylight saving
        time occurs on an operating system."
    ::= { win32TimeZoneEntry 8 }

ostzDaylightMinute  OBJECT-TYPE
    SYNTAX     Gauge32
    MAX-ACCESS read-only
    STATUS     current
    DESCRIPTION
        "Minute of the DaylightHour when the transition
        from standard time to daylight saving time occurs
        on an operating system.
        Example: 59"
    ::= { win32TimeZoneEntry 9 }

ostzDaylightMonth  OBJECT-TYPE
    SYNTAX     INTEGER {
        january(1),
        february(2),
        march(3),
        april(4),
        may(5),
        june(6),
        july(7),
        august(8),
        september(9),
        october(10),
        november(11),
        december(12)
    }
    MAX-ACCESS read-only
    STATUS     current
    DESCRIPTION
        "Month when the transition from standard time to
        daylight saving time occurs on an operating
        system."
    ::= { win32TimeZoneEntry 10 }

ostzDaylightName  OBJECT-TYPE
    SYNTAX     WtcsDisplayString (SIZE (0..256))
    MAX-ACCESS read-only
    STATUS     current
    DESCRIPTION
        "Time zone being represented when daylight saving
        time is in effect.
        Example: 'EDT' (Eastern Daylight Time)"
    ::= { win32TimeZoneEntry 11 }

ostzDaylightSecond  OBJECT-TYPE
    SYNTAX     Gauge32
    MAX-ACCESS read-only
    STATUS     current
    DESCRIPTION
        "Second of the DaylightMinute when the transition
        from standard time to daylight saving time occurs
        on an operating system.
        Example: 59"
    ::= { win32TimeZoneEntry 12 }

ostzDaylightYear  OBJECT-TYPE
    SYNTAX     Gauge32
    MAX-ACCESS read-only
    STATUS     current
    DESCRIPTION
        "Year when daylight saving time is in effect. This
        property is not required.
        Example: 1997"
    ::= { win32TimeZoneEntry 13 }

ostzDescription  OBJECT-TYPE
    SYNTAX     WtcsDisplayString
    MAX-ACCESS read-only
    STATUS     current
    DESCRIPTION
        "Description of the CIM_Setting object."
    ::= { win32TimeZoneEntry 14 }

ostzSettingID  OBJECT-TYPE
    SYNTAX     WtcsDisplayString
    MAX-ACCESS read-only
    STATUS     current
    DESCRIPTION
        "Identifier for the CIM_Setting object."
    ::= { win32TimeZoneEntry 15 }

ostzStandardBias  OBJECT-TYPE
    SYNTAX     Gauge32
    UNITS "Minutes"
    MAX-ACCESS read-only
    STATUS     current
    DESCRIPTION
        "Bias value to use when daylight saving time is not
        in effect. This property is ignored if a value for
        StandardDay is not supplied. The value of this
        property is added to the Bias property to form the
        bias during standard time.
        Example: 0"
    ::= { win32TimeZoneEntry 16 }

ostzStandardDay  OBJECT-TYPE
    SYNTAX     Gauge32
    MAX-ACCESS read-only
    STATUS     current
    DESCRIPTION
        "StandardDayOfWeek of the StandardMonth when the
        transition from daylight saving time to standard
        time occurs on an operating system.
        If the transition day (StandardDayOfWeek) occurs on
        a Sunday then the value '1' indicates the first
        Sunday of the StandardMonth, '2' indicates the
        second Sunday and so on. The value '5' indicates
        the last StandardDayOfWeek in the month."
    ::= { win32TimeZoneEntry 17 }

ostzStandardDayOfWeek  OBJECT-TYPE
    SYNTAX     INTEGER {
        sunday(1),
        monday(2),
        tuesday(3),
        wednesday(4),
        thursday(5),
        friday(6),
        saturday(7)
    }
    MAX-ACCESS read-only
    STATUS     current
    DESCRIPTION
        "Day of the week when the transition from daylight
        saving time to standard time occurs on an operating
        system."
    ::= { win32TimeZoneEntry 18 }

ostzStandardHour  OBJECT-TYPE
    SYNTAX     Gauge32
    MAX-ACCESS read-only
    STATUS     current
    DESCRIPTION
        "Hour of the day when the transition from daylight
        saving time to standard time occurs on an operating
        system.
        Example: 11"
    ::= { win32TimeZoneEntry 19 }

ostzStandardMillisecond  OBJECT-TYPE
    SYNTAX     Gauge32
    MAX-ACCESS read-only
    STATUS     current
    DESCRIPTION
        "Millisecond of the StandardSecond when the
        transition from daylight saving time to standard
        time occurs on an operating system."
    ::= { win32TimeZoneEntry 20 }

ostzStandardMinute  OBJECT-TYPE
    SYNTAX     Gauge32
    MAX-ACCESS read-only
    STATUS     current
    DESCRIPTION
        "Minute of the StandardDay when the transition from
        daylight saving time to standard time occurs on an
        operating system.
        Example: 59"
    ::= { win32TimeZoneEntry 21 }

ostzStandardMonth  OBJECT-TYPE
    SYNTAX     INTEGER {
        january(1),
        february(2),
        march(3),
        april(4),
        may(5),
        june(6),
        july(7),
        august(8),
        september(9),
        october(10),
        november(11),
        december(12)
    }
    MAX-ACCESS read-only
    STATUS     current
    DESCRIPTION
        "Month when the transition from daylight saving
        time to standard time occurs on an operating
        system."
    ::= { win32TimeZoneEntry 22 }

ostzStandardName  OBJECT-TYPE
    SYNTAX     WtcsDisplayString (SIZE (0..256))
    MAX-ACCESS read-only
    STATUS     current
    DESCRIPTION
        "Name of the time zone being represented when
        standard time is in effect.
        Example: 'EST' (Eastern Standard Time)"
    ::= { win32TimeZoneEntry 23 }

ostzStandardSecond  OBJECT-TYPE
    SYNTAX     Gauge32
    MAX-ACCESS read-only
    STATUS     current
    DESCRIPTION
        "Second of the StandardMinute when the transition
        from daylight saving time to standard time occurs
        on an operating system.
        Example: 59"
    ::= { win32TimeZoneEntry 24 }

ostzStandardYear  OBJECT-TYPE
    SYNTAX     Gauge32
    MAX-ACCESS read-only
    STATUS     current
    DESCRIPTION
        "Year when standard time is in effect. This
        property is not required.
        Example: 1997"
    ::= { win32TimeZoneEntry 25 }

wmiDrivers OBJECT-IDENTITY
    STATUS     current
    DESCRIPTION
        "The Drivers subcategory groups classes that
        represent virtual device drivers and system drivers
        for base services."
    ::= { wmiOperatingSystem 2 }

win32DriverVXDTable OBJECT-TYPE
    SYNTAX     SEQUENCE OF Win32DriverVXDEntry
    MAX-ACCESS not-accessible
    STATUS     current
    DESCRIPTION
        "The Win32_DriverVXD WMI class represents a virtual
        device driver on a Windows computer system. A
        virtual device is a program that manages a system
        resource (such as a hardware device or installed
        software) so that more than one application can use
        the resource at the same time. Windows uses virtual
        devices to allow multitasking for Windows-based
        applications. The virtual devices work in
        conjunction with Windows to process interrupts, and
        carry out I/O operations for a given application
        without disrupting the execution of other
        applications.
        
        Most virtual devices manage a hardware device and
        many also manage or replace corresponding software
        such as ROM BIOS routines. A virtual device can
        contain the device-specific code needed to carry
        out actions on the device or it can rely on the
        other software to carry out these operations. In
        all cases, the virtual device keeps track of the
        state of the device for each application and
        ensures that the device is in the correct state
        whenever an application continues execution.
        
        Some virtual devices manage only installed
        software, such as an MS-DOS device driver or a
        Terminate and Stay Resident (TSR) program. Such
        virtual devices often contain code that either
        emulates the software or ensures that the software
        uses data that applies only to the currently
        running application. Virtual devices are sometimes
        used to improve the performance of installed
        software; the Intel-compatible microprocessors can
        execute the 32-bit code of a virtual device more
        efficiently than the 16-bit code of an MS-DOS
        device driver or TSR."
    ::= { wmiDrivers 1 }

win32DriverVXDEntry OBJECT-TYPE
    SYNTAX     Win32DriverVXDEntry
    MAX-ACCESS not-accessible
    STATUS     current
    DESCRIPTION
        "None"
    INDEX      { osvxdIndex }
    ::= { win32DriverVXDTable 1 }

Win32DriverVXDEntry ::= SEQUENCE {
    osvxdIndex Integer32,
    osvxdBuildNumber  WtcsDisplayString,
    osvxdCaption  WtcsDisplayString,
    osvxdCodeSet  WtcsDisplayString,
    osvxdControl  WtcsDisplayString,
    osvxdDescription  WtcsDisplayString,
    osvxdDeviceDescriptorBlock  WtcsDisplayString,
    osvxdIdentificationCode  WtcsDisplayString,
    osvxdInstallDate  DateAndTime,
    osvxdLanguageEdition  WtcsDisplayString,
    osvxdManufacturer  WtcsDisplayString,
    osvxdName  WtcsDisplayString,
    osvxdOtherTargetOS  WtcsDisplayString,
    osvxdPMAPI  WtcsDisplayString,
    osvxdSerialNumber  WtcsDisplayString,
    osvxdServiceTableSize  Gauge32,
    osvxdSoftwareElementID  WtcsDisplayString,
    osvxdSoftwareElementState  INTEGER,
    osvxdStatus  INTEGER,
    osvxdTargetOperatingSystem  INTEGER,
    osvxdV86API  WtcsDisplayString,
    osvxdVersion  WtcsDisplayString
}

osvxdIndex OBJECT-TYPE
    SYNTAX     Integer32 (1..2147483647)
    MAX-ACCESS read-only
    STATUS     current
    DESCRIPTION
        "The value of this object uniquely identifies the
        instance entry for this class."
    ::= { win32DriverVXDEntry 1 }

osvxdBuildNumber  OBJECT-TYPE
    SYNTAX     WtcsDisplayString
    MAX-ACCESS read-only
    STATUS     current
    DESCRIPTION
        "Internal identifier for this compilation of this
        software element."
    ::= { win32DriverVXDEntry 2 }

osvxdCaption  OBJECT-TYPE
    SYNTAX     WtcsDisplayString
    MAX-ACCESS read-only
    STATUS     current
    DESCRIPTION
        "Short description (one-line string) of the
        object."
    ::= { win32DriverVXDEntry 3 }

osvxdCodeSet  OBJECT-TYPE
    SYNTAX     WtcsDisplayString
    MAX-ACCESS read-only
    STATUS     current
    DESCRIPTION
        "Code set used by this software element."
    ::= { win32DriverVXDEntry 4 }

osvxdControl  OBJECT-TYPE
    SYNTAX     WtcsDisplayString
    MAX-ACCESS read-only
    STATUS     current
    DESCRIPTION
        "Offset address to the driver's control procedures.
        The virtual machine manager calls this procedure to
        send control messages to the virtual device system.
        The system control messages direct the virtual
        device to carry out actions. An example of an
        action is initializing itself; another is notifying
        the virtual device of changes to virtual machines
        (such as a virtual machine is being created)."
    ::= { win32DriverVXDEntry 5 }

osvxdDescription  OBJECT-TYPE
    SYNTAX     WtcsDisplayString
    MAX-ACCESS read-only
    STATUS     current
    DESCRIPTION
        "Description of the object."
    ::= { win32DriverVXDEntry 6 }

osvxdDeviceDescriptorBlock  OBJECT-TYPE
    SYNTAX     WtcsDisplayString
    MAX-ACCESS read-only
    STATUS     current
    DESCRIPTION
        "Offset address to the device descriptor block
        (DDB) structure. The DDB contains information that
        the operating system uses to execute the procedures
        of the driver, including its location in the
        interrupt list, and other data to run and
        communicate with this VXD."
    ::= { win32DriverVXDEntry 7 }

osvxdIdentificationCode  OBJECT-TYPE
    SYNTAX     WtcsDisplayString
    MAX-ACCESS read-only
    STATUS     current
    DESCRIPTION
        "Manufacturer's identifier for this software
        element. Often this will be a stock-keeping unit
        (SKU) or a part number."
    ::= { win32DriverVXDEntry 8 }

osvxdInstallDate  OBJECT-TYPE
    SYNTAX     DateAndTime
    MAX-ACCESS read-only
    STATUS     current
    DESCRIPTION
        "Object was installed. This property does not need
        a value to indicate that the object is installed."
    ::= { win32DriverVXDEntry 9 }

osvxdLanguageEdition  OBJECT-TYPE
    SYNTAX     WtcsDisplayString
    MAX-ACCESS read-only
    STATUS     current
    DESCRIPTION
        "Language edition of this software element. The
        language codes defined in ISO 639 should be used.
        Where the software element represents multi-lingual
        or international version of a product, the string
        'multilingual' should be used."
    ::= { win32DriverVXDEntry 10 }

osvxdManufacturer  OBJECT-TYPE
    SYNTAX     WtcsDisplayString
    MAX-ACCESS read-only
    STATUS     current
    DESCRIPTION
        "Manufacturer of this software element."
    ::= { win32DriverVXDEntry 11 }

osvxdName  OBJECT-TYPE
    SYNTAX     WtcsDisplayString
    MAX-ACCESS read-only
    STATUS     current
    DESCRIPTION
        "Name used to identify this software element."
    ::= { win32DriverVXDEntry 12 }

osvxdOtherTargetOS  OBJECT-TYPE
    SYNTAX     WtcsDisplayString
    MAX-ACCESS read-only
    STATUS     current
    DESCRIPTION
        "Manufacturer and operating system type for a
        software element when the TargetOperatingSystem
        property has a value of 1 (Other). Therefore, when
        the TargetOperatingSystem property has a value of
        Other, the OtherTargetOS property must have a
        non-null value. For all other values of
        TargetOperatingSystem, the OtherTargetOS property
        is to be NULL."
    ::= { win32DriverVXDEntry 13 }

osvxdPMAPI  OBJECT-TYPE
    SYNTAX     WtcsDisplayString
    MAX-ACCESS read-only
    STATUS     current
    DESCRIPTION
        "Offset address to the protected mode application
        programming interface for this VXD. These functions
        can give applications direct access to the features
        of the VXD."
    ::= { win32DriverVXDEntry 14 }

osvxdSerialNumber  OBJECT-TYPE
    SYNTAX     WtcsDisplayString
    MAX-ACCESS read-only
    STATUS     current
    DESCRIPTION
        "Assigned serial number of this software element."
    ::= { win32DriverVXDEntry 15 }

osvxdServiceTableSize  OBJECT-TYPE
    SYNTAX     Gauge32
    MAX-ACCESS read-only
    STATUS     current
    DESCRIPTION
        "Number of installed services and device driver
        services provided by the operating system.
        Example: 1024"
    ::= { win32DriverVXDEntry 16 }

osvxdSoftwareElementID  OBJECT-TYPE
    SYNTAX     WtcsDisplayString (SIZE (0..256))
    MAX-ACCESS read-only
    STATUS     current
    DESCRIPTION
        "Identifier for this software element, designed to
        be used in conjunction with other keys to create a
        unique representation of this CIM_SoftwareElement
        instance."
    ::= { win32DriverVXDEntry 17 }

osvxdSoftwareElementState  OBJECT-TYPE
    SYNTAX     INTEGER {
        deployable(1),
        installable(2),
        executable(3),
        running(4)
    }
    MAX-ACCESS read-only
    STATUS     current
    DESCRIPTION
        "State of a software element."
    ::= { win32DriverVXDEntry 18 }

osvxdStatus  OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is on-line,
        yet the managed element is neither 'OK' nor in one
        of the other states."
    ::= { win32DriverVXDEntry 19 }

osvxdTargetOperatingSystem  OBJECT-TYPE
    SYNTAX     INTEGER {
        unknown(0),
        other(1),
        macos(2),
        attunix(3),
        dgux(4),
        decnt(5),
        digitalUnix(6),
        openVMS(7),
        hpux(8),
        aix(9),
        mvs(10),
        os400(11),
        os2(12),
        javaVM(13),
        msdos(14),
        win3x(15),
        win95(16),
        win98(17),
        winnt(18),
        wince(19),
        ncr3000(20),
        netWare(21),
        osf(22),
        dcOS(23),
        reliantUNIX(24),
        scoUnixWare(25),
        scoOpenServer(26),
        sequent(27),
        irix(28),
        solaris(29),
        sunOS(30),
        u6000(31),
        aseries(32),
        tandemNSK(33),
        tandemNT(34),
        bs2000(35),
        linux(36),
        lynx(37),
        xenix(38),
        vmESA(39),
        interactiveUNIX(40),
        bsdunix(41),
        freeBSD(42),
        netBSD(43),
        gnuHurd(44),
        os9(45),
        machKernel(46),
        inferno(47),
        qnx(48),
        epoc(49),
        ixWorks(50),
        vxWorks(51),
        miNT(52),
        beOS(53),
        hpMPE(54),
        nextStep(55),
        palmPilot(56),
        rhapsody(57),
        windows2000(58),
        dedicated(59),
        vse(60),
        tpf(61)
    }
    MAX-ACCESS read-only
    STATUS     current
    DESCRIPTION
        "Target operating system of the owning software
        element. The possible values for this property are
        as follows."
    ::= { win32DriverVXDEntry 20 }

osvxdV86API  OBJECT-TYPE
    SYNTAX     WtcsDisplayString
    MAX-ACCESS read-only
    STATUS     current
    DESCRIPTION
        "Offset to the application programming interface
        for use under virtual 8086 mode. These functions
        can give applications direct access to the features
        of the VXD."
    ::= { win32DriverVXDEntry 21 }

osvxdVersion  OBJECT-TYPE
    SYNTAX     WtcsDisplayString
    MAX-ACCESS read-only
    STATUS     current
    DESCRIPTION
        "Version of the VXD driver.
        Example: '3.51'"
    ::= { win32DriverVXDEntry 22 }

win32SystemDriverTable OBJECT-TYPE
    SYNTAX     SEQUENCE OF Win32SystemDriverEntry
    MAX-ACCESS not-accessible
    STATUS     current
    DESCRIPTION
        "The Win32_SystemDriver WMI class represents the
        system driver for a base service."
    ::= { wmiDrivers 2 }

win32SystemDriverEntry OBJECT-TYPE
    SYNTAX     Win32SystemDriverEntry
    MAX-ACCESS not-accessible
    STATUS     current
    DESCRIPTION
        "None"
    INDEX      { ossdIndex }
    ::= { win32SystemDriverTable 1 }

Win32SystemDriverEntry ::= SEQUENCE {
    ossdIndex Integer32,
    ossdAcceptPause  TruthValue,
    ossdAcceptStop  TruthValue,
    ossdCaption  WtcsDisplayString,
    ossdCreationClassName  WtcsDisplayString,
    ossdDescription  WtcsDisplayString,
    ossdDesktopInteract  TruthValue,
    ossdDisplayName  WtcsDisplayString,
    ossdErrorControl  WtcsDisplayString,
    ossdExitCode  Gauge32,
    ossdInstallDate  DateAndTime,
    ossdName  WtcsDisplayString,
    ossdPathName  WtcsDisplayString,
    ossdServiceSpecificExitCode  Gauge32,
    ossdServiceType  INTEGER,
    ossdStarted  TruthValue,
    ossdStartMode  WtcsDisplayString,
    ossdStartName  WtcsDisplayString,
    ossdState  INTEGER,
    ossdStatus  INTEGER,
    ossdSystemCreationClassName  WtcsDisplayString,
    ossdSystemName  WtcsDisplayString,
    ossdTagId  Gauge32
}

ossdIndex OBJECT-TYPE
    SYNTAX     Integer32 (1..2147483647)
    MAX-ACCESS read-only
    STATUS     current
    DESCRIPTION
        "The value of this object uniquely identifies the
        instance entry for this class."
    ::= { win32SystemDriverEntry 1 }

ossdAcceptPause  OBJECT-TYPE
    SYNTAX     TruthValue
    MAX-ACCESS read-only
    STATUS     current
    DESCRIPTION
        "Service can be paused."
    ::= { win32SystemDriverEntry 2 }

ossdAcceptStop  OBJECT-TYPE
    SYNTAX     TruthValue
    MAX-ACCESS read-only
    STATUS     current
    DESCRIPTION
        "Service can be stopped."
    ::= { win32SystemDriverEntry 3 }

ossdCaption  OBJECT-TYPE
    SYNTAX     WtcsDisplayString
    MAX-ACCESS read-only
    STATUS     current
    DESCRIPTION
        "Short description (one-line string) of the
        object."
    ::= { win32SystemDriverEntry 4 }

ossdCreationClassName  OBJECT-TYPE
    SYNTAX     WtcsDisplayString (SIZE (0..256))
    MAX-ACCESS read-only
    STATUS     current
    DESCRIPTION
        "Name of the first concrete class to appear in the
        inheritance chain used in the creation of an
        instance. When used with the other key properties
        of the class, the property allows all instances of
        this class and its subclasses to be uniquely
        identified."
    ::= { win32SystemDriverEntry 5 }

ossdDescription  OBJECT-TYPE
    SYNTAX     WtcsDisplayString
    MAX-ACCESS read-only
    STATUS     current
    DESCRIPTION
        "Description of the object."
    ::= { win32SystemDriverEntry 6 }

ossdDesktopInteract  OBJECT-TYPE
    SYNTAX     TruthValue
    MAX-ACCESS read-only
    STATUS     current
    DESCRIPTION
        "Service can create or communicate with windows on
        the desktop."
    ::= { win32SystemDriverEntry 7 }

ossdDisplayName  OBJECT-TYPE
    SYNTAX     WtcsDisplayString
    MAX-ACCESS read-only
    STATUS     current
    DESCRIPTION
        "Display name of the service. This string has a
        maximum length of 256 characters. The name is
        case-preserved in the Service Control Manager.
        DisplayName comparisons are always
        case-insensitive. Constraints: Accepts the same
        value as the Name property.
        Example: 'Atdisk'"
    ::= { win32SystemDriverEntry 8 }

ossdErrorControl  OBJECT-TYPE
    SYNTAX     WtcsDisplayString
    MAX-ACCESS read-only
    STATUS     current
    DESCRIPTION
        "Severity of the error if this service fails to
        start during startup. The value indicates the
        action taken by the startup program if failure
        occurs. All errors are logged by the computer
        system. 
        Value Meaning 
        'Ignore' User is not notified. 
        'Normal' User is notified. 
        'Severe' System is restarted wth the
        last-known-good configuration. 
        'Critical' System attempts to restart with a good
        configuration. 
        'Unknown' Cause of the failure is unknown. "
    ::= { win32SystemDriverEntry 9 }

ossdExitCode  OBJECT-TYPE
    SYNTAX     Gauge32
    MAX-ACCESS read-only
    STATUS     current
    DESCRIPTION
        "Windows error code defining any problems
        encountered in starting or stopping the service.
        This property is set to
        ERROR_SERVICE_SPECIFIC_ERROR (1066) when the error
        is unique to the service represented by this class,
        and information about the error is available in the
        ServiceSpecificExitCode property. The service sets
        this value to NO_ERROR when running, and again upon
        normal termination."
    ::= { win32SystemDriverEntry 10 }

ossdInstallDate  OBJECT-TYPE
    SYNTAX     DateAndTime
    MAX-ACCESS read-only
    STATUS     current
    DESCRIPTION
        "Object was installed. This property does not need
        a value to indicate that the object is installed."
    ::= { win32SystemDriverEntry 11 }

ossdName  OBJECT-TYPE
    SYNTAX     WtcsDisplayString
    MAX-ACCESS read-only
    STATUS     current
    DESCRIPTION
        "Unique identifier for the service which provides
        an indication of the functionality that is managed.
        This functionality is described in more detail in
        the object's Description property."
    ::= { win32SystemDriverEntry 12 }

ossdPathName  OBJECT-TYPE
    SYNTAX     WtcsDisplayString
    MAX-ACCESS read-only
    STATUS     current
    DESCRIPTION
        "Fully-qualified path to the service binary file
        that implements the service.
        Example: '\SystemRoot\System32\drivers\afd.sys'"
    ::= { win32SystemDriverEntry 13 }

ossdServiceSpecificExitCode  OBJECT-TYPE
    SYNTAX     Gauge32
    MAX-ACCESS read-only
    STATUS     current
    DESCRIPTION
        "Service-specific error code for errors that occur
        while the service is either starting or stopping.
        The exit codes are defined by the service
        represented by this class. This value is only set
        when the ExitCode property value is
        ERROR_SERVICE_SPECIFIC_ERROR (1066)."
    ::= { win32SystemDriverEntry 14 }

ossdServiceType  OBJECT-TYPE
    SYNTAX     INTEGER {
        kernalDriver(1),
        fileSystemDriver(2),
        adapter(3),
        recognizerDriver(4),
        ownProcess(5),
        shareProcess(6),
        interactiveProcess(7)
    }
    MAX-ACCESS read-only
    STATUS     current
    DESCRIPTION
        "Type of service provided to calling processes."
    ::= { win32SystemDriverEntry 15 }

ossdStarted  OBJECT-TYPE
    SYNTAX     TruthValue
    MAX-ACCESS read-only
    STATUS     current
    DESCRIPTION
        "Service has been started."
    ::= { win32SystemDriverEntry 16 }

ossdStartMode  OBJECT-TYPE
    SYNTAX     WtcsDisplayString
    MAX-ACCESS read-only
    STATUS     current
    DESCRIPTION
        "Severity of the error if this service fails to
        start during startup. The value indicates the
        action taken by the startup program if failure
        occurs. All errors are logged by the computer
        system.
        Value Meaning 
        'Ignore' User is not notified. 
        'Normal' User is notified. 
        'Severe' System is restarted with the
        last-known-good configuration. 
        'Critical' System attempts to restart with a good
        configuration. 
        'Unknown' Cause of the failure is unknown. "
    ::= { win32SystemDriverEntry 17 }

ossdStartName  OBJECT-TYPE
    SYNTAX     WtcsDisplayString
    MAX-ACCESS read-only
    STATUS     current
    DESCRIPTION
        "Account name under which the service runs.
        Depending on the service type, the account name may
        be in the form of DomainName\Username. The service
        process will be logged using one of these two forms
        when it runs. If the account belongs to the
        built-in domain, .\Username can be specified. If
        NULL is specified, the service will be logged on as
        the LocalSystem account. For kernel or system level
        drivers, StartName contains the driver object name
        (that is, \FileSystem\Rdr or \Driver\Xns) which the
        input and output (I/O) system uses to load the
        device driver. Additionally, if NULL is specified,
        the driver runs with a default object name created
        by the I/O system based on the service name.
        Example: 'DWDOM\Admin'
        Windows XP:  You can use UPN format
        (Username@DomainName) to specify the StartName."
    ::= { win32SystemDriverEntry 18 }

ossdState  OBJECT-TYPE
    SYNTAX     INTEGER {
        stopped(1),
        startPending(2),
        stopPending(3),
        running(4),
        continuePending(5),
        pausePending(6),
        paused(7),
        unknown(8)
    }
    MAX-ACCESS read-only
    STATUS     current
    DESCRIPTION
        "Current state of the base service."
    ::= { win32SystemDriverEntry 19 }

ossdStatus  OBJECT-TYPE
    SYNTAX     INTEGER {
        ok(1),
        error(2),
        degraded(3),
        unknown(4),
        predFail(5),
        starting(6),
        stopping(7),
        service(8)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is on-line,
        yet the managed element is neither 'OK' nor in one
        of the other states."
    ::= { win32SystemDriverEntry 20 }

ossdSystemCreationClassName  OBJECT-TYPE
    SYNTAX     WtcsDisplayString
    MAX-ACCESS read-only
    STATUS     current
    DESCRIPTION
        "Type name of the system that hosts this service."
    ::= { win32SystemDriverEntry 21 }

ossdSystemName  OBJECT-TYPE
    SYNTAX     WtcsDisplayString
    MAX-ACCESS read-only
    STATUS     current
    DESCRIPTION
        "Name of the system that hosts this service."
    ::= { win32SystemDriverEntry 22 }

ossdTagId  OBJECT-TYPE
    SYNTAX     Gauge32
    MAX-ACCESS read-only
    STATUS     current
    DESCRIPTION
        "Unique tag value for this service in the group. A
        value of 0 indicates that the service has not been
        assigned a tag. A tag can be used for ordering
        service startup within a load order group by
        specifying a tag order vector in the registry
        located at:
        HKEY_LOCAL_MACHINE\System\CurrentControlSet\Control
        \GroupOrderList. Tags are only evaluated for Kernel
        Driver and File System Driver start type services
        that have Boot or System start modes."
    ::= { win32SystemDriverEntry 23 }

wmiFileSystem OBJECT-IDENTITY
    STATUS     current
    DESCRIPTION
        "The File System subcategory groups classes that
        represent the way a hard disk is logically
        arranged. This includes the type of file system
        used, the directory structure, and way the disk is
        partitioned."
    ::= { wmiOperatingSystem 3 }

win32DiskPartitionTable OBJECT-TYPE
    SYNTAX     SEQUENCE OF Win32DiskPartitionEntry
    MAX-ACCESS not-accessible
    STATUS     current
    DESCRIPTION
        "The Win32_DiskPartition WMI class represents the
        capabilities and management capacity of a
        partitioned area of a physical disk on a Windows
        system. Example: Disk #0, Partition #1."
    ::= { wmiFileSystem 1 }

win32DiskPartitionEntry OBJECT-TYPE
    SYNTAX     Win32DiskPartitionEntry
    MAX-ACCESS not-accessible
    STATUS     current
    DESCRIPTION
        "None"
    INDEX      { osdpIndex }
    ::= { win32DiskPartitionTable 1 }

Win32DiskPartitionEntry ::= SEQUENCE {
    osdpIndex Integer32,
    osdpAccess  INTEGER,
    osdpAvailability  INTEGER,
    osdpBlockSize  Gauge32,
    osdpBootable  TruthValue,
    osdpBootPartition  TruthValue,
    osdpCaption  WtcsDisplayString,
    osdpConfigManagerErrorCode  INTEGER,
    osdpConfigManagerUserConfig  TruthValue,
    osdpCreationClassName  WtcsDisplayString,
    osdpDescription  WtcsDisplayString,
    osdpDeviceID  WtcsDisplayString,
    osdpDiskIndex  Gauge32,
    osdpErrorCleared  TruthValue,
    osdpErrorDescription  WtcsDisplayString,
    osdpErrorMethodology  WtcsDisplayString,
    osdpHiddenSectors  Gauge32,
    osdpPartitionIndex  Gauge32,
    osdpInstallDate  DateAndTime,
    osdpLastErrorCode  Gauge32,
    osdpName  WtcsDisplayString,
    osdpNumberOfBlocks  Gauge32,
    osdpPNPDeviceID  WtcsDisplayString,
    osdpPowerManagementCapabilities  WtcsDisplayString,
    osdpPowerManagementSupported  TruthValue,
    osdpPrimaryPartition  TruthValue,
    osdpPurpose  WtcsDisplayString,
    osdpRewritePartition  TruthValue,
    osdpSize  WtcsDisplayString,
    osdpStartingOffset  Gauge32,
    osdpStatus  INTEGER,
    osdpStatusInfo  INTEGER,
    osdpSystemCreationClassName  WtcsDisplayString,
    osdpSystemName  WtcsDisplayString,
    osdpType  WtcsDisplayString
}

osdpIndex OBJECT-TYPE
    SYNTAX     Integer32 (1..2147483647)
    MAX-ACCESS read-only
    STATUS     current
    DESCRIPTION
        "The value of this object uniquely identifies the
        instance entry for this class."
    ::= { win32DiskPartitionEntry 1 }

osdpAccess  OBJECT-TYPE
    SYNTAX     INTEGER {
        unknown(0),
        readable(1),
        writable(2),
        readwriteSupported(3),
        writeOnce(4)
    }
    MAX-ACCESS read-only
    STATUS     current
    DESCRIPTION
        "Media access available."
    ::= { win32DiskPartitionEntry 2 }

osdpAvailability  OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Availability and status of the device. Power Save
        - Unknown indicates that the device is known to be
        in a power save mode, but its exact status is
        unknown; Power Save - Low Power Mode indicates that
        the device is in a power save state but still
        functioning, and may exhibit degraded performance;
        Power Save - Standby indicates that the device is
        not functioning but could be brought to full power
        quickly; and Power Save - Warning indicates that
        the device is in a warning state, though also in a
        power save mode."
    ::= { win32DiskPartitionEntry 3 }

osdpBlockSize  OBJECT-TYPE
    SYNTAX     Gauge32
    MAX-ACCESS read-only
    STATUS     current
    DESCRIPTION
        "Size in bytes of the blocks which form this
        storage extent. If unknown or if a block concept is
        not valid (for example, for aggregate extents,
        memory or logical disks), enter a 1."
    ::= { win32DiskPartitionEntry 4 }

osdpBootable  OBJECT-TYPE
    SYNTAX     TruthValue
    MAX-ACCESS read-only
    STATUS     current
    DESCRIPTION
        "Computer may be booted from this partition."
    ::= { win32DiskPartitionEntry 5 }

osdpBootPartition  OBJECT-TYPE
    SYNTAX     TruthValue
    MAX-ACCESS read-only
    STATUS     current
    DESCRIPTION
        "Partition is the active partition. The operating
        system uses the active partition when booting from
        a hard disk."
    ::= { win32DiskPartitionEntry 6 }

osdpCaption  OBJECT-TYPE
    SYNTAX     WtcsDisplayString
    MAX-ACCESS read-only
    STATUS     current
    DESCRIPTION
        "Short description (one-line string) of the
        object."
    ::= { win32DiskPartitionEntry 7 }

osdpConfigManagerErrorCode  OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code."
    ::= { win32DiskPartitionEntry 8 }

osdpConfigManagerUserConfig  OBJECT-TYPE
    SYNTAX     TruthValue
    MAX-ACCESS read-only
    STATUS     current
    DESCRIPTION
        "Device is using a user-defined configuration."
    ::= { win32DiskPartitionEntry 9 }

osdpCreationClassName  OBJECT-TYPE
    SYNTAX     WtcsDisplayString
    MAX-ACCESS read-only
    STATUS     current
    DESCRIPTION
        "Name of the first concrete class to appear in the
        inheritance chain used in the creation of an
        instance. When used with the other key properties
        of the class, the property allows all instances of
        this class and its subclasses to be uniquely
        identified."
    ::= { win32DiskPartitionEntry 10 }

osdpDescription  OBJECT-TYPE
    SYNTAX     WtcsDisplayString
    MAX-ACCESS read-only
    STATUS     current
    DESCRIPTION
        "Description of the object."
    ::= { win32DiskPartitionEntry 11 }

osdpDeviceID  OBJECT-TYPE
    SYNTAX     WtcsDisplayString
    MAX-ACCESS read-only
    STATUS     current
    DESCRIPTION
        "Unique identifier of the disk drive and partition,
        from the rest of the system."
    ::= { win32DiskPartitionEntry 12 }

osdpDiskIndex  OBJECT-TYPE
    SYNTAX     Gauge32
    MAX-ACCESS read-only
    STATUS     current
    DESCRIPTION
        "Index number of the disk containing this
        partition.
        Example: 0"
    ::= { win32DiskPartitionEntry 13 }

osdpErrorCleared  OBJECT-TYPE
    SYNTAX     TruthValue
    MAX-ACCESS read-only
    STATUS     current
    DESCRIPTION
        "Error reported in LastErrorCode is now cleared."
    ::= { win32DiskPartitionEntry 14 }

osdpErrorDescription  OBJECT-TYPE
    SYNTAX     WtcsDisplayString
    MAX-ACCESS read-only
    STATUS     current
    DESCRIPTION
        "Information about the error recorded in
        LastErrorCode, and information on any corrective
        actions that may be taken."
    ::= { win32DiskPartitionEntry 15 }

osdpErrorMethodology  OBJECT-TYPE
    SYNTAX     WtcsDisplayString
    MAX-ACCESS read-only
    STATUS     current
    DESCRIPTION
        "Type of error detection and correction supported
        by this storage extent."
    ::= { win32DiskPartitionEntry 16 }

osdpHiddenSectors  OBJECT-TYPE
    SYNTAX     Gauge32
    MAX-ACCESS read-only
    STATUS     current
    DESCRIPTION
        "Number of hidden sectors in the partition.
        Example: 63"
    ::= { win32DiskPartitionEntry 17 }

osdpPartitionIndex  OBJECT-TYPE
    SYNTAX     Gauge32
    MAX-ACCESS read-only
    STATUS     current
    DESCRIPTION
        "Index number of the partition.
        Example: 1"
    ::= { win32DiskPartitionEntry 18 }

osdpInstallDate  OBJECT-TYPE
    SYNTAX     DateAndTime
    MAX-ACCESS read-only
    STATUS     current
    DESCRIPTION
        "Object was installed. This property does not need
        a value to indicate that the object is installed."
    ::= { win32DiskPartitionEntry 19 }

osdpLastErrorCode  OBJECT-TYPE
    SYNTAX     Gauge32
    MAX-ACCESS read-only
    STATUS     current
    DESCRIPTION
        "Last error code reported by the logical device."
    ::= { win32DiskPartitionEntry 20 }

osdpName  OBJECT-TYPE
    SYNTAX     WtcsDisplayString
    MAX-ACCESS read-only
    STATUS     current
    DESCRIPTION
        "Label by which the object is known. When
        subclassed, the property can be overridden to be a
        key property."
    ::= { win32DiskPartitionEntry 21 }

osdpNumberOfBlocks  OBJECT-TYPE
    SYNTAX     Gauge32
    MAX-ACCESS read-only
    STATUS     current
    DESCRIPTION
        "Total number of consecutive blocks, each block the
        size of the value contained in the BlockSize
        property, which form this storage extent. Total
        size of the storage extent can be calculated by
        multiplying the value of the BlockSize property by
        the value of this property. If the value of
        BlockSize is 1, this property is the total size of
        the storage extent."
    ::= { win32DiskPartitionEntry 22 }

osdpPNPDeviceID  OBJECT-TYPE
    SYNTAX     WtcsDisplayString
    MAX-ACCESS read-only
    STATUS     current
    DESCRIPTION
        "Windows Plug and Play device identifier of the
        logical device.
        Example: '*PNP030b'"
    ::= { win32DiskPartitionEntry 23 }

osdpPowerManagementCapabilities  OBJECT-TYPE
    SYNTAX     WtcsDisplayString
    MAX-ACCESS read-only
    STATUS     current
    DESCRIPTION
        "Specific power-related capabilities of a logical
        device. The Enabled value indicates that the power
        management features are currently enabled but the
        exact feature set is unknown or the information is
        unavailable. Power Saving Modes Entered
        Automatically indicates that a device can change
        its power state based on usage or other criteria.
        Power State Settable indicates that the
        SetPowerState method is supported. Power Cycling
        Supported indicates that the SetPowerState method
        can be invoked with the PowerState parameter set to
        5 (Power Cycle). Timed Power On Supported indicates
        that the SetPowerState method can be invoked with
        the PowerState parameter set to 5 (Power Cycle) and
        Time set to a specific date and time, or interval,
        for power-on.
        Value Meaning 
        0 Unknown 
        1 Not Supported 
        2 Disabled 
        3 Enabled 
        4 Power Saving Modes Entered Automatically 
        5 Power State Settable 
        6 Power Cycling Supported 
        7 Timed Power On Supported "
    ::= { win32DiskPartitionEntry 24 }

osdpPowerManagementSupported  OBJECT-TYPE
    SYNTAX     TruthValue
    MAX-ACCESS read-only
    STATUS     current
    DESCRIPTION
        "Device can be power-managed (can be put into
        suspend mode, and so on). The property does not
        indicate that power management features are
        currently enabled, only that the logical device is
        capable of power management."
    ::= { win32DiskPartitionEntry 25 }

osdpPrimaryPartition  OBJECT-TYPE
    SYNTAX     TruthValue
    MAX-ACCESS read-only
    STATUS     current
    DESCRIPTION
        "Primary partition."
    ::= { win32DiskPartitionEntry 26 }

osdpPurpose  OBJECT-TYPE
    SYNTAX     WtcsDisplayString
    MAX-ACCESS read-only
    STATUS     current
    DESCRIPTION
        "Description of the media and/or its use."
    ::= { win32DiskPartitionEntry 27 }

osdpRewritePartition  OBJECT-TYPE
    SYNTAX     TruthValue
    MAX-ACCESS read-only
    STATUS     current
    DESCRIPTION
        "Partition information has changed. When you change
        a partition (with IOCTL_DISK_SET_DRIVE_LAYOUT), the
        system uses this property to determine which
        partitions have changed and need their information
        rewritten. If TRUE, the partition needs to be
        rewritten."
    ::= { win32DiskPartitionEntry 28 }

osdpSize  OBJECT-TYPE
    SYNTAX     WtcsDisplayString
    UNITS "Bytes"
    MAX-ACCESS read-only
    STATUS     current
    DESCRIPTION
        "Total size of the partition.
        Example: 1059045376"
    ::= { win32DiskPartitionEntry 29 }

osdpStartingOffset  OBJECT-TYPE
    SYNTAX     Gauge32
    UNITS "Bytes"
    MAX-ACCESS read-only
    STATUS     current
    DESCRIPTION
        "Starting offset (in bytes) of the partition.
        Example: 32256"
    ::= { win32DiskPartitionEntry 30 }

osdpStatus  OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is on-line,
        yet the managed element is neither 'OK' nor in one
        of the other states."
    ::= { win32DiskPartitionEntry 31 }

osdpStatusInfo  OBJECT-TYPE
    SYNTAX     INTEGER {
        other(1),
        unknown(2),
        enabled(3),
        disabled(4),
        notApplicable(5)
    }
    MAX-ACCESS read-only
    STATUS     current
    DESCRIPTION
        "State of the logical device. If this property does
        not apply to the logical device, the value 5 (Not
        Applicable) should be used."
    ::= { win32DiskPartitionEntry 32 }

osdpSystemCreationClassName  OBJECT-TYPE
    SYNTAX     WtcsDisplayString
    MAX-ACCESS read-only
    STATUS     current
    DESCRIPTION
        "Creation class name of the scoping system."
    ::= { win32DiskPartitionEntry 33 }

osdpSystemName  OBJECT-TYPE
    SYNTAX     WtcsDisplayString
    MAX-ACCESS read-only
    STATUS     current
    DESCRIPTION
        "Name of the scoping system."
    ::= { win32DiskPartitionEntry 34 }

osdpType  OBJECT-TYPE
    SYNTAX     WtcsDisplayString
    MAX-ACCESS read-only
    STATUS     current
    DESCRIPTION
        "Type of the partition. Values are:
        'Unused'
        '12-bit FAT'
        'Xenix Type 1'
        'Xenix Type 2'
        '16-bit FAT'
        'Extended Partition'
        'MS-DOS V4 Huge'
        'Installable File System'
        'PowerPC Reference Platform'
        'UNIX'
        'NTFS'
        'Win95 w/Extended Int 13'
        'Extended w/Extended Int 13'
        'Logical Disk Manager'
        'Unknown'"
    ::= { win32DiskPartitionEntry 35 }

win32LogicalDiskTable OBJECT-TYPE
    SYNTAX     SEQUENCE OF Win32LogicalDiskEntry
    MAX-ACCESS not-accessible
    STATUS     current
    DESCRIPTION
        "The Win32_LogicalDisk WMI class represents a data
        source that resolves to an actual local storage
        device on a Windows system."
    ::= { wmiFileSystem 2 }

win32LogicalDiskEntry OBJECT-TYPE
    SYNTAX     Win32LogicalDiskEntry
    MAX-ACCESS not-accessible
    STATUS     current
    DESCRIPTION
        "None"
    INDEX      { osldIndex }
    ::= { win32LogicalDiskTable 1 }

Win32LogicalDiskEntry ::= SEQUENCE {
    osldIndex Integer32,
    osldAccess  INTEGER,
    osldAvailability  INTEGER,
    osldBlockSize  Gauge32,
    osldCaption  WtcsDisplayString,
    osldCompressed  TruthValue,
    osldConfigManagerErrorCode  INTEGER,
    osldConfigManagerUserConfig  TruthValue,
    osldCreationClassName  WtcsDisplayString,
    osldDescription  WtcsDisplayString,
    osldDeviceID  WtcsDisplayString,
    osldDriveType  INTEGER,
    osldErrorCleared  TruthValue,
    osldErrorDescription  WtcsDisplayString,
    osldErrorMethodology  WtcsDisplayString,
    osldFileSystem  WtcsDisplayString,
    osldFreeSpace  Gauge32,
    osldInstallDate  DateAndTime,
    osldLastErrorCode  Gauge32,
    osldMaximumComponentLength  Gauge32,
    osldMediaType  Gauge32,
    osldName  WtcsDisplayString,
    osldNumberOfBlocks  Gauge32,
    osldPNPDeviceID  WtcsDisplayString,
    osldPowerManagementCapabilities  WtcsDisplayString,
    osldPowerManagementSupported  TruthValue,
    osldProviderName  WtcsDisplayString,
    osldPurpose  WtcsDisplayString,
    osldQuotasDisabled  TruthValue,
    osldQuotasIncomplete  TruthValue,
    osldQuotasRebuilding  TruthValue,
    osldSize  Gauge32,
    osldStatus  INTEGER,
    osldStatusInfo  INTEGER,
    osldSupportsDiskQuotas  TruthValue,
    osldSupportsFileBasedCompression  TruthValue,
    osldSystemCreationClassName  WtcsDisplayString,
    osldSystemName  WtcsDisplayString,
    osldVolumeDirty  TruthValue,
    osldVolumeName  WtcsDisplayString,
    osldVolumeSerialNumber  WtcsDisplayString
}

osldIndex OBJECT-TYPE
    SYNTAX     Integer32 (1..2147483647)
    MAX-ACCESS read-only
    STATUS     current
    DESCRIPTION
        "The value of this object uniquely identifies the
        instance entry for this class."
    ::= { win32LogicalDiskEntry 1 }

osldAccess  OBJECT-TYPE
    SYNTAX     INTEGER {
        unknown(0),
        readable(1),
        writable(2),
        readWriteSupported(3),
        writeOnce(4)
    }
    MAX-ACCESS read-only
    STATUS     current
    DESCRIPTION
        "Type of media access available. This property is
        inherited from CIM_StorageExtent."
    ::= { win32LogicalDiskEntry 2 }

osldAvailability  OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Availability and status of the device. Power Save
        - Unknown indicates that the device is known to be
        in a power save mode, but its exact status is
        unknown; Power Save - Low Power Mode indicates that
        the device is in a power save state but still
        functioning, and may exhibit degraded performance;
        Power Save - Standby indicates that the device is
        not functioning but could be brought to full power
        quickly; and Power Save - Warning indicates that
        the device is in a warning state, though also in a
        power save mode. This property is inherited from
        CIM_LogicalDevice."
    ::= { win32LogicalDiskEntry 3 }

osldBlockSize  OBJECT-TYPE
    SYNTAX     Gauge32
    MAX-ACCESS read-only
    STATUS     current
    DESCRIPTION
        "Size in bytes of the blocks that form this storage
        extent. If unknown or if a block concept is not
        valid (for example, for aggregate extents, memory
        or logical disks), enter a 1. This property is
        inherited from CIM_StorageExtent."
    ::= { win32LogicalDiskEntry 4 }

osldCaption  OBJECT-TYPE
    SYNTAX     WtcsDisplayString
    MAX-ACCESS read-only
    STATUS     current
    DESCRIPTION
        "Short description of the object a one-line string.
        This property is inherited from
        CIM_ManagedSystemElement."
    ::= { win32LogicalDiskEntry 5 }

osldCompressed  OBJECT-TYPE
    SYNTAX     TruthValue
    MAX-ACCESS read-only
    STATUS     current
    DESCRIPTION
        "If TRUE, the logical volume exists as a single
        compressed entity, such as a DoubleSpace volume. If
        file based compression is supported (such as on
        NTFS), this property will be FALSE."
    ::= { win32LogicalDiskEntry 6 }

osldConfigManagerErrorCode  OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code. This
        property is inherited from CIM_LogicalDevice."
    ::= { win32LogicalDiskEntry 7 }

osldConfigManagerUserConfig  OBJECT-TYPE
    SYNTAX     TruthValue
    MAX-ACCESS read-only
    STATUS     current
    DESCRIPTION
        "If TRUE, the device is using a user-defined
        configuration. This property is inherited from
        CIM_LogicalDevice."
    ::= { win32LogicalDiskEntry 8 }

osldCreationClassName  OBJECT-TYPE
    SYNTAX     WtcsDisplayString
    MAX-ACCESS read-only
    STATUS     current
    DESCRIPTION
        "Name of the first concrete class to appear in the
        inheritance chain used in the creation of an
        instance. When used with the other key properties
        of the class, the property allows all instances of
        this class and its subclasses to be uniquely
        identified. This property is inherited from
        CIM_LogicalDevice."
    ::= { win32LogicalDiskEntry 9 }

osldDescription  OBJECT-TYPE
    SYNTAX     WtcsDisplayString
    MAX-ACCESS read-only
    STATUS     current
    DESCRIPTION
        "Description of the object. This property is
        inherited from CIM_ManagedSystemElement."
    ::= { win32LogicalDiskEntry 10 }

osldDeviceID  OBJECT-TYPE
    SYNTAX     WtcsDisplayString
    MAX-ACCESS read-only
    STATUS     current
    DESCRIPTION
        "Unique identifier of the logical disk from other
        devices on the system. This property is inherited
        from CIM_LogicalDevice."
    ::= { win32LogicalDiskEntry 11 }

osldDriveType  OBJECT-TYPE
    SYNTAX     INTEGER {
        unknown(0),
        noRootDirectory(1),
        removableDisk(2),
        localDisk(3),
        networkDrive(4),
        compactDisc(5),
        ramDisk(6)
    }
    MAX-ACCESS read-only
    STATUS     current
    DESCRIPTION
        "Numeric value corresponding to the type of disk
        drive this logical disk represents."
    ::= { win32LogicalDiskEntry 12 }

osldErrorCleared  OBJECT-TYPE
    SYNTAX     TruthValue
    MAX-ACCESS read-only
    STATUS     current
    DESCRIPTION
        "If TRUE, the error reported in LastErrorCode is
        now cleared. This property is inherited from
        CIM_LogicalDevice."
    ::= { win32LogicalDiskEntry 13 }

osldErrorDescription  OBJECT-TYPE
    SYNTAX     WtcsDisplayString
    MAX-ACCESS read-only
    STATUS     current
    DESCRIPTION
        "More information about the error recorded in
        LastErrorCode, and information on any corrective
        actions that may be taken. This property is
        inherited from CIM_LogicalDevice."
    ::= { win32LogicalDiskEntry 14 }

osldErrorMethodology  OBJECT-TYPE
    SYNTAX     WtcsDisplayString
    MAX-ACCESS read-only
    STATUS     current
    DESCRIPTION
        "Type of error detection and correction supported
        by this storage extent. This property is inherited
        from CIM_StorageExtent."
    ::= { win32LogicalDiskEntry 15 }

osldFileSystem  OBJECT-TYPE
    SYNTAX     WtcsDisplayString
    MAX-ACCESS read-only
    STATUS     current
    DESCRIPTION
        "File system on the logical disk.
        Example: 'NTFS'"
    ::= { win32LogicalDiskEntry 16 }

osldFreeSpace  OBJECT-TYPE
    SYNTAX     Gauge32
    MAX-ACCESS read-only
    STATUS     current
    DESCRIPTION
        "Space available on the logical disk. This property
        is inherited from CIM_LogicalDisk."
    ::= { win32LogicalDiskEntry 17 }

osldInstallDate  OBJECT-TYPE
    SYNTAX     DateAndTime
    MAX-ACCESS read-only
    STATUS     current
    DESCRIPTION
        "Date and time the object was installed. This
        property does not need a value to indicate that the
        object is installed. This property is inherited
        from CIM_ManagedSystemElement."
    ::= { win32LogicalDiskEntry 18 }

osldLastErrorCode  OBJECT-TYPE
    SYNTAX     Gauge32
    MAX-ACCESS read-only
    STATUS     current
    DESCRIPTION
        "Last error code reported by the logical device.
        This property is inherited from CIM_LogicalDevice."
    ::= { win32LogicalDiskEntry 19 }

osldMaximumComponentLength  OBJECT-TYPE
    SYNTAX     Gauge32
    MAX-ACCESS read-only
    STATUS     current
    DESCRIPTION
        "Maximum length of a filename component supported
        by the Windows drive. A filename component is that
        portion of a filename between backslashes. The
        value can be used to indicate that long names are
        supported by the specified file system. For
        example, for a FAT file system supporting long
        names, the function stores the value 255, rather
        than the previous 8.3 indicator. Long names can
        also be supported on systems that use the NTFS file
        system.
        Example: 255"
    ::= { win32LogicalDiskEntry 20 }

osldMediaType  OBJECT-TYPE
    SYNTAX     Gauge32 (0..22)
    MAX-ACCESS read-only
    STATUS     current
    DESCRIPTION
        "Type of media currently present in the logical
        drive. This value will be one of the values of the
        MEDIA_TYPE enumeration defined in Winioctl.h. The
        value may not be exact for removable drives if
        currently there is no media in the drive.
        
        Value Meaning 
        0 Unknown Format is unknown 
        1 F5_1Pt2_512 51/4-Inch Floppy Disk - 1.2Mb - 512
        bytes/sector 
        2 F3_1Pt44_512 31/2-Inch Floppy Disk - 1.44Mb -512
        bytes/sector 
        3 F3_2Pt88_512 31/2-Inch Floppy Disk - 2.88Mb - 512
        bytes/sector 
        4 F3_20Pt8_512 31/2-Inch Floppy Disk - 20.8Mb - 512
        bytes/sector 
        5 F3_720_512 31/2-Inch Floppy Disk - 720Kb - 512
        bytes/sector 
        6 F5_360_512 51/4-Inch Floppy Disk - 360Kb - 512
        bytes/sector 
        7 F5_320_512 51/4-Inch Floppy Disk - 320Kb - 512
        bytes/sector 
        8 F5_320_1024 51/4-Inch Floppy Disk - 320Kb - 1024
        bytes/sector 
        9 F5_180_512 51/4-Inch Floppy Disk - 180Kb - 512
        bytes/sector 
        10 F5_160_512 51/4-Inch Floppy Disk - 160Kb - 512
        bytes/sector 
        11 Removable media other than floppy 
        12 Fixed hard disk media 
        13 F3_120M_512 31/2-Inch Floppy Disk - 120Mb - 512
        bytes/sector 
        14 F3_640_512 31/2-Inch Floppy Disk - 640Kb - 512
        bytes/sector 
        15 F5_640_512 51/4-Inch Floppy Disk - 640Kb - 512
        bytes/sector 
        16 F5_720_512 51/4-Inch Floppy Disk - 720Kb - 512
        bytes/sector 
        17 F3_1Pt2_512 31/2-Inch Floppy Disk - 1.2Mb - 512
        bytes/sector 
        18 F3_1Pt23_1024 31/2-Inch Floppy Disk - 1.23Mb -
        1024 bytes/sector 
        19 F5_1Pt23_1024 51/4-Inch Floppy Disk - 1.23Mb -
        1024 bytes/sector 
        20 F3_128Mb_512 31/2-Inch Floppy Disk - 128Mb - 512
        bytes/sector 
        21 F3_230Mb_512 31/2-Inch Floppy Disk - 230Mb - 512
        bytes/sector 
        22 F8_256_128 8-Inch Floppy Disk - 256Kb - 128
        bytes/sector"
    ::= { win32LogicalDiskEntry 21 }

osldName  OBJECT-TYPE
    SYNTAX     WtcsDisplayString
    MAX-ACCESS read-only
    STATUS     current
    DESCRIPTION
        "Label by which the object is known. When
        subclassed, the property can be overridden to be a
        key property. This property is inherited from
        CIM_ManagedSystemElement."
    ::= { win32LogicalDiskEntry 22 }

osldNumberOfBlocks  OBJECT-TYPE
    SYNTAX     Gauge32
    MAX-ACCESS read-only
    STATUS     current
    DESCRIPTION
        "Total number of consecutive blocks, each block the
        size of the value contained in the BlockSize
        property, which form this storage extent. Total
        size of the storage extent can be calculated by
        multiplying the value of the BlockSize property by
        the value of this property. If the value of
        BlockSize is 1, this property is the total size of
        the storage extent. This property is inherited from
        CIM_StorageExtent."
    ::= { win32LogicalDiskEntry 23 }

osldPNPDeviceID  OBJECT-TYPE
    SYNTAX     WtcsDisplayString
    MAX-ACCESS read-only
    STATUS     current
    DESCRIPTION
        "Windows Plug and Play device identifier of the
        logical device. This property is inherited from
        CIM_LogicalDevice.
        Example: '*PNP030b'"
    ::= { win32LogicalDiskEntry 24 }

osldPowerManagementCapabilities  OBJECT-TYPE
    SYNTAX     WtcsDisplayString
    MAX-ACCESS read-only
    STATUS     current
    DESCRIPTION
        "Array of the specific power-related capabilities
        of a logical device. The Enabled value indicates
        that the power management features are currently
        enabled but the exact feature set is unknown or the
        information is unavailable. Power Saving Modes
        Entered Automatically indicates that a device can
        change its power state based on usage or other
        criteria. Power State Settable indicates that the
        SetPowerState method is supported. Power Cycling
        Supported indicates that the SetPowerState method
        can be invoked with the PowerState parameter set to
        5 (Power Cycle). Timed Power On Supported indicates
        that the SetPowerState method can be invoked with
        the PowerState parameter set to 5 (Power Cycle) and
        Time set to a specific date and time, or interval,
        for power-on. This property is inherited from
        CIM_LogicalDevice.
        Value Meaning 
        0 Unknown 
        1 Not Supported 
        2 Disabled 
        3 Enabled 
        4 Power Saving Modes Entered Automatically 
        5 Power State Settable 
        6 Power Cycling Supported 
        7 Timed Power On Supported "
    ::= { win32LogicalDiskEntry 25 }

osldPowerManagementSupported  OBJECT-TYPE
    SYNTAX     TruthValue
    MAX-ACCESS read-only
    STATUS     current
    DESCRIPTION
        "If TRUE, the device can be power-managed (can be
        put into suspend mode, and so on). The property
        does not indicate that power management features
        are currently enabled, only that the logical device
        is capable of power management. This property is
        inherited from CIM_LogicalDevice."
    ::= { win32LogicalDiskEntry 26 }

osldProviderName  OBJECT-TYPE
    SYNTAX     WtcsDisplayString
    MAX-ACCESS read-only
    STATUS     current
    DESCRIPTION
        "Network path to the logical device."
    ::= { win32LogicalDiskEntry 27 }

osldPurpose  OBJECT-TYPE
    SYNTAX     WtcsDisplayString
    MAX-ACCESS read-only
    STATUS     current
    DESCRIPTION
        "Free-form string describing the media and/or its
        use. This property is inherited from
        CIM_StorageExtent."
    ::= { win32LogicalDiskEntry 28 }

osldQuotasDisabled  OBJECT-TYPE
    SYNTAX     TruthValue
    MAX-ACCESS read-only
    STATUS     current
    DESCRIPTION
        "Indicates that quota management is not enabled
        (TRUE) on this system. This property is new for
        Windows XP."
    ::= { win32LogicalDiskEntry 29 }

osldQuotasIncomplete  OBJECT-TYPE
    SYNTAX     TruthValue
    MAX-ACCESS read-only
    STATUS     current
    DESCRIPTION
        "Indicates that the quota management was used but
        has been disabled (TRUE). Incomplete refers to the
        information left in the file system after quota
        management was disabled. This property is new for
        Windows XP."
    ::= { win32LogicalDiskEntry 30 }

osldQuotasRebuilding  OBJECT-TYPE
    SYNTAX     TruthValue
    MAX-ACCESS read-only
    STATUS     current
    DESCRIPTION
        "Indicates that the file system is in the active
        process of compiling information and setting the
        disk up for quota management. This property is new
        for Windows XP."
    ::= { win32LogicalDiskEntry 31 }

osldSize  OBJECT-TYPE
    SYNTAX     Gauge32
    MAX-ACCESS read-only
    STATUS     current
    DESCRIPTION
        "Size of the disk drive. This property is inherited
        from CIM_LogicalDisk."
    ::= { win32LogicalDiskEntry 32 }

osldStatus  OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is online,
        yet the managed element is neither 'OK' nor in one
        of the other states. This property is inherited
        from CIM_ManagedSystemElement."
    ::= { win32LogicalDiskEntry 33 }

osldStatusInfo  OBJECT-TYPE
    SYNTAX     INTEGER {
        other(1),
        unknown(2),
        enabled(3),
        disabled(4),
        notApplicable(5)
    }
    MAX-ACCESS read-only
    STATUS     current
    DESCRIPTION
        "State of the logical device. If this property does
        not apply to the logical device, the value 5 (Not
        Applicable) should be used. This property is
        inherited from CIM_LogicalDevice."
    ::= { win32LogicalDiskEntry 34 }

osldSupportsDiskQuotas  OBJECT-TYPE
    SYNTAX     TruthValue
    MAX-ACCESS read-only
    STATUS     current
    DESCRIPTION
        "If TRUE, this volume supports disk quotas. This
        property is new for Windows XP."
    ::= { win32LogicalDiskEntry 35 }

osldSupportsFileBasedCompression  OBJECT-TYPE
    SYNTAX     TruthValue
    MAX-ACCESS read-only
    STATUS     current
    DESCRIPTION
        "If TRUE, the logical disk partition supports file
        based compression, such as is the case with NTFS
        file system. This property is FALSE, when the
        Compressed property is TRUE."
    ::= { win32LogicalDiskEntry 36 }

osldSystemCreationClassName  OBJECT-TYPE
    SYNTAX     WtcsDisplayString
    MAX-ACCESS read-only
    STATUS     current
    DESCRIPTION
        "Value of the scoping computer's CreationClassName
        property. This property is inherited from
        CIM_LogicalDevice."
    ::= { win32LogicalDiskEntry 37 }

osldSystemName  OBJECT-TYPE
    SYNTAX     WtcsDisplayString
    MAX-ACCESS read-only
    STATUS     current
    DESCRIPTION
        "Name of the scoping system. This property is
        inherited from CIM_LogicalDevice."
    ::= { win32LogicalDiskEntry 38 }

osldVolumeDirty  OBJECT-TYPE
    SYNTAX     TruthValue
    MAX-ACCESS read-only
    STATUS     current
    DESCRIPTION
        "If TRUE, the disk requires ChkDsk to be run at
        next boot up. This property is only applicable to
        those instances of logical disk that represent a
        physical disk in the machine. It is not applicable
        to mapped logical drives. This property is new for
        Windows XP."
    ::= { win32LogicalDiskEntry 39 }

osldVolumeName  OBJECT-TYPE
    SYNTAX     WtcsDisplayString
    MAX-ACCESS read-only
    STATUS     current
    DESCRIPTION
        "Volume name of the logical disk. Constraints:
        maximum 32 characters."
    ::= { win32LogicalDiskEntry 40 }

osldVolumeSerialNumber  OBJECT-TYPE
    SYNTAX     WtcsDisplayString
    MAX-ACCESS read-only
    STATUS     current
    DESCRIPTION
        "Volume serial number of the logical disk.
        Constraints: maximum 11 characters.
        Example: 'A8C3-D032'"
    ::= { win32LogicalDiskEntry 41 }

win32MappedLogicalDiskTable OBJECT-TYPE
    SYNTAX     SEQUENCE OF Win32MappedLogicalDiskEntry
    MAX-ACCESS not-accessible
    STATUS     current
    DESCRIPTION
        "The Win32_MappedLogicalDisk WMI class represents
        network storage devices that are mapped as logical
        disks on the computer system."
    ::= { wmiFileSystem 3 }

win32MappedLogicalDiskEntry OBJECT-TYPE
    SYNTAX     Win32MappedLogicalDiskEntry
    MAX-ACCESS not-accessible
    STATUS     current
    DESCRIPTION
        "None"
    INDEX      { osmldIndex }
    ::= { win32MappedLogicalDiskTable 1 }

Win32MappedLogicalDiskEntry ::= SEQUENCE {
    osmldIndex Integer32,
    osmldAccess  INTEGER,
    osmldAvailability  INTEGER,
    osmldBlockSize  Gauge32,
    osmldCaption  WtcsDisplayString,
    osmldCompressed  TruthValue,
    osmldConfigManagerErrorCode  INTEGER,
    osmldConfigManagerUserConfig  TruthValue,
    osmldCreationClassName  WtcsDisplayString,
    osmldDescription  WtcsDisplayString,
    osmldDeviceID  WtcsDisplayString,
    osmldErrorCleared  TruthValue,
    osmldErrorDescription  WtcsDisplayString,
    osmldErrorMethodology  WtcsDisplayString,
    osmldFileSystem  WtcsDisplayString,
    osmldFreeSpace  Gauge32,
    osmldInstallDate  DateAndTime,
    osmldLastErrorCode  Gauge32,
    osmldMaximumComponentLength  Gauge32,
    osmldName  WtcsDisplayString,
    osmldNumberOfBlocks  Gauge32,
    osmldPNPDeviceID  WtcsDisplayString,
    osmldPowerManagementCapabilities  INTEGER,
    osmldPowerManagementSupported  TruthValue,
    osmldProviderName  WtcsDisplayString,
    osmldPurpose  WtcsDisplayString,
    osmldQuotasDisabled  TruthValue,
    osmldQuotasIncomplete  TruthValue,
    osmldQuotasRebuilding  TruthValue,
    osmldSessionID  WtcsDisplayString,
    osmldSize  Gauge32,
    osmldStatus  INTEGER,
    osmldStatusInfo  INTEGER,
    osmldSupportsDiskQuotas  TruthValue,
    osmldSupportFileBasedCompression  TruthValue,
    osmldSystemCreationClassName  WtcsDisplayString,
    osmldSystemName  WtcsDisplayString,
    osmldVolumeName  WtcsDisplayString,
    osmldVolumeSerialNumber  WtcsDisplayString
}

osmldIndex OBJECT-TYPE
    SYNTAX     Integer32 (1..2147483647)
    MAX-ACCESS read-only
    STATUS     current
    DESCRIPTION
        "The value of this object uniquely identifies the
        instance entry for this class."
    ::= { win32MappedLogicalDiskEntry 1 }

osmldAccess  OBJECT-TYPE
    SYNTAX     INTEGER {
        unknown(0),
        readable(1),
        writeable(2),
        readWriteSupported(3),
        writeOnce(4)
    }
    MAX-ACCESS read-only
    STATUS     current
    DESCRIPTION
        "Device access state. This property is inherited
        from CIM_StorageExtent."
    ::= { win32MappedLogicalDiskEntry 2 }

osmldAvailability  OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17)
    }
    MAX-ACCESS read-only
    STATUS     current
    DESCRIPTION
        "Availability and status of the device. Power Save
        - Unknown indicates that the device is known to be
        in a power save mode, but its exact status is
        unknown; Power Save - Low Power Mode indicates that
        the device is in a power save state but still
        functioning, and may exhibit degraded performance;
        Power Save - Standby indicates that the device is
        not functioning but could be brought to full power
        quickly; and Power Save - Warning indicates that
        the device is in a warning state, though also in a
        power save mode. This property is inherited from
        CIM_LogicalDevice."
    ::= { win32MappedLogicalDiskEntry 3 }

osmldBlockSize  OBJECT-TYPE
    SYNTAX     Gauge32
    UNITS "Bytes"
    MAX-ACCESS read-only
    STATUS     current
    DESCRIPTION
        "Size, in bytes, of the blocks which form this
        storage extent. If this concept is not valid for
        the device type, the value is 1. This property is
        inherited from CIM_StorageExtent."
    ::= { win32MappedLogicalDiskEntry 4 }

osmldCaption  OBJECT-TYPE
    SYNTAX     WtcsDisplayString
    MAX-ACCESS read-only
    STATUS     current
    DESCRIPTION
        "Short description (one-line string) of the object.
        This property is inherited from
        CIM_ManagedSystemElement."
    ::= { win32MappedLogicalDiskEntry 5 }

osmldCompressed  OBJECT-TYPE
    SYNTAX     TruthValue
    MAX-ACCESS read-only
    STATUS     current
    DESCRIPTION
        "If TRUE, the file is compressed. This property is
        inherited from CIM_ManagedSystemElement."
    ::= { win32MappedLogicalDiskEntry 6 }

osmldConfigManagerErrorCode  OBJECT-TYPE
    SYNTAX     INTEGER {
        workingProperly (0), -- This device is working properly. 
        notConfigured (1), -- This device is not configured correctly. 
        cannotLoad (2), -- Windows cannot load the driver for this device. 
        lowResource (3), -- The driver for this device might be corrupted, or your system may be running low on memory or other resources. 
        driverCorrupted (4), -- This device is not working properly. One of its drivers or your registry might be corrupted. 
        needResource (5), -- The driver for this device needs a resource that Windows cannot manage. 
        bootConflicts (6), -- The boot configuration for this device conflicts with other devices. 
        cannotFilter (7), -- Cannot filter. 
        driverLoaderMissing (8), -- The driver loader for the device is missing. 
        resourceIncorrect (9), -- This device is not working properly because the controlling firmware is reporting the resources for the device incorrectly. 
        cannotStart (10), -- This device cannot start. 
        deviceFailed (11), -- This device failed. 
        noFreeResources (12), -- This device cannot find enough free resources that it can use. 
        cannotVerifyResources (13), -- Windows cannot verify this device's resources. 
        restartComputer (14), -- This device cannot work properly until you restart your computer. 
        reenumerationProblem (15), -- This device is not working properly because there is probably a re-enumeration problem. 
        cannotIdentify (16), -- Windows cannot identify all the resources this device uses. 
        unknownResourceType (17), -- This device is asking for an unknown resource type. 
        reinstallDrivers (18), -- Reinstall the drivers for this device. 
        failedVXDloader (19), -- Failure using the VXD loader. 
        registryCorrupted (20), -- Your registry might be corrupted. 
        systemFailure (21), -- System failure: Try changing the driver for this device. If that does not work, see your hardware documentation. Windows is removing this device. 
        deviceDisabled (22), -- This device is disabled. 
        systemFailuer2 (23), -- System failure: Try changing the driver for this device. If that doesn't work, see your hardware documentation. 
        deviceProblem (24), -- This device is not present, is not working properly, or does not have all its drivers installed. 
        settingUpDevice (25), -- Windows is still setting up this device. 
        settingUpDevice2 (26), -- Windows is still setting up this device. 
        invalidLogConfiguration (27), -- This device does not have valid log configuration. 
        driversNotInstalled (28), -- The drivers for this device are not installed. 
        missingResources (29), -- This device is disabled because the firmware of the device did not give it the required resources. 
        conflictIRQ (30), -- This device is using an Interrupt Request (IRQ) resource that another device is using. 
        cannotLoadDrivers (31) -- This device is not working properly because Windows cannot load the drivers required for this device.
    }
    MAX-ACCESS read-only
    STATUS     current
    DESCRIPTION
        "Windows Configuration Manager error code. This
        property is inherited from CIM_LogicalDevice."
    ::= { win32MappedLogicalDiskEntry 7 }

osmldConfigManagerUserConfig  OBJECT-TYPE
    SYNTAX     TruthValue
    MAX-ACCESS read-only
    STATUS     current
    DESCRIPTION
        "If TRUE, the device is using a user-defined
        configuration. This property is inherited from
        CIM_LogicalDevice."
    ::= { win32MappedLogicalDiskEntry 8 }

osmldCreationClassName  OBJECT-TYPE
    SYNTAX     WtcsDisplayString (SIZE (0..256))
    MAX-ACCESS read-only
    STATUS     current
    DESCRIPTION
        "Name of the first concrete class to appear in the
        inheritance chain used in the creation of an
        instance. When used with the other key properties
        of the class, the property allows all instances of
        this class and its subclasses to be uniquely
        identified. This property is inherited from
        CIM_LogicalDevice."
    ::= { win32MappedLogicalDiskEntry 9 }

osmldDescription  OBJECT-TYPE
    SYNTAX     WtcsDisplayString
    MAX-ACCESS read-only
    STATUS     current
    DESCRIPTION
        "Description of the object. This property is
        inherited from CIM_ManagedSystemElement."
    ::= { win32MappedLogicalDiskEntry 10 }

osmldDeviceID  OBJECT-TYPE
    SYNTAX     WtcsDisplayString
    MAX-ACCESS read-only
    STATUS     current
    DESCRIPTION
        "Unique identifier of the memory array. This
        property is inherited from CIM_LogicalDevice.
        Example: 'Memory Array 1'"
    ::= { win32MappedLogicalDiskEntry 11 }

osmldErrorCleared  OBJECT-TYPE
    SYNTAX     TruthValue
    MAX-ACCESS read-only
    STATUS     current
    DESCRIPTION
        "If TRUE, the error reported in LastErrorCode is
        now cleared. This property is inherited from
        CIM_LogicalDevice."
    ::= { win32MappedLogicalDiskEntry 12 }

osmldErrorDescription  OBJECT-TYPE
    SYNTAX     WtcsDisplayString
    MAX-ACCESS read-only
    STATUS     current
    DESCRIPTION
        "More information about the error recorded in
        LastErrorCode, and information on any corrective
        actions that may be taken. This property is
        inherited from CIM_LogicalDevice."
    ::= { win32MappedLogicalDiskEntry 13 }

osmldErrorMethodology  OBJECT-TYPE
    SYNTAX     WtcsDisplayString
    MAX-ACCESS read-only
    STATUS     current
    DESCRIPTION
        "Types of error checking used by the hardware. This
        property is inherited from CIM_StorageExtent."
    ::= { win32MappedLogicalDiskEntry 14 }

osmldFileSystem  OBJECT-TYPE
    SYNTAX     WtcsDisplayString
    MAX-ACCESS read-only
    STATUS     current
    DESCRIPTION
        "File system on the logical disk.
        Example: 'NTFS'"
    ::= { win32MappedLogicalDiskEntry 15 }

osmldFreeSpace  OBJECT-TYPE
    SYNTAX     Gauge32
    UNITS "Bytes"
    MAX-ACCESS read-only
    STATUS     current
    DESCRIPTION
        "Space available on the logical disk. This property
        is inherited from CIM_LogicalDisk."
    ::= { win32MappedLogicalDiskEntry 16 }

osmldInstallDate  OBJECT-TYPE
    SYNTAX     DateAndTime
    MAX-ACCESS read-only
    STATUS     current
    DESCRIPTION
        "Date and time when the object was installed. This
        property does not need a value to indicate that the
        object is installed. This property is inherited
        from CIM_ManagedSystemElement."
    ::= { win32MappedLogicalDiskEntry 17 }

osmldLastErrorCode  OBJECT-TYPE
    SYNTAX     Gauge32
    MAX-ACCESS read-only
    STATUS     current
    DESCRIPTION
        "Last error code reported by the logical device.
        This property is inherited from CIM_LogicalDevice."
    ::= { win32MappedLogicalDiskEntry 18 }

osmldMaximumComponentLength  OBJECT-TYPE
    SYNTAX     Gauge32
    MAX-ACCESS read-only
    STATUS     current
    DESCRIPTION
        "Contains the maximum length of a filename
        component supported by the Windows drive.
        Example: 255"
    ::= { win32MappedLogicalDiskEntry 19 }

osmldName  OBJECT-TYPE
    SYNTAX     WtcsDisplayString
    MAX-ACCESS read-only
    STATUS     current
    DESCRIPTION
        "Object label. This property is inherited from
        CIM_ManagedSystemElement."
    ::= { win32MappedLogicalDiskEntry 20 }

osmldNumberOfBlocks  OBJECT-TYPE
    SYNTAX     Gauge32
    MAX-ACCESS read-only
    STATUS     current
    DESCRIPTION
        "Total number of consecutive blocks, each block the
        size of the value contained in the BlockSize
        property, which form this storage extent. Total
        size of the storage extent can be calculated by
        multiplying the value of the BlockSize property by
        the value of this property. If the value of
        BlockSize is 1, this property is the total size of
        the storage extent. This property is inherited from
        CIM_StorageExtent."
    ::= { win32MappedLogicalDiskEntry 21 }

osmldPNPDeviceID  OBJECT-TYPE
    SYNTAX     WtcsDisplayString
    MAX-ACCESS read-only
    STATUS     current
    DESCRIPTION
        "Windows Plug and Play device identifier of the
        logical device. This property is inherited from
        CIM_LogicalDevice.
        Example: '*PNP030b'"
    ::= { win32MappedLogicalDiskEntry 22 }

osmldPowerManagementCapabilities  OBJECT-TYPE
    SYNTAX     INTEGER {
        unknown(0),
        notSupported(1),
        disabled(2),
        enabled(3),
        powerSavingModesEnterAutomatic(4),
        powerStateSettable(5),
        powerCyclingSupported(6),
        timedPowerOnSupported(7)
    }
    MAX-ACCESS read-only
    STATUS     current
    DESCRIPTION
        "Array of the specific power-related capabilities
        of a logical device. The Enabled value indicates
        that the power management features are currently
        enabled but the exact feature set is unknown or the
        information is unavailable. Power Saving Modes
        Entered Automatically indicates that a device can
        change its power state based on usage or other
        criteria. Power State Settable indicates that the
        SetPowerState method is supported. Power Cycling
        Supported indicates that the SetPowerState method
        can be invoked with the PowerState parameter set to
        5 (Power Cycle). Timed Power On Supported indicates
        that the SetPowerState method can be invoked with
        the PowerState parameter set to 5 (Power Cycle) and
        Time set to a specific date and time, or interval,
        for power-on. This property is inherited from
        CIM_LogicalDevice."
    ::= { win32MappedLogicalDiskEntry 23 }

osmldPowerManagementSupported  OBJECT-TYPE
    SYNTAX     TruthValue
    MAX-ACCESS read-only
    STATUS     current
    DESCRIPTION
        "If TRUE, the device can be power-managed (can be
        put into suspend mode, and so on). The property
        does not indicate that power management features
        are currently enabled, only that the logical device
        is capable of power management. This property is
        inherited from CIM_LogicalDevice."
    ::= { win32MappedLogicalDiskEntry 24 }

osmldProviderName  OBJECT-TYPE
    SYNTAX     WtcsDisplayString
    MAX-ACCESS read-only
    STATUS     current
    DESCRIPTION
        "Network path name to the logical device."
    ::= { win32MappedLogicalDiskEntry 25 }

osmldPurpose  OBJECT-TYPE
    SYNTAX     WtcsDisplayString
    MAX-ACCESS read-only
    STATUS     current
    DESCRIPTION
        "Free-form string describing the media and/or its
        use. This property is inherited from
        CIM_StorageExtent."
    ::= { win32MappedLogicalDiskEntry 26 }

osmldQuotasDisabled  OBJECT-TYPE
    SYNTAX     TruthValue
    MAX-ACCESS read-only
    STATUS     current
    DESCRIPTION
        "If TRUE, quota management is not enabled for this
        volume."
    ::= { win32MappedLogicalDiskEntry 27 }

osmldQuotasIncomplete  OBJECT-TYPE
    SYNTAX     TruthValue
    MAX-ACCESS read-only
    STATUS     current
    DESCRIPTION
        "If TRUE, quota management was used but has been
        disabled. Incomplete refers to the information left
        in the file system after quota management has been
        disabled."
    ::= { win32MappedLogicalDiskEntry 28 }

osmldQuotasRebuilding  OBJECT-TYPE
    SYNTAX     TruthValue
    MAX-ACCESS read-only
    STATUS     current
    DESCRIPTION
        "If TRUE, the file system is setting up for quota
        management."
    ::= { win32MappedLogicalDiskEntry 29 }

osmldSessionID  OBJECT-TYPE
    SYNTAX     WtcsDisplayString
    MAX-ACCESS read-only
    STATUS     current
    DESCRIPTION
        "ID of the user's session. The user may be
        connected using a local login or a terminal
        session."
    ::= { win32MappedLogicalDiskEntry 30 }

osmldSize  OBJECT-TYPE
    SYNTAX     Gauge32
    UNITS "Bytes"
    MAX-ACCESS read-only
    STATUS     current
    DESCRIPTION
        "Size of the logical disk."
    ::= { win32MappedLogicalDiskEntry 31 }

osmldStatus  OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is on-line,
        yet the managed element is neither 'OK' nor in one
        of the other states. This property is inherited
        from CIM_ManagedSystemElement."
    ::= { win32MappedLogicalDiskEntry 32 }

osmldStatusInfo  OBJECT-TYPE
    SYNTAX     INTEGER {
        other(1),
        unknown(2),
        enabled(3),
        disabled(4),
        notApplicable(5)
    }
    MAX-ACCESS read-only
    STATUS     current
    DESCRIPTION
        "State of the logical device. If this property does
        not apply to the logical device, the value 5 (Not
        Applicable) should be used. This property is
        inherited from CIM_LogicalDevice."
    ::= { win32MappedLogicalDiskEntry 33 }

osmldSupportsDiskQuotas  OBJECT-TYPE
    SYNTAX     TruthValue
    MAX-ACCESS read-only
    STATUS     current
    DESCRIPTION
        "If TRUE, this volume supports disk quotas."
    ::= { win32MappedLogicalDiskEntry 34 }

osmldSupportFileBasedCompression  OBJECT-TYPE
    SYNTAX     TruthValue
    MAX-ACCESS read-only
    STATUS     current
    DESCRIPTION
        "If TRUE, the logical disk partition supports file
        based compression, such as is the case with NTFS.
        This property is FALSE, when the Compressed
        property is TRUE."
    ::= { win32MappedLogicalDiskEntry 35 }

osmldSystemCreationClassName  OBJECT-TYPE
    SYNTAX     WtcsDisplayString
    MAX-ACCESS read-only
    STATUS     current
    DESCRIPTION
        "Value of the scoping computer's CreationClassName
        property. This property is inherited from
        CIM_LogicalDevice."
    ::= { win32MappedLogicalDiskEntry 36 }

osmldSystemName  OBJECT-TYPE
    SYNTAX     WtcsDisplayString
    MAX-ACCESS read-only
    STATUS     current
    DESCRIPTION
        "Name of the scoping system. This property is
        inherited from CIM_LogicalDevice."
    ::= { win32MappedLogicalDiskEntry 37 }

osmldVolumeName  OBJECT-TYPE
    SYNTAX     WtcsDisplayString
    MAX-ACCESS read-only
    STATUS     current
    DESCRIPTION
        "Volume name of the logical disk. This property
        value may have a maximum of 32 characters."
    ::= { win32MappedLogicalDiskEntry 38 }

osmldVolumeSerialNumber  OBJECT-TYPE
    SYNTAX     WtcsDisplayString
    MAX-ACCESS read-only
    STATUS     current
    DESCRIPTION
        "Volume serial number of the logical disk. This
        property value may have a maximum of 11 characters.
        This property is inherited from CIM_LogicalDevice.
        Example: 'A8C3-D032'"
    ::= { win32MappedLogicalDiskEntry 39 }

win32QuotaSettingTable OBJECT-TYPE
    SYNTAX     SEQUENCE OF Win32QuotaSettingEntry
    MAX-ACCESS not-accessible
    STATUS     current
    DESCRIPTION
        "The Win32_QuotaSetting WMI class contains setting
        information for disk quotas on a volume. This class
        is new for Windows XP."
    ::= { wmiFileSystem 4 }

win32QuotaSettingEntry OBJECT-TYPE
    SYNTAX     Win32QuotaSettingEntry
    MAX-ACCESS not-accessible
    STATUS     current
    DESCRIPTION
        "None"
    INDEX      { osqsIndex }
    ::= { win32QuotaSettingTable 1 }

Win32QuotaSettingEntry ::= SEQUENCE {
    osqsIndex Integer32,
    osqsCaption  WtcsDisplayString,
    osqsDefaultLimit  WtcsDisplayString,
    osqsDefaultWarningLimit  WtcsDisplayString,
    osqsDescription  WtcsDisplayString,
    osqsExceededNotification  TruthValue,
    osqsSettingID  WtcsDisplayString,
    osqsState  INTEGER,
    osqsVolumePath  WtcsDisplayString,
    osqsWarningExceededNotification  TruthValue
}

osqsIndex OBJECT-TYPE
    SYNTAX     Integer32 (1..2147483647)
    MAX-ACCESS read-only
    STATUS     current
    DESCRIPTION
        "The value of this object uniquely identifies the
        instance entry for this class."
    ::= { win32QuotaSettingEntry 1 }

osqsCaption  OBJECT-TYPE
    SYNTAX     WtcsDisplayString (SIZE (0..64))
    MAX-ACCESS read-only
    STATUS     current
    DESCRIPTION
        "Short description of the object a one line string.
        This property is inherited from CIM_Setting."
    ::= { win32QuotaSettingEntry 2 }

osqsDefaultLimit  OBJECT-TYPE
    SYNTAX     WtcsDisplayString
    UNITS "Bytes"
    MAX-ACCESS read-only
    STATUS     current
    DESCRIPTION
        "Default limit set for quotas on this specific
        volume."
    ::= { win32QuotaSettingEntry 3 }

osqsDefaultWarningLimit  OBJECT-TYPE
    SYNTAX     WtcsDisplayString
    UNITS "Bytes"
    MAX-ACCESS read-only
    STATUS     current
    DESCRIPTION
        "Default warning limit set for quotas on this
        specific volume."
    ::= { win32QuotaSettingEntry 4 }

osqsDescription  OBJECT-TYPE
    SYNTAX     WtcsDisplayString
    MAX-ACCESS read-only
    STATUS     current
    DESCRIPTION
        "Comment that describes the link. This property is
        inherited from CIM_Setting."
    ::= { win32QuotaSettingEntry 5 }

osqsExceededNotification  OBJECT-TYPE
    SYNTAX     TruthValue
    MAX-ACCESS read-only
    STATUS     current
    DESCRIPTION
        "If TRUE, events are written to the event log when
        quotas are exceeded."
    ::= { win32QuotaSettingEntry 6 }

osqsSettingID  OBJECT-TYPE
    SYNTAX     WtcsDisplayString (SIZE (0..256))
    MAX-ACCESS read-only
    STATUS     current
    DESCRIPTION
        "Name of a CIM_Setting object."
    ::= { win32QuotaSettingEntry 7 }

osqsState  OBJECT-TYPE
    SYNTAX     INTEGER {
        disabled(0),
        tracked(1),
        enforced(2)
    }
    MAX-ACCESS read-only
    STATUS     current
    DESCRIPTION
        "Level of quota management set for this volume."
    ::= { win32QuotaSettingEntry 8 }

osqsVolumePath  OBJECT-TYPE
    SYNTAX     WtcsDisplayString
    MAX-ACCESS read-only
    STATUS     current
    DESCRIPTION
        "Name of the volume where disk quotas are located.
        It can be volume name, volume path (such as D:\\),
        or it can be the unique volume name (such as
        '\\\\?Volume{GUID}\\.')."
    ::= { win32QuotaSettingEntry 9 }

osqsWarningExceededNotification  OBJECT-TYPE
    SYNTAX     TruthValue
    MAX-ACCESS read-only
    STATUS     current
    DESCRIPTION
        "If TRUE, events are written to the event log when
        warnings are exceeded."
    ::= { win32QuotaSettingEntry 10 }

win32VolumeTable OBJECT-TYPE
    SYNTAX     SEQUENCE OF Win32VolumeEntry
    MAX-ACCESS not-accessible
    STATUS     current
    DESCRIPTION
        "The Win32_Volume class represents an area of
        storage on a hard disk. The class returns local
        volumes that are formatted, unformatted, mounted,
        or offline. A volume is formatted by using a file
        system, such as FAT or NTFS, and might have a drive
        letter assigned to it. One hard disk can have
        multiple volumes, and volumes can span multiple
        physical disks. The Win32_Volume class does not
        support disk drive management."
    ::= { wmiFileSystem 5 }

win32VolumeEntry OBJECT-TYPE
    SYNTAX     Win32VolumeEntry
    MAX-ACCESS not-accessible
    STATUS     current
    DESCRIPTION
        "None"
    INDEX      { osvlIndex }
    ::= { win32VolumeTable 1 }

Win32VolumeEntry ::= SEQUENCE {
    osvlIndex Integer32,
    osvlAutomount  TruthValue,
    osvlCapacity  WtcsDisplayString,
    osvlCompressed  TruthValue,
    osvlDeviceId  WtcsDisplayString,
    osvlDirtyBitSet  TruthValue,
    osvlDriveLetter  WtcsDisplayString,
    osvlDriveType  INTEGER,
    osvlFileSystem  WtcsDisplayString,
    osvlFreeSpace  WtcsDisplayString,
    osvlIndexingEnabled  TruthValue,
    osvlLabel  WtcsDisplayString,
    osvlMaximumFileNameLength  Gauge32,
    osvlQuotasEnabled  TruthValue,
    osvlQuotasIncomplete  TruthValue,
    osvlQuotasRebuilding  TruthValue,
    osvlSerialNumber  Gauge32,
    osvlSupportsDiskQuotas  TruthValue,
    osvlSupportsFileBasedCompression  TruthValue
}

osvlIndex OBJECT-TYPE
    SYNTAX     Integer32 (1..2147483647)
    MAX-ACCESS read-only
    STATUS     current
    DESCRIPTION
        "The value of this object uniquely identifies the
        instance entry for this class."
    ::= { win32VolumeEntry 1 }

osvlAutomount  OBJECT-TYPE
    SYNTAX     TruthValue
    MAX-ACCESS read-only
    STATUS     current
    DESCRIPTION
        "If true, the volume is mounted to the file system
        automatically when the first I/O is issued. If
        false, the volume is not mounted until explicitly
        mounted by using the Mount method, or by adding a
        drive letter or mount point."
    ::= { win32VolumeEntry 2 }

osvlCapacity  OBJECT-TYPE
    SYNTAX     WtcsDisplayString
    MAX-ACCESS read-only
    STATUS     current
    DESCRIPTION
        "Size of the volume in bytes."
    ::= { win32VolumeEntry 3 }

osvlCompressed  OBJECT-TYPE
    SYNTAX     TruthValue
    MAX-ACCESS read-only
    STATUS     current
    DESCRIPTION
        "If true the volume exists as one compressed
        entity, such as a DoubleSpace volume. If file-based
        compression is supported, such as the NTFS file
        system, this property is false."
    ::= { win32VolumeEntry 4 }

osvlDeviceId  OBJECT-TYPE
    SYNTAX     WtcsDisplayString
    MAX-ACCESS read-only
    STATUS     current
    DESCRIPTION
        "Unique identifier for the volume on this system."
    ::= { win32VolumeEntry 5 }

osvlDirtyBitSet  OBJECT-TYPE
    SYNTAX     TruthValue
    MAX-ACCESS read-only
    STATUS     current
    DESCRIPTION
        "If true, the Chkdsk method is automatically run by
        the system at the next boot up."
    ::= { win32VolumeEntry 6 }

osvlDriveLetter  OBJECT-TYPE
    SYNTAX     WtcsDisplayString
    MAX-ACCESS read-only
    STATUS     current
    DESCRIPTION
        "Drive letter assigned to a volume. This property
        is NULL for volumes without drive letters."
    ::= { win32VolumeEntry 7 }

osvlDriveType  OBJECT-TYPE
    SYNTAX     INTEGER {
        unknown(0),
        noRootDirectory(1),
        removableDisk(2),
        localDisk(3),
        networkDrive(4),
        compactDisk(5),
        ramDisk(6)
    }
    MAX-ACCESS read-only
    STATUS     current
    DESCRIPTION
        "Numeric value that corresponds to the type of disk
        drive that this logical disk represents."
    ::= { win32VolumeEntry 8 }

osvlFileSystem  OBJECT-TYPE
    SYNTAX     WtcsDisplayString
    MAX-ACCESS read-only
    STATUS     current
    DESCRIPTION
        "File system on the logical disk.
        Example: NTFS"
    ::= { win32VolumeEntry 9 }

osvlFreeSpace  OBJECT-TYPE
    SYNTAX     WtcsDisplayString
    MAX-ACCESS read-only
    STATUS     current
    DESCRIPTION
        "Number of bytes of available space on the volume."
    ::= { win32VolumeEntry 10 }

osvlIndexingEnabled  OBJECT-TYPE
    SYNTAX     TruthValue
    MAX-ACCESS read-only
    STATUS     current
    DESCRIPTION
        "If true, context indexing is enabled."
    ::= { win32VolumeEntry 11 }

osvlLabel  OBJECT-TYPE
    SYNTAX     WtcsDisplayString
    MAX-ACCESS read-only
    STATUS     current
    DESCRIPTION
        "Volume name of the logical disk. This property is
        null for volumes without a label. For FAT, FAT32
        systems the maximum length is 11 characters. For
        NTFS file systems the maximum length is 32
        characters."
    ::= { win32VolumeEntry 12 }

osvlMaximumFileNameLength  OBJECT-TYPE
    SYNTAX     Gauge32
    MAX-ACCESS read-only
    STATUS     current
    DESCRIPTION
        "Maximum length, in characters, of a filename
        component supported by a Windows drive. A filename
        component is the portion of a filename between
        backslashes. This value can be used to indicate
        that long names are supported by the file system.
        For example, for a FAT file system that supports
        long names, the property stores the value 255 not
        the previous 8.3 indicator. Long names can be
        supported on systems that use the NTFS file system.
        Example: 255"
    ::= { win32VolumeEntry 13 }

osvlQuotasEnabled  OBJECT-TYPE
    SYNTAX     TruthValue
    MAX-ACCESS read-only
    STATUS     current
    DESCRIPTION
        "If true, quota management is enabled for this
        volume."
    ::= { win32VolumeEntry 14 }

osvlQuotasIncomplete  OBJECT-TYPE
    SYNTAX     TruthValue
    MAX-ACCESS read-only
    STATUS     current
    DESCRIPTION
        "If true, quota management was used but is
        disabled. Incomplete refers to the information left
        in the file system after quota management is
        disabled."
    ::= { win32VolumeEntry 15 }

osvlQuotasRebuilding  OBJECT-TYPE
    SYNTAX     TruthValue
    MAX-ACCESS read-only
    STATUS     current
    DESCRIPTION
        "If true, the file system is in the process of
        compiling information and setting the disk up for
        quota management."
    ::= { win32VolumeEntry 16 }

osvlSerialNumber  OBJECT-TYPE
    SYNTAX     Gauge32
    MAX-ACCESS read-only
    STATUS     current
    DESCRIPTION
        "Serial number of the volume.
        Example: A8C3D032"
    ::= { win32VolumeEntry 17 }

osvlSupportsDiskQuotas  OBJECT-TYPE
    SYNTAX     TruthValue
    MAX-ACCESS read-only
    STATUS     current
    DESCRIPTION
        "If true, the volume supports disk quotas."
    ::= { win32VolumeEntry 18 }

osvlSupportsFileBasedCompression  OBJECT-TYPE
    SYNTAX     TruthValue
    MAX-ACCESS read-only
    STATUS     current
    DESCRIPTION
        "If true, the volume supports file-based
        compression like the NTFS file system."
    ::= { win32VolumeEntry 19 }

wmiJobObjects OBJECT-IDENTITY
    STATUS     current
    DESCRIPTION
        "The Job Objects subcategory groups classes that
        represent classes that provide the means of
        instrumenting named job objects. An unnamed job
        object cannot be instrumented."
    ::= { wmiOperatingSystem 4 }

win32NamedJobObjectTable OBJECT-TYPE
    SYNTAX     SEQUENCE OF Win32NamedJobObjectEntry
    MAX-ACCESS not-accessible
    STATUS     current
    DESCRIPTION
        "The Win32_NamedJobObject WMI class represents a
        kernel object that is used to group processes for
        controlling the life and resources of the processes
        within the job object. Only the job objects that
        are named are instrumented. This class is new for
        Windows XP."
    ::= { wmiJobObjects 1 }

win32NamedJobObjectEntry OBJECT-TYPE
    SYNTAX     Win32NamedJobObjectEntry
    MAX-ACCESS not-accessible
    STATUS     current
    DESCRIPTION
        "None"
    INDEX      { osnjoIndex }
    ::= { win32NamedJobObjectTable 1 }

Win32NamedJobObjectEntry ::= SEQUENCE {
    osnjoIndex Integer32,
    osnjoBasicUIRestrictions  INTEGER,
    osnjoCaption  WtcsDisplayString,
    osnjoCollectionID  WtcsDisplayString,
    osnjoDescription  WtcsDisplayString
}

osnjoIndex OBJECT-TYPE
    SYNTAX     Integer32 (1..2147483647)
    MAX-ACCESS read-only
    STATUS     current
    DESCRIPTION
        "The value of this object uniquely identifies the
        instance entry for this class."
    ::= { win32NamedJobObjectEntry 1 }

osnjoBasicUIRestrictions  OBJECT-TYPE
    SYNTAX     INTEGER {
        desktop(1),
        displaySettings(2),
        exitWindows(4),
        globalAtoms(8),
        handles(16),
        readClipboard(32),
        systemParameters(64),
        writeClipboard(128)
    }
    MAX-ACCESS read-only
    STATUS     current
    DESCRIPTION
        "Restrictions on a job regarding the user
        interface."
    ::= { win32NamedJobObjectEntry 2 }

osnjoCaption  OBJECT-TYPE
    SYNTAX     WtcsDisplayString (SIZE (0..64))
    MAX-ACCESS read-only
    STATUS     current
    DESCRIPTION
        "Short description of the object a one-line string.
        This property is inherited from
        CIM_ManagedSystemElement."
    ::= { win32NamedJobObjectEntry 3 }

osnjoCollectionID  OBJECT-TYPE
    SYNTAX     WtcsDisplayString (SIZE (0..256))
    MAX-ACCESS read-only
    STATUS     current
    DESCRIPTION
        "Number that identifies a job object. Because they
        are kernel objects, job object names are case
        sensitive. However, Windows Management
        Instrumentation (WMI) keys are case insensitive and
        must be decorated to distinguish case. To indicate
        a capital letter, precede the letter by using a
        backslash. For example, 'A' and 'a' are lowercase
        and '\A' and '\a' are uppercase. This property
        overrides the CollectionID property in
        CIM_CollectionofMSEs."
    ::= { win32NamedJobObjectEntry 4 }

osnjoDescription  OBJECT-TYPE
    SYNTAX     WtcsDisplayString
    MAX-ACCESS read-only
    STATUS     current
    DESCRIPTION
        "Description of the object. This property is
        inherited from CIM_ManagedSystemElement."
    ::= { win32NamedJobObjectEntry 5 }

win32NamedJobObjectActgInfoTable OBJECT-TYPE
    SYNTAX     SEQUENCE OF Win32NamedJobObjectActgInfoEntry
    MAX-ACCESS not-accessible
    STATUS     current
    DESCRIPTION
        "The Win32_NamedJobObjectActgInfo WMI class class
        represents the I/O accounting information for a job
        object. This class is new for Windows XP."
    ::= { wmiJobObjects 2 }

win32NamedJobObjectActgInfoEntry OBJECT-TYPE
    SYNTAX     Win32NamedJobObjectActgInfoEntry
    MAX-ACCESS not-accessible
    STATUS     current
    DESCRIPTION
        "None"
    INDEX      { osjoaIndex }
    ::= { win32NamedJobObjectActgInfoTable 1 }

Win32NamedJobObjectActgInfoEntry ::= SEQUENCE {
    osjoaIndex Integer32,
    osjoaActiveProcesses  Gauge32,
    osjoaCaption  WtcsDisplayString,
    osjoaDescription  WtcsDisplayString,
    osjoaName  WtcsDisplayString,
    osjoaOtherOperationCount  Gauge32,
    osjoaOtherTransferCount  Gauge32,
    osjoaPeakJobMemoryUsed  Gauge32,
    osjoaPeakProcessMemoryUsed  Gauge32,
    osjoaReadOperationCount  Gauge32,
    osjoaReadTransferCount  Gauge32,
    osjoaThisPeriodTotalKernelTime  WtcsDisplayString,
    osjoaThisPeriodTotalUserTime  WtcsDisplayString,
    osjoaTotalKernelTime  WtcsDisplayString,
    osjoaTotalPageFaultCount  Gauge32,
    osjoaTotalProcesses  Gauge32,
    osjoaTotalTerminatedProcesses  Gauge32,
    osjoaTotalUserTime  WtcsDisplayString,
    osjoaWriteOperationCount  Gauge32,
    osjoaWriteTransferCount  Gauge32
}

osjoaIndex OBJECT-TYPE
    SYNTAX     Integer32 (1..2147483647)
    MAX-ACCESS read-only
    STATUS     current
    DESCRIPTION
        "The value of this object uniquely identifies the
        instance entry for this class."
    ::= { win32NamedJobObjectActgInfoEntry 1 }

osjoaActiveProcesses  OBJECT-TYPE
    SYNTAX     Gauge32
    MAX-ACCESS read-only
    STATUS     current
    DESCRIPTION
        "Total number of processes associated with a job.
        When a process is associated with a job, but the
        association fails because of a limit violation, the
        value is temporarily incremented. When the
        terminated process exits and all references to the
        process are released, the value is decremented."
    ::= { win32NamedJobObjectActgInfoEntry 2 }

osjoaCaption  OBJECT-TYPE
    SYNTAX     WtcsDisplayString (SIZE (0..64))
    MAX-ACCESS read-only
    STATUS     current
    DESCRIPTION
        "Short description (one-line string) of the object.
        This property is inherited from
        CIM_ManagedSystemElement."
    ::= { win32NamedJobObjectActgInfoEntry 3 }

osjoaDescription  OBJECT-TYPE
    SYNTAX     WtcsDisplayString
    MAX-ACCESS read-only
    STATUS     current
    DESCRIPTION
        "Description of the object. This property is
        inherited from CIM_StatisticalInformation."
    ::= { win32NamedJobObjectActgInfoEntry 4 }

osjoaName  OBJECT-TYPE
    SYNTAX     WtcsDisplayString (SIZE (0..256))
    MAX-ACCESS read-only
    STATUS     current
    DESCRIPTION
        "Label by which the statistic or metric is known.
        When subclassed, the property can be overridden to
        be a key property. This property overrides the Name
        property in CIM_StatisticalInformation."
    ::= { win32NamedJobObjectActgInfoEntry 5 }

osjoaOtherOperationCount  OBJECT-TYPE
    SYNTAX     Gauge32
    MAX-ACCESS read-only
    STATUS     current
    DESCRIPTION
        "Number of I/O operations performed other than read
        and write operations by all processes that have
        been associated with the job including all
        processes currently associated with the job."
    ::= { win32NamedJobObjectActgInfoEntry 6 }

osjoaOtherTransferCount  OBJECT-TYPE
    SYNTAX     Gauge32
    MAX-ACCESS read-only
    STATUS     current
    DESCRIPTION
        "Number of bytes transferred during operations
        other than read and write by all processes that
        have been associated with the job including all
        processes currently associated with the job."
    ::= { win32NamedJobObjectActgInfoEntry 7 }

osjoaPeakJobMemoryUsed  OBJECT-TYPE
    SYNTAX     Gauge32
    UNITS "KB"
    MAX-ACCESS read-only
    STATUS     current
    DESCRIPTION
        "Peak memory in kilobyte usage of all processes
        associated with the job."
    ::= { win32NamedJobObjectActgInfoEntry 8 }

osjoaPeakProcessMemoryUsed  OBJECT-TYPE
    SYNTAX     Gauge32
    UNITS "KB"
    MAX-ACCESS read-only
    STATUS     current
    DESCRIPTION
        "The most process memory in kilobytes used by any
        process ever associated with the job."
    ::= { win32NamedJobObjectActgInfoEntry 9 }

osjoaReadOperationCount  OBJECT-TYPE
    SYNTAX     Gauge32
    MAX-ACCESS read-only
    STATUS     current
    DESCRIPTION
        "Number of read operations performed by all
        processes that have ever been associated with the
        job, in addition to all processes currently
        associated with the job."
    ::= { win32NamedJobObjectActgInfoEntry 10 }

osjoaReadTransferCount  OBJECT-TYPE
    SYNTAX     Gauge32
    MAX-ACCESS read-only
    STATUS     current
    DESCRIPTION
        "Number of bytes read by all processes that have
        been associated with the job including all
        processes currently associated with the job."
    ::= { win32NamedJobObjectActgInfoEntry 11 }

osjoaThisPeriodTotalKernelTime  OBJECT-TYPE
    SYNTAX     WtcsDisplayString
    UNITS "100ns"
    MAX-ACCESS read-only
    STATUS     current
    DESCRIPTION
        "Total amount of kernel-mode execution time, in 100
        nanosecond units, for all active processes
        associated with the job (and all terminated
        processes no longer associated with the job) after
        the last call that set a per-job kernel-mode time
        limit. This property is set to 0 (zero) when a job
        is created, and each time a per-job kernel-mode
        time limit is established."
    ::= { win32NamedJobObjectActgInfoEntry 12 }

osjoaThisPeriodTotalUserTime  OBJECT-TYPE
    SYNTAX     WtcsDisplayString
    UNITS "100ns"
    MAX-ACCESS read-only
    STATUS     current
    DESCRIPTION
        "Total amount of user-mode execution time, in 100
        nanosecond units, for all active processes
        associated with the job (and all terminated
        processes no longer associated with the job) since
        the last call that set a per-job user-mode time
        limit. This property is set to 0 (zero) when a job
        is created, and each time a per-job user-mode time
        limit is established"
    ::= { win32NamedJobObjectActgInfoEntry 13 }

osjoaTotalKernelTime  OBJECT-TYPE
    SYNTAX     WtcsDisplayString
    UNITS "100ns"
    MAX-ACCESS read-only
    STATUS     current
    DESCRIPTION
        "Total amount of kernel-mode execution time, in 100
        nanosecond units, for all active processes
        associated with the job, as well as all terminated
        processes no longer associated with the job."
    ::= { win32NamedJobObjectActgInfoEntry 14 }

osjoaTotalPageFaultCount  OBJECT-TYPE
    SYNTAX     Gauge32
    MAX-ACCESS read-only
    STATUS     current
    DESCRIPTION
        "Total number of page faults encountered by all
        active processes associated with the job, as well
        as all terminated processes no longer associated
        with the job."
    ::= { win32NamedJobObjectActgInfoEntry 15 }

osjoaTotalProcesses  OBJECT-TYPE
    SYNTAX     Gauge32
    MAX-ACCESS read-only
    STATUS     current
    DESCRIPTION
        "Total number of processes associated with the job
        during its lifetime, including those that are
        terminated. For example, when a process is
        associated with a job, but the association fails
        because of a limit violation, the value is
        incremented."
    ::= { win32NamedJobObjectActgInfoEntry 16 }

osjoaTotalTerminatedProcesses  OBJECT-TYPE
    SYNTAX     Gauge32
    MAX-ACCESS read-only
    STATUS     current
    DESCRIPTION
        "Total number of processes terminated because of a
        limit violation."
    ::= { win32NamedJobObjectActgInfoEntry 17 }

osjoaTotalUserTime  OBJECT-TYPE
    SYNTAX     WtcsDisplayString
    UNITS "100ns"
    MAX-ACCESS read-only
    STATUS     current
    DESCRIPTION
        "Total amount of user-mode execution time, in 100
        nanosecond units, for all active processes
        associated with a job, and all terminated processes
        not associated with a job."
    ::= { win32NamedJobObjectActgInfoEntry 18 }

osjoaWriteOperationCount  OBJECT-TYPE
    SYNTAX     Gauge32
    MAX-ACCESS read-only
    STATUS     current
    DESCRIPTION
        "Number of write operations performed by all
        processes that have been associated with a job, and
        all processes currently associated with the job."
    ::= { win32NamedJobObjectActgInfoEntry 19 }

osjoaWriteTransferCount  OBJECT-TYPE
    SYNTAX     Gauge32
    MAX-ACCESS read-only
    STATUS     current
    DESCRIPTION
        "Number of bytes written by all processes that have
        been associated with a job, and all processes
        currently associated with a job."
    ::= { win32NamedJobObjectActgInfoEntry 20 }

win32NamedJobObjectLimitSetTable OBJECT-TYPE
    SYNTAX     SEQUENCE OF Win32NamedJobObjectLimitSetEntry
    MAX-ACCESS not-accessible
    STATUS     current
    DESCRIPTION
        "The Win32_NamedJobObjectLimitSetting WMI class
        represents the limit settings for a job object.
        This class is new for Windows XP."
    ::= { wmiJobObjects 3 }

win32NamedJobObjectLimitSetEntry OBJECT-TYPE
    SYNTAX     Win32NamedJobObjectLimitSetEntry
    MAX-ACCESS not-accessible
    STATUS     current
    DESCRIPTION
        "None"
    INDEX      { osjolIndex }
    ::= { win32NamedJobObjectLimitSetTable 1 }

Win32NamedJobObjectLimitSetEntry ::= SEQUENCE {
    osjolIndex Integer32,
    osjolActiveProcessLimit  Gauge32,
    osjolAffinity  Gauge32,
    osjolCaption  WtcsDisplayString,
    osjolDescription  WtcsDisplayString,
    osjolJobMemoryLimit  Gauge32,
    osjolLimitFlags  INTEGER,
    osjolMaximumWorkingSetSize  Gauge32,
    osjolMinimumWorkingSetSize  Gauge32,
    osjolPerJobUserTimeLimit  WtcsDisplayString,
    osjolPerProcessUserTimeLimit  WtcsDisplayString,
    osjolPriorityClass  Gauge32,
    osjolProcessMemoryLimit  Gauge32,
    osjolSchedulingClass  Gauge32,
    osjolSettingID  WtcsDisplayString
}

osjolIndex OBJECT-TYPE
    SYNTAX     Integer32 (1..2147483647)
    MAX-ACCESS read-only
    STATUS     current
    DESCRIPTION
        "The value of this object uniquely identifies the
        instance entry for this class."
    ::= { win32NamedJobObjectLimitSetEntry 1 }

osjolActiveProcessLimit  OBJECT-TYPE
    SYNTAX     Gauge32
    MAX-ACCESS read-only
    STATUS     current
    DESCRIPTION
        "Active process limit for a job. If associating a
        process with a job causes the active process count
        to exceed the limit, the process is terminated and
        the association fails. This property is ignored
        unless the LimitFlags property specifies the Active
        Process Limit value."
    ::= { win32NamedJobObjectLimitSetEntry 2 }

osjolAffinity  OBJECT-TYPE
    SYNTAX     Gauge32
    MAX-ACCESS read-only
    STATUS     current
    DESCRIPTION
        "Processor affinity for all processes associated
        with a job. The affinity of each thread is set to
        this value, but threads are free to set the
        affinity subsequently, when it is a subset of the
        specified affinity mask. Processes cannot set an
        affinity mask. This property is ignored unless
        LimitFlags specifies the Limit Affinity value."
    ::= { win32NamedJobObjectLimitSetEntry 3 }

osjolCaption  OBJECT-TYPE
    SYNTAX     WtcsDisplayString (SIZE (0..64))
    MAX-ACCESS read-only
    STATUS     current
    DESCRIPTION
        "Short description of the object a one-line string.
        This property is inherited from
        CIM_ManagedSystemElement."
    ::= { win32NamedJobObjectLimitSetEntry 4 }

osjolDescription  OBJECT-TYPE
    SYNTAX     WtcsDisplayString
    MAX-ACCESS read-only
    STATUS     current
    DESCRIPTION
        "Description of the object. This property is
        inherited from CIM_ManagedSystemElement."
    ::= { win32NamedJobObjectLimitSetEntry 5 }

osjolJobMemoryLimit  OBJECT-TYPE
    SYNTAX     Gauge32
    MAX-ACCESS read-only
    STATUS     current
    DESCRIPTION
        "Per-job memory limit in kilobytes. This property
        is ignored unless LimitFlags specifies the Limit
        Job Memory value."
    ::= { win32NamedJobObjectLimitSetEntry 6 }

osjolLimitFlags  OBJECT-TYPE
    SYNTAX     INTEGER {
        limitWorkingSet(1),
        limitProcessTime(2),
        limitJobTime(4),
        activeProcessLimit(8),
        limitAffinity(16),
        limitPriorityClass(32),
        limitPreserveJobTime(64),
        limitSchedulingClass(128),
        limitProcessMemory(256),
        limitJobMemory(512),
        limitDieOnUnhandledException(1024),
        limitBreakawayOK(2048),
        silentBreakawayOK(4096)
    }
    MAX-ACCESS read-only
    STATUS     current
    DESCRIPTION
        "Bitmap that represents the job limits. One or more
        of the limits can be in effect at the same time."
    ::= { win32NamedJobObjectLimitSetEntry 7 }

osjolMaximumWorkingSetSize  OBJECT-TYPE
    SYNTAX     Gauge32
    MAX-ACCESS read-only
    STATUS     current
    DESCRIPTION
        "Maximum working set size for all processes
        associated with a job. This property is ignored
        unless LimitFlags specifies the Limit Working Set
        value."
    ::= { win32NamedJobObjectLimitSetEntry 8 }

osjolMinimumWorkingSetSize  OBJECT-TYPE
    SYNTAX     Gauge32
    MAX-ACCESS read-only
    STATUS     current
    DESCRIPTION
        "Minimum working set size for all processes
        associated with a job. This property is ignored
        unless LimitFlags specifies the Limit Working Set
        value."
    ::= { win32NamedJobObjectLimitSetEntry 9 }

osjolPerJobUserTimeLimit  OBJECT-TYPE
    SYNTAX     WtcsDisplayString
    UNITS "100ns"
    MAX-ACCESS read-only
    STATUS     current
    DESCRIPTION
        "Per-job user mode execution time limit, in 100
        nanosecond units. The system adds the current time
        of the processes associated with the job to this
        limit. For example, if you set this limit to 1
        minute, and the job has a process that has
        accumulated 5 minutes of user mode time, the limit
        actually enforced is 6 minutes."
    ::= { win32NamedJobObjectLimitSetEntry 10 }

osjolPerProcessUserTimeLimit  OBJECT-TYPE
    SYNTAX     WtcsDisplayString
    UNITS "100ns"
    MAX-ACCESS read-only
    STATUS     current
    DESCRIPTION
        "Per-process user mode execution time limit, in
        100-nanosecond units. This property is ignored
        unless LimitFlags specifies Limit Process Time. The
        system periodically checks to determine whether or
        not each process associated with the job has
        accumulated more user-mode time than the set limit.
        If it has, the process is terminated."
    ::= { win32NamedJobObjectLimitSetEntry 11 }

osjolPriorityClass  OBJECT-TYPE
    SYNTAX     Gauge32
    MAX-ACCESS read-only
    STATUS     current
    DESCRIPTION
        "Priority class for all processes associated with
        the job. Processes and threads cannot modify their
        priority class. This property is ignored unless
        LimitFlags specifies the Limit Priority value."
    ::= { win32NamedJobObjectLimitSetEntry 12 }

osjolProcessMemoryLimit  OBJECT-TYPE
    SYNTAX     Gauge32
    MAX-ACCESS read-only
    STATUS     current
    DESCRIPTION
        "Per-process memory limit in kilobytes. This
        property is ignored unless LimitFlags specifies the
        Limit Process Memory value."
    ::= { win32NamedJobObjectLimitSetEntry 13 }

osjolSchedulingClass  OBJECT-TYPE
    SYNTAX     Gauge32
    MAX-ACCESS read-only
    STATUS     current
    DESCRIPTION
        "Scheduling class for all processes associated with
        the job. The valid values are 0 to 9. Use 0 (zero)
        for the least favorable scheduling class relative
        to other threads, and 9 for the most favorable
        scheduling class relative to other threads. This
        property is ignored unless LimitFlags specifies the
        Limit Scheduling Class value."
    ::= { win32NamedJobObjectLimitSetEntry 14 }

osjolSettingID  OBJECT-TYPE
    SYNTAX     WtcsDisplayString (SIZE (0..256))
    MAX-ACCESS read-only
    STATUS     current
    DESCRIPTION
        "Job object limit setting instance. Because they
        are kernel objects, job object names are
        case-sensitive. However, Windows Management
        Instrumentation (WMI) keys are case-insensitive and
        must be decorated to distinguish case. To indicate
        a capital letter, precede the letter by a
        backslash. For example, 'A' and 'a' are lowercase
        and '\A' and '\a' are uppercase."
    ::= { win32NamedJobObjectLimitSetEntry 15 }

wmiPageFiles OBJECT-IDENTITY
    STATUS     current
    DESCRIPTION
        "The Memory and Page files subcategory groups
        classes that represent page file configuration
        settings."
    ::= { wmiOperatingSystem 5 }

win32PageFileTable OBJECT-TYPE
    SYNTAX     SEQUENCE OF Win32PageFileEntry
    MAX-ACCESS not-accessible
    STATUS     current
    DESCRIPTION
        "The Win32_PageFile WMI class represents the file
        used for handling virtual memory file swapping on a
        Win32 system. This class has been deprecated."
    ::= { wmiPageFiles 1 }

win32PageFileEntry OBJECT-TYPE
    SYNTAX     Win32PageFileEntry
    MAX-ACCESS not-accessible
    STATUS     current
    DESCRIPTION
        "None"
    INDEX      { ospfIndex }
    ::= { win32PageFileTable 1 }

Win32PageFileEntry ::= SEQUENCE {
    ospfIndex Integer32,
    ospfAccessMask  WtcsDisplayString,
    ospfArchive  TruthValue,
    ospfCaption  WtcsDisplayString,
    ospfCompressed  TruthValue,
    ospfCompressionMethod  WtcsDisplayString,
    ospfCreationClassName  WtcsDisplayString,
    ospfCreationDate  DateAndTime,
    ospfCSCreationClassName  WtcsDisplayString,
    ospfCSName  WtcsDisplayString,
    ospfDescription  WtcsDisplayString,
    ospfDrive  WtcsDisplayString,
    ospfEightDotThreeFileName  WtcsDisplayString,
    ospfEncrypted  TruthValue,
    ospfEncryptionMethod  WtcsDisplayString,
    ospfExtension  WtcsDisplayString,
    ospfFileName  WtcsDisplayString,
    ospfFileSize  Gauge32,
    ospfFileType  WtcsDisplayString,
    ospfFreeSpace  Gauge32,
    ospfFSCreationClassName  WtcsDisplayString,
    ospfFSName  WtcsDisplayString,
    ospfHidden  TruthValue,
    ospfInitialSize  Gauge32,
    ospfInstallDate  DateAndTime,
    ospfInUseCount  Gauge32,
    ospfLastAccessed  DateAndTime,
    ospfLastModified  DateAndTime,
    ospfManufacturer  WtcsDisplayString,
    ospfMaximumSize  Gauge32,
    ospfName  WtcsDisplayString,
    ospfPath  WtcsDisplayString,
    ospfReadable  TruthValue,
    ospfStatus  INTEGER,
    ospfSystem  TruthValue,
    ospfVersion  WtcsDisplayString,
    ospfWriteable  TruthValue
}

ospfIndex OBJECT-TYPE
    SYNTAX     Integer32 (1..2147483647)
    MAX-ACCESS read-only
    STATUS     current
    DESCRIPTION
        "The value of this object uniquely identifies the
        instance entry for this class."
    ::= { win32PageFileEntry 1 }

ospfAccessMask  OBJECT-TYPE
    SYNTAX     WtcsDisplayString
    MAX-ACCESS read-only
    STATUS     current
    DESCRIPTION
        "List of access rights to the given file or
        directory held by the user or group on whose behalf
        the instance is returned. This property is only
        supported under Windows NT and Windows 2000. On
        Windows 98 and on Windows NT/Windows 2000 FAT
        volumes, the FULL_ACCESS value, 0xFFFFFFFF hex or
        4294967295 decimal, is returned instead, indicating
        no security has been set on the object.
        Value Meaning 
        0 FILE_LIST_DIRECTORY 
        Grants the right to read data from the file. For a
        directory, this value grants the right to list the
        contents of the directory.
         
        1 FILE_ADD_FILE 
        Grants the right to write data to the file. For a
        directory, this value grants the right to create a
        file in the directory.
         
        2 FILE_ADD_SUBDIRECTORY 
        Grants the right to append data to the file. For a
        directory, this value grants the right to create a
        subdirectory.
         
        3 FILE_READ_EA 
        Grants the right to read extended attributes.
         
        4 FILE_WRITE_EA 
        Grants the right to write extended attributes.
         
        5 FILE_TRAVERSE 
        Grants the right to execute a file. For a
        directory, the directory can be traversed.
         
        6 FILE_DELETE_CHILD 
        Grants the right to delete a directory and all the
        files it contains (its children), even if the files
        are read-only.
         
        7 FILE_READ_ATTRIBUTES 
        Grants the right to read file attributes.
         
        8 FILE_WRITE_ATTRIBUTES 
        Grants the right to change file attributes.
         
        16 DELETE 
        Grants delete access.
         
        17 READ_CONTROL 
        Grants read access to the security descriptor and
        owner.
         
        18 WRITE_DAC 
        Grants write access to the discretionary ACL.
         
        19 WRITE_OWNER 
        Assigns the write owner.
         
        20 SYNCHRONIZE 
        Synchronizes access and allows a process to wait
        for an object to enter the signaled state.
         "
    ::= { win32PageFileEntry 2 }

ospfArchive  OBJECT-TYPE
    SYNTAX     TruthValue
    MAX-ACCESS read-only
    STATUS     current
    DESCRIPTION
        "File should be archived."
    ::= { win32PageFileEntry 3 }

ospfCaption  OBJECT-TYPE
    SYNTAX     WtcsDisplayString
    MAX-ACCESS read-only
    STATUS     current
    DESCRIPTION
        "Short description (one-line string) of the
        object."
    ::= { win32PageFileEntry 4 }

ospfCompressed  OBJECT-TYPE
    SYNTAX     TruthValue
    MAX-ACCESS read-only
    STATUS     current
    DESCRIPTION
        "File is compressed."
    ::= { win32PageFileEntry 5 }

ospfCompressionMethod  OBJECT-TYPE
    SYNTAX     WtcsDisplayString
    MAX-ACCESS read-only
    STATUS     current
    DESCRIPTION
        "Algorithm or tool used to compress the logical
        file. If it is not possible (or not desired) to
        describe the compression scheme (perhaps because it
        is not known), use the following words: 'Unknown'
        to represent that it is not known whether the
        logical file is compressed or not; 'Compressed' to
        represent that the file is compressed but either
        its compression scheme is not known or not
        disclosed; and 'Not Compressed' to represent that
        the logical file is not compressed."
    ::= { win32PageFileEntry 6 }

ospfCreationClassName  OBJECT-TYPE
    SYNTAX     WtcsDisplayString (SIZE (0..256))
    MAX-ACCESS read-only
    STATUS     current
    DESCRIPTION
        "Name of the first concrete class to appear in the
        inheritance chain used in the creation of an
        instance. When used with the other key properties
        of the class, the property allows all instances of
        this class and its subclasses to be uniquely
        identified."
    ::= { win32PageFileEntry 7 }

ospfCreationDate  OBJECT-TYPE
    SYNTAX     DateAndTime
    MAX-ACCESS read-only
    STATUS     current
    DESCRIPTION
        "File creation date."
    ::= { win32PageFileEntry 8 }

ospfCSCreationClassName  OBJECT-TYPE
    SYNTAX     WtcsDisplayString
    MAX-ACCESS read-only
    STATUS     current
    DESCRIPTION
        "Class of the computer system."
    ::= { win32PageFileEntry 9 }

ospfCSName  OBJECT-TYPE
    SYNTAX     WtcsDisplayString
    MAX-ACCESS read-only
    STATUS     current
    DESCRIPTION
        "Name of the computer system."
    ::= { win32PageFileEntry 10 }

ospfDescription  OBJECT-TYPE
    SYNTAX     WtcsDisplayString
    MAX-ACCESS read-only
    STATUS     current
    DESCRIPTION
        "Description of the object."
    ::= { win32PageFileEntry 11 }

ospfDrive  OBJECT-TYPE
    SYNTAX     WtcsDisplayString
    MAX-ACCESS read-only
    STATUS     current
    DESCRIPTION
        "Drive letter (including colon) of the file.
        Example: 'c:'"
    ::= { win32PageFileEntry 12 }

ospfEightDotThreeFileName  OBJECT-TYPE
    SYNTAX     WtcsDisplayString
    MAX-ACCESS read-only
    STATUS     current
    DESCRIPTION
        "DOS-compatible file name for this file.
        Example: 'c:\progra~1'"
    ::= { win32PageFileEntry 13 }

ospfEncrypted  OBJECT-TYPE
    SYNTAX     TruthValue
    MAX-ACCESS read-only
    STATUS     current
    DESCRIPTION
        "File is encrypted."
    ::= { win32PageFileEntry 14 }

ospfEncryptionMethod  OBJECT-TYPE
    SYNTAX     WtcsDisplayString
    MAX-ACCESS read-only
    STATUS     current
    DESCRIPTION
        "Algorithm or tool used to encrypt the logical
        file. If it is not possible (or not desired) to
        describe the encryption scheme (perhaps for
        security reasons), use the following words:
        'Unknown' to represent that it is not known whether
        the logical file is encrypted or not; 'Encrypted'
        to represent that the file is encrypted but either
        its encryption scheme is not known or not
        disclosed; and 'Not Encrypted' to represent that
        the logical file is not encrypted."
    ::= { win32PageFileEntry 15 }

ospfExtension  OBJECT-TYPE
    SYNTAX     WtcsDisplayString
    MAX-ACCESS read-only
    STATUS     current
    DESCRIPTION
        "File extension (without the dot). Examples: 'txt',
        'mof', 'mdb'."
    ::= { win32PageFileEntry 16 }

ospfFileName  OBJECT-TYPE
    SYNTAX     WtcsDisplayString
    MAX-ACCESS read-only
    STATUS     current
    DESCRIPTION
        "Name (without extension) of the file.
        Example: 'autoexec'"
    ::= { win32PageFileEntry 17 }

ospfFileSize  OBJECT-TYPE
    SYNTAX     Gauge32
    MAX-ACCESS read-only
    STATUS     current
    DESCRIPTION
        "Size of the file (in bytes)."
    ::= { win32PageFileEntry 18 }

ospfFileType  OBJECT-TYPE
    SYNTAX     WtcsDisplayString
    MAX-ACCESS read-only
    STATUS     current
    DESCRIPTION
        "File type (indicated by the Extension property)."
    ::= { win32PageFileEntry 19 }

ospfFreeSpace  OBJECT-TYPE
    SYNTAX     Gauge32
    UNITS "Megabytes"
    MAX-ACCESS read-only
    STATUS     current
    DESCRIPTION
        "Space available in the paging file. The operating
        system can enlarge the paging file as necessary up
        to the limit imposed by the user. This property
        shows the difference between the size of current
        committed memory and the current size of the paging
        file; it does not show the largest possible size of
        the paging file."
    ::= { win32PageFileEntry 20 }

ospfFSCreationClassName  OBJECT-TYPE
    SYNTAX     WtcsDisplayString
    MAX-ACCESS read-only
    STATUS     current
    DESCRIPTION
        "Class of the file system."
    ::= { win32PageFileEntry 21 }

ospfFSName  OBJECT-TYPE
    SYNTAX     WtcsDisplayString
    MAX-ACCESS read-only
    STATUS     current
    DESCRIPTION
        "Name of the file system."
    ::= { win32PageFileEntry 22 }

ospfHidden  OBJECT-TYPE
    SYNTAX     TruthValue
    MAX-ACCESS read-only
    STATUS     current
    DESCRIPTION
        "File is hidden."
    ::= { win32PageFileEntry 23 }

ospfInitialSize  OBJECT-TYPE
    SYNTAX     Gauge32
    UNITS "Megabytes"
    MAX-ACCESS read-only
    STATUS     current
    DESCRIPTION
        "Initial size of the page file."
    ::= { win32PageFileEntry 24 }

ospfInstallDate  OBJECT-TYPE
    SYNTAX     DateAndTime
    MAX-ACCESS read-only
    STATUS     current
    DESCRIPTION
        "Object was installed. This property does not need
        a value to indicate that the object is installed."
    ::= { win32PageFileEntry 25 }

ospfInUseCount  OBJECT-TYPE
    SYNTAX     Gauge32
    MAX-ACCESS read-only
    STATUS     current
    DESCRIPTION
        "Number of 'file opens' that are currently active
        against the file."
    ::= { win32PageFileEntry 26 }

ospfLastAccessed  OBJECT-TYPE
    SYNTAX     DateAndTime
    MAX-ACCESS read-only
    STATUS     current
    DESCRIPTION
        "File was last accessed."
    ::= { win32PageFileEntry 27 }

ospfLastModified  OBJECT-TYPE
    SYNTAX     DateAndTime
    MAX-ACCESS read-only
    STATUS     current
    DESCRIPTION
        "File was last modified."
    ::= { win32PageFileEntry 28 }

ospfManufacturer  OBJECT-TYPE
    SYNTAX     WtcsDisplayString
    MAX-ACCESS read-only
    STATUS     current
    DESCRIPTION
        "Manufacturer name from version resource, if one is
        present."
    ::= { win32PageFileEntry 29 }

ospfMaximumSize  OBJECT-TYPE
    SYNTAX     Gauge32
    UNITS "Megabytes"
    MAX-ACCESS read-only
    STATUS     current
    DESCRIPTION
        "Maximum size of the page file as set by the user.
        The operating system will not allow the page file
        to exceed this limit."
    ::= { win32PageFileEntry 30 }

ospfName  OBJECT-TYPE
    SYNTAX     WtcsDisplayString
    MAX-ACCESS read-only
    STATUS     current
    DESCRIPTION
        "Name of the page file.
        Example: 'C:\PAGEFILE.SYS'"
    ::= { win32PageFileEntry 31 }

ospfPath  OBJECT-TYPE
    SYNTAX     WtcsDisplayString
    MAX-ACCESS read-only
    STATUS     current
    DESCRIPTION
        "Path of the file. This includes leading and
        trailing backslashes.
        Example: '\windows\system\'"
    ::= { win32PageFileEntry 32 }

ospfReadable  OBJECT-TYPE
    SYNTAX     TruthValue
    MAX-ACCESS read-only
    STATUS     current
    DESCRIPTION
        "File can be read."
    ::= { win32PageFileEntry 33 }

ospfStatus  OBJECT-TYPE
    SYNTAX     INTEGER {
        ok(1),
        error(2),
        degraded(3),
        unknown(4),
        predFail(5),
        starting(6),
        stopping(7),
        service(8)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is on-line,
        yet the managed element is neither 'OK' nor in one
        of the other states."
    ::= { win32PageFileEntry 34 }

ospfSystem  OBJECT-TYPE
    SYNTAX     TruthValue
    MAX-ACCESS read-only
    STATUS     current
    DESCRIPTION
        "File is a system file."
    ::= { win32PageFileEntry 35 }

ospfVersion  OBJECT-TYPE
    SYNTAX     WtcsDisplayString
    MAX-ACCESS read-only
    STATUS     current
    DESCRIPTION
        "Version name from version resource, if one is
        present."
    ::= { win32PageFileEntry 36 }

ospfWriteable  OBJECT-TYPE
    SYNTAX     TruthValue
    MAX-ACCESS read-only
    STATUS     current
    DESCRIPTION
        "File can be written."
    ::= { win32PageFileEntry 37 }

win32PageFileSettingTable OBJECT-TYPE
    SYNTAX     SEQUENCE OF Win32PageFileSettingEntry
    MAX-ACCESS not-accessible
    STATUS     current
    DESCRIPTION
        "The Win32_PageFileSetting WMI class represents the
        settings of a page file. Information contained
        within objects instantiated from this class specify
        the page file parameters used when the file is
        created at system startup. The properties in this
        class can be modified and deferred until startup.
        These settings are different from the run-time
        state of a page file expressed through the
        associated class Win32_PageFileUsage.
        
        To create an instance of this class, enable the
        SeCreatePagefilePrivilege privilege. For more
        information, see Windows NT/Windows 2000 Privilege
        Strings and Executing Privileged Operations."
    ::= { wmiPageFiles 2 }

win32PageFileSettingEntry OBJECT-TYPE
    SYNTAX     Win32PageFileSettingEntry
    MAX-ACCESS not-accessible
    STATUS     current
    DESCRIPTION
        "None"
    INDEX      { ospfsIndex }
    ::= { win32PageFileSettingTable 1 }

Win32PageFileSettingEntry ::= SEQUENCE {
    ospfsIndex Integer32,
    ospfsCaption  WtcsDisplayString,
    ospfsDescription  WtcsDisplayString,
    ospfsInitialSize  Gauge32,
    ospfsMaximumSize  Gauge32,
    ospfsName  WtcsDisplayString,
    ospfsSettingID  WtcsDisplayString
}

ospfsIndex OBJECT-TYPE
    SYNTAX     Integer32 (1..2147483647)
    MAX-ACCESS read-only
    STATUS     current
    DESCRIPTION
        "The value of this object uniquely identifies the
        instance entry for this class."
    ::= { win32PageFileSettingEntry 1 }

ospfsCaption  OBJECT-TYPE
    SYNTAX     WtcsDisplayString
    MAX-ACCESS read-only
    STATUS     current
    DESCRIPTION
        "Short description (one-line string) of the
        CIM_Setting object."
    ::= { win32PageFileSettingEntry 2 }

ospfsDescription  OBJECT-TYPE
    SYNTAX     WtcsDisplayString
    MAX-ACCESS read-only
    STATUS     current
    DESCRIPTION
        "Description of the CIM_Setting object."
    ::= { win32PageFileSettingEntry 3 }

ospfsInitialSize  OBJECT-TYPE
    SYNTAX     Gauge32
    UNITS "Megabytes"
    MAX-ACCESS read-only
    STATUS     current
    DESCRIPTION
        "Initial size of the page file.
        Example: 139"
    ::= { win32PageFileSettingEntry 4 }

ospfsMaximumSize  OBJECT-TYPE
    SYNTAX     Gauge32
    UNITS "Megabytes"
    MAX-ACCESS read-only
    STATUS     current
    DESCRIPTION
        "Maximum size of the page file.
        Example: 178"
    ::= { win32PageFileSettingEntry 5 }

ospfsName  OBJECT-TYPE
    SYNTAX     WtcsDisplayString
    MAX-ACCESS read-only
    STATUS     current
    DESCRIPTION
        "Path and file name of the page file.
        Example: 'C:\PAGEFILE.SYS'"
    ::= { win32PageFileSettingEntry 6 }

ospfsSettingID  OBJECT-TYPE
    SYNTAX     WtcsDisplayString
    MAX-ACCESS read-only
    STATUS     current
    DESCRIPTION
        "Identifier by which the CIM_Setting object is
        known."
    ::= { win32PageFileSettingEntry 7 }

win32PageFileUsageTable OBJECT-TYPE
    SYNTAX     SEQUENCE OF Win32PageFileUsageEntry
    MAX-ACCESS not-accessible
    STATUS     current
    DESCRIPTION
        "The Win32_PageFileUsage WMI class represents the
        file used for handling virtual memory file swapping
        on a Win32 system. Information contained within
        objects instantiated from this class specify the
        run-time state of the page file."
    ::= { wmiPageFiles 3 }

win32PageFileUsageEntry OBJECT-TYPE
    SYNTAX     Win32PageFileUsageEntry
    MAX-ACCESS not-accessible
    STATUS     current
    DESCRIPTION
        "None"
    INDEX      { ospfuIndex }
    ::= { win32PageFileUsageTable 1 }

Win32PageFileUsageEntry ::= SEQUENCE {
    ospfuIndex Integer32,
    ospfuAllocatedBaseSize  Gauge32,
    ospfuCaption  WtcsDisplayString,
    ospfuCurrentUsage  Gauge32,
    ospfuDescription  WtcsDisplayString,
    ospfuInstallDate  DateAndTime,
    ospfuName  WtcsDisplayString,
    ospfuPeakUsage  Gauge32,
    ospfuStatus  INTEGER,
    ospfuTempPageFile  TruthValue
}

ospfuIndex OBJECT-TYPE
    SYNTAX     Integer32 (1..2147483647)
    MAX-ACCESS read-only
    STATUS     current
    DESCRIPTION
        "The value of this object uniquely identifies the
        instance entry for this class."
    ::= { win32PageFileUsageEntry 1 }

ospfuAllocatedBaseSize  OBJECT-TYPE
    SYNTAX     Gauge32
    UNITS "Megabytes"
    MAX-ACCESS read-only
    STATUS     current
    DESCRIPTION
        "Actual amount of disk space allocated for use with
        this page file. This value corresponds to the range
        established in Win32_PageFileSetting under the
        InitialSize and MaximumSize properties, set at
        system startup.
        Example: 178"
    ::= { win32PageFileUsageEntry 2 }

ospfuCaption  OBJECT-TYPE
    SYNTAX     WtcsDisplayString
    MAX-ACCESS read-only
    STATUS     current
    DESCRIPTION
        "Short description of the object a one-line
        string."
    ::= { win32PageFileUsageEntry 3 }

ospfuCurrentUsage  OBJECT-TYPE
    SYNTAX     Gauge32
    UNITS "Megabytes"
    MAX-ACCESS read-only
    STATUS     current
    DESCRIPTION
        "Amount of disk space currently used by the page
        file."
    ::= { win32PageFileUsageEntry 4 }

ospfuDescription  OBJECT-TYPE
    SYNTAX     WtcsDisplayString
    MAX-ACCESS read-only
    STATUS     current
    DESCRIPTION
        "Description of the object."
    ::= { win32PageFileUsageEntry 5 }

ospfuInstallDate  OBJECT-TYPE
    SYNTAX     DateAndTime
    MAX-ACCESS read-only
    STATUS     current
    DESCRIPTION
        "Object was installed. This property does not need
        a value to indicate that the object is installed."
    ::= { win32PageFileUsageEntry 6 }

ospfuName  OBJECT-TYPE
    SYNTAX     WtcsDisplayString
    MAX-ACCESS read-only
    STATUS     current
    DESCRIPTION
        "Name of the page file.
        Example: 'C:\PAGEFILE.SYS'"
    ::= { win32PageFileUsageEntry 7 }

ospfuPeakUsage  OBJECT-TYPE
    SYNTAX     Gauge32
    UNITS "Megabytes"
    MAX-ACCESS read-only
    STATUS     current
    DESCRIPTION
        "Highest use page file."
    ::= { win32PageFileUsageEntry 8 }

ospfuStatus  OBJECT-TYPE
    SYNTAX     INTEGER {
        ok(1),
        error(2),
        degraded(3),
        unknown(4),
        predFail(5),
        starting(6),
        stopping(7),
        service(8)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is on-line,
        yet the managed element is neither 'OK' nor in one
        of the other states."
    ::= { win32PageFileUsageEntry 9 }

ospfuTempPageFile  OBJECT-TYPE
    SYNTAX     TruthValue
    MAX-ACCESS read-only
    STATUS     current
    DESCRIPTION
        "Windows XP, Windows Server 2003:  If true, a
        temporary page file has been created, usually
        because there is no permanent page file on the
        current computer system."
    ::= { win32PageFileUsageEntry 10 }

wmiMultimedia OBJECT-IDENTITY
    STATUS     current
    DESCRIPTION
        "The class in the Multimedia Audio/Visual
        subcategory represents properties of the audio or
        video codec installed on the computer system."
    ::= { wmiOperatingSystem 6 }

win32CodecFileTable OBJECT-TYPE
    SYNTAX     SEQUENCE OF Win32CodecFileEntry
    MAX-ACCESS not-accessible
    STATUS     current
    DESCRIPTION
        "The Win32_CodecFile WMI class represents the audio
        or video codec installed on the computer system.
        Codecs convert one media format type to another,
        typically a compressed format to an uncompressed
        format. The name codec is derived from a
        combination of compress and decompress. For
        example, a codec can convert a compressed format
        such as MS-ADPCM to an uncompressed format such as
        PCM, which most audio hardware can play directly."
    ::= { wmiMultimedia 1 }

win32CodecFileEntry OBJECT-TYPE
    SYNTAX     Win32CodecFileEntry
    MAX-ACCESS not-accessible
    STATUS     current
    DESCRIPTION
        "None"
    INDEX      { oscfIndex }
    ::= { win32CodecFileTable 1 }

Win32CodecFileEntry ::= SEQUENCE {
    oscfIndex Integer32,
    oscfAccessMask  INTEGER,
    oscfArchive  TruthValue,
    oscfCaption  WtcsDisplayString,
    oscfCompressed  TruthValue,
    oscfCompressionMethod  WtcsDisplayString,
    oscfCreationClassName  WtcsDisplayString,
    oscfCreationDate  DateAndTime,
    oscfCSCreationClassName  WtcsDisplayString,
    oscfCSName  WtcsDisplayString,
    oscfDescription  WtcsDisplayString,
    oscfDrive  WtcsDisplayString,
    oscfEightDotThreeFileName  WtcsDisplayString,
    oscfEncrypted  TruthValue,
    oscfEncryptionMethod  WtcsDisplayString,
    oscfExtension  WtcsDisplayString,
    oscfFileName  WtcsDisplayString,
    oscfFileSize  Gauge32,
    oscfFileType  WtcsDisplayString,
    oscfFSCreationClassName  WtcsDisplayString,
    oscfFSName  WtcsDisplayString,
    oscfGroup  INTEGER,
    oscfHidden  TruthValue,
    oscfInstallDate  DateAndTime,
    oscfInUseCount  Gauge32,
    oscfLastAccessed  DateAndTime,
    oscfLastModified  DateAndTime,
    oscfManufacturer  WtcsDisplayString,
    oscfName  WtcsDisplayString,
    oscfPath  WtcsDisplayString,
    oscfReadable  TruthValue,
    oscfStatus  INTEGER,
    oscfSystem  TruthValue,
    oscfVersion  WtcsDisplayString,
    oscfWriteable  TruthValue
}

oscfIndex OBJECT-TYPE
    SYNTAX     Integer32 (1..2147483647)
    MAX-ACCESS read-only
    STATUS     current
    DESCRIPTION
        "The value of this object uniquely identifies the
        instance entry for this class."
    ::= { win32CodecFileEntry 1 }

oscfAccessMask  OBJECT-TYPE
    SYNTAX     INTEGER {
        fileLISTDIRECTORY(0),
        fileADDFILE(1),
        fileADDSUBDIRECTORY(2),
        fileREADEA(3),
        fileWRITEEA(4),
        fileTRAVERSE(5),
        fileDELETECHILD(6),
        fileREADATTRIBUTES(7),
        fileWRITEATTRIBUTES(8),
        delete(16),
        readCONTROL(17),
        writeDAC(18),
        writeOWNER(19),
        synchronize(20)
    }
    MAX-ACCESS read-only
    STATUS     current
    DESCRIPTION
        "Bitmap list of access rights to the given file or
        directory held by the user or group on whose behalf
        the instance is returned. This property is only
        supported under Windows NT and Windows 2000. On
        Windows 98 and on Windows NT/Windows 2000 FAT
        volumes, the FULL_ACCESS value is returned instead,
        indicating no security has been set on the object.
        This property is inherited from CIM_LogicalFile."
    ::= { win32CodecFileEntry 2 }

oscfArchive  OBJECT-TYPE
    SYNTAX     TruthValue
    MAX-ACCESS read-only
    STATUS     current
    DESCRIPTION
        "File should be archived. This property is
        inherited from CIM_LogicalFile."
    ::= { win32CodecFileEntry 3 }

oscfCaption  OBJECT-TYPE
    SYNTAX     WtcsDisplayString (SIZE (0..64))
    MAX-ACCESS read-only
    STATUS     current
    DESCRIPTION
        "Short description (one-line string) of the object.
        This property is inherited from
        CIM_ManagedSystemElement."
    ::= { win32CodecFileEntry 4 }

oscfCompressed  OBJECT-TYPE
    SYNTAX     TruthValue
    MAX-ACCESS read-only
    STATUS     current
    DESCRIPTION
        "File is compressed. This property is inherited
        from CIM_LogicalFile."
    ::= { win32CodecFileEntry 5 }

oscfCompressionMethod  OBJECT-TYPE
    SYNTAX     WtcsDisplayString
    MAX-ACCESS read-only
    STATUS     current
    DESCRIPTION
        "Algorithm or tool used to compress the logical
        file. If it is not possible (or not desired) to
        describe the compression scheme (perhaps because it
        is not known), use the following words: 'Unknown'
        to represent that it is not known whether the
        logical file is compressed or not; 'Compressed' to
        represent that the file is compressed but either
        its compression scheme is not known or not
        disclosed; and 'Not Compressed' to represent that
        the logical file is not compressed. This property
        is inherited from CIM_LogicalFile."
    ::= { win32CodecFileEntry 6 }

oscfCreationClassName  OBJECT-TYPE
    SYNTAX     WtcsDisplayString (SIZE (0..256))
    MAX-ACCESS read-only
    STATUS     current
    DESCRIPTION
        "Name of the first concrete class to appear in the
        inheritance chain used in the creation of an
        instance. When used with the other key properties
        of the class, the property allows all instances of
        this class and its subclasses to be uniquely
        identified. This property is inherited from
        CIM_LogicalFile."
    ::= { win32CodecFileEntry 7 }

oscfCreationDate  OBJECT-TYPE
    SYNTAX     DateAndTime
    MAX-ACCESS read-only
    STATUS     current
    DESCRIPTION
        "File creation date. This property is inherited
        from CIM_LogicalFile."
    ::= { win32CodecFileEntry 8 }

oscfCSCreationClassName  OBJECT-TYPE
    SYNTAX     WtcsDisplayString
    MAX-ACCESS read-only
    STATUS     current
    DESCRIPTION
        "Class of the computer system. This property is
        inherited from CIM_LogicalFile."
    ::= { win32CodecFileEntry 9 }

oscfCSName  OBJECT-TYPE
    SYNTAX     WtcsDisplayString
    MAX-ACCESS read-only
    STATUS     current
    DESCRIPTION
        "String representing the name of the computer
        system. This property is inherited from
        CIM_LogicalFile."
    ::= { win32CodecFileEntry 10 }

oscfDescription  OBJECT-TYPE
    SYNTAX     WtcsDisplayString
    MAX-ACCESS read-only
    STATUS     current
    DESCRIPTION
        "Full name of the codec driver. This string is
        intended to be displayed in large (descriptive)
        spaces. This property is inherited from
        CIM_ManagedSystemElement.
        Example: 'Microsoft PCM Converter'"
    ::= { win32CodecFileEntry 11 }

oscfDrive  OBJECT-TYPE
    SYNTAX     WtcsDisplayString
    MAX-ACCESS read-only
    STATUS     current
    DESCRIPTION
        "Drive letter (including colon) of the file. This
        property is inherited from CIM_LogicalFile.
        Example: 'c:'"
    ::= { win32CodecFileEntry 12 }

oscfEightDotThreeFileName  OBJECT-TYPE
    SYNTAX     WtcsDisplayString
    MAX-ACCESS read-only
    STATUS     current
    DESCRIPTION
        "DOS-compatible file name for this file. This
        property is inherited from CIM_LogicalFile.
        Example: 'c:\progra~1'"
    ::= { win32CodecFileEntry 13 }

oscfEncrypted  OBJECT-TYPE
    SYNTAX     TruthValue
    MAX-ACCESS read-only
    STATUS     current
    DESCRIPTION
        "If TRUE, the file is encrypted. This property is
        inherited from CIM_LogicalFile."
    ::= { win32CodecFileEntry 14 }

oscfEncryptionMethod  OBJECT-TYPE
    SYNTAX     WtcsDisplayString
    MAX-ACCESS read-only
    STATUS     current
    DESCRIPTION
        "Algorithm or tool used to encrypt the logical
        file. If it is not possible (or not desired) to
        describe the encryption scheme (perhaps for
        security reasons), use the following words:
        'Unknown' to represent that it is not known whether
        the logical file is encrypted or not; 'Encrypted'
        to represent that the file is encrypted but either
        its encryption scheme is not known or not
        disclosed; and 'Not Encrypted' to represent that
        the logical file is not encrypted. This property is
        inherited from CIM_LogicalFile."
    ::= { win32CodecFileEntry 15 }

oscfExtension  OBJECT-TYPE
    SYNTAX     WtcsDisplayString
    MAX-ACCESS read-only
    STATUS     current
    DESCRIPTION
        "File extension (without the dot). This property is
        inherited from CIM_LogicalFile.
        Examples: 'txt', 'mof', 'mdb'"
    ::= { win32CodecFileEntry 16 }

oscfFileName  OBJECT-TYPE
    SYNTAX     WtcsDisplayString
    MAX-ACCESS read-only
    STATUS     current
    DESCRIPTION
        "Name (without extension) of the file. This
        property is inherited from CIM_LogicalFile.
        Example: 'autoexec'"
    ::= { win32CodecFileEntry 17 }

oscfFileSize  OBJECT-TYPE
    SYNTAX     Gauge32
    MAX-ACCESS read-only
    STATUS     current
    DESCRIPTION
        "Size of the file (in bytes). This property is
        inherited from CIM_LogicalFile."
    ::= { win32CodecFileEntry 18 }

oscfFileType  OBJECT-TYPE
    SYNTAX     WtcsDisplayString
    MAX-ACCESS read-only
    STATUS     current
    DESCRIPTION
        "File type (indicated by the Extension property).
        This property is inherited from CIM_LogicalFile."
    ::= { win32CodecFileEntry 19 }

oscfFSCreationClassName  OBJECT-TYPE
    SYNTAX     WtcsDisplayString
    MAX-ACCESS read-only
    STATUS     current
    DESCRIPTION
        "Class of the file system. This property is
        inherited from CIM_LogicalFile."
    ::= { win32CodecFileEntry 20 }

oscfFSName  OBJECT-TYPE
    SYNTAX     WtcsDisplayString
    MAX-ACCESS read-only
    STATUS     current
    DESCRIPTION
        "Name of the file system. This property is
        inherited from CIM_LogicalFile."
    ::= { win32CodecFileEntry 21 }

oscfGroup  OBJECT-TYPE
    SYNTAX     INTEGER {
        audio(1),
        video(2)
    }
    MAX-ACCESS read-only
    STATUS     current
    DESCRIPTION
        "Codec represented by this class."
    ::= { win32CodecFileEntry 22 }

oscfHidden  OBJECT-TYPE
    SYNTAX     TruthValue
    MAX-ACCESS read-only
    STATUS     current
    DESCRIPTION
        "If TRUE, the file is hidden. This property is
        inherited from CIM_LogicalFile."
    ::= { win32CodecFileEntry 23 }

oscfInstallDate  OBJECT-TYPE
    SYNTAX     DateAndTime
    MAX-ACCESS read-only
    STATUS     current
    DESCRIPTION
        "Object was installed. This property does not need
        a value to indicate that the object is installed.
        This property is inherited from
        CIM_ManagedSystemElement."
    ::= { win32CodecFileEntry 24 }

oscfInUseCount  OBJECT-TYPE
    SYNTAX     Gauge32
    MAX-ACCESS read-only
    STATUS     current
    DESCRIPTION
        "Number of 'file opens' that are currently active
        against the file. This property is inherited from
        CIM_LogicalFile."
    ::= { win32CodecFileEntry 25 }

oscfLastAccessed  OBJECT-TYPE
    SYNTAX     DateAndTime
    MAX-ACCESS read-only
    STATUS     current
    DESCRIPTION
        "File was last accessed. This property is inherited
        from CIM_LogicalFile."
    ::= { win32CodecFileEntry 26 }

oscfLastModified  OBJECT-TYPE
    SYNTAX     DateAndTime
    MAX-ACCESS read-only
    STATUS     current
    DESCRIPTION
        "File was last modified. This property is inherited
        from CIM_LogicalFile."
    ::= { win32CodecFileEntry 27 }

oscfManufacturer  OBJECT-TYPE
    SYNTAX     WtcsDisplayString
    MAX-ACCESS read-only
    STATUS     current
    DESCRIPTION
        "Manufacturer string from version resource, if one
        is present. This property is inherited from
        CIM_DataFile."
    ::= { win32CodecFileEntry 28 }

oscfName  OBJECT-TYPE
    SYNTAX     WtcsDisplayString
    MAX-ACCESS read-only
    STATUS     current
    DESCRIPTION
        "Inherited name that serves as a key of a logical
        file instance within a file system. Full path names
        should be provided. This property is inherited from
        CIM_ManagedSystemElement.
        Example: 'c:\winnt\system\win.ini'"
    ::= { win32CodecFileEntry 29 }

oscfPath  OBJECT-TYPE
    SYNTAX     WtcsDisplayString
    MAX-ACCESS read-only
    STATUS     current
    DESCRIPTION
        "Path of the file. This includes leading and
        trailing backslashes. This property is inherited
        from CIM_LogicalFile.
        Example: '\windows\system\'"
    ::= { win32CodecFileEntry 30 }

oscfReadable  OBJECT-TYPE
    SYNTAX     TruthValue
    MAX-ACCESS read-only
    STATUS     current
    DESCRIPTION
        "File can be read. This property is inherited from
        CIM_LogicalFile."
    ::= { win32CodecFileEntry 31 }

oscfStatus  OBJECT-TYPE
    SYNTAX     INTEGER {
        ok(1),
        error(2),
        degraded(3),
        unknown(4),
        predFail(5),
        starting(6),
        stopping(7),
        service(8)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is on-line,
        yet the managed element is neither 'OK' nor in one
        of the other states. This property is inherited
        from CIM_ManagedSystemElement."
    ::= { win32CodecFileEntry 32 }

oscfSystem  OBJECT-TYPE
    SYNTAX     TruthValue
    MAX-ACCESS read-only
    STATUS     current
    DESCRIPTION
        "File is a system file. This property is inherited
        from CIM_LogicalFile."
    ::= { win32CodecFileEntry 33 }

oscfVersion  OBJECT-TYPE
    SYNTAX     WtcsDisplayString
    MAX-ACCESS read-only
    STATUS     current
    DESCRIPTION
        "Version string from version resource, if one is
        present. This property is inherited from
        CIM_DataFile."
    ::= { win32CodecFileEntry 34 }

oscfWriteable  OBJECT-TYPE
    SYNTAX     TruthValue
    MAX-ACCESS read-only
    STATUS     current
    DESCRIPTION
        "File can be written. This property is inherited
        from CIM_LogicalFile."
    ::= { win32CodecFileEntry 35 }

wmiNetworking OBJECT-IDENTITY
    STATUS     current
    DESCRIPTION
        "The Networking subcategory groups classes that
        represent network connections, network clients, and
        network connection settings such as the protocol
        used."
    ::= { wmiOperatingSystem 7 }

win32IP4PersistedRouteTableTable OBJECT-TYPE
    SYNTAX     SEQUENCE OF Win32IP4PersistedRouteTableEntry
    MAX-ACCESS not-accessible
    STATUS     current
    DESCRIPTION
        "The Win32_IP4PersistedRouteTable WMI class
        represents persisted IP routes. By default, the
        routes added to the routing table are not
        permanent. Rebooting the computer clears the routes
        from the table. However, the following Windows NT
        command makes the route persist after the computer
        is restarted:
        route -p add
        Persistent entries are automatically reinserted in
        the route table each time the route table is
        rebuilt. Windows NT stores persistent routes in the
        registry. This class is only applicable to IP4 and
        does not address IPX or IP6.  This class was added
        for Windows Server 2003 family."
    ::= { wmiNetworking 1 }

win32IP4PersistedRouteTableEntry OBJECT-TYPE
    SYNTAX     Win32IP4PersistedRouteTableEntry
    MAX-ACCESS not-accessible
    STATUS     current
    DESCRIPTION
        "None"
    INDEX      { osprtIndex }
    ::= { win32IP4PersistedRouteTableTable 1 }

Win32IP4PersistedRouteTableEntry ::= SEQUENCE {
    osprtIndex Integer32,
    osprtCaption  WtcsDisplayString,
    osprtDescription  WtcsDisplayString,
    osprtDestination  WtcsDisplayString,
    osprtInstallDate  DateAndTime,
    osprtMask  WtcsDisplayString,
    osprtMetric1  Integer32,
    osprtName  WtcsDisplayString,
    osprtNextHop  WtcsDisplayString,
    osprtStatus  INTEGER
}

osprtIndex OBJECT-TYPE
    SYNTAX     Integer32 (1..2147483647)
    MAX-ACCESS read-only
    STATUS     current
    DESCRIPTION
        "The value of this object uniquely identifies the
        instance entry for this class."
    ::= { win32IP4PersistedRouteTableEntry 1 }

osprtCaption  OBJECT-TYPE
    SYNTAX     WtcsDisplayString (SIZE (0..64))
    MAX-ACCESS read-only
    STATUS     current
    DESCRIPTION
        "Short description (one-line string) of the object.
        This property is inherited from
        CIM_ManagedSystemElement."
    ::= { win32IP4PersistedRouteTableEntry 2 }

osprtDescription  OBJECT-TYPE
    SYNTAX     WtcsDisplayString
    MAX-ACCESS read-only
    STATUS     current
    DESCRIPTION
        "Description of the object. This property is
        inherited from CIM_ManagedSystemElement."
    ::= { win32IP4PersistedRouteTableEntry 3 }

osprtDestination  OBJECT-TYPE
    SYNTAX     WtcsDisplayString
    MAX-ACCESS read-only
    STATUS     current
    DESCRIPTION
        "Destination IP address for this persisted route."
    ::= { win32IP4PersistedRouteTableEntry 4 }

osprtInstallDate  OBJECT-TYPE
    SYNTAX     DateAndTime
    MAX-ACCESS read-only
    STATUS     current
    DESCRIPTION
        "Object was installed. This property does not need
        a value to indicate that the object is installed.
        This property is inherited from
        CIM_ManagedSystemElement."
    ::= { win32IP4PersistedRouteTableEntry 5 }

osprtMask  OBJECT-TYPE
    SYNTAX     WtcsDisplayString
    MAX-ACCESS read-only
    STATUS     current
    DESCRIPTION
        "Mask used in this persisted entry. Use the logical
        AND operation to combine the mask with the
        destination address. Compare the result to the
        value in the ipRouteDest field."
    ::= { win32IP4PersistedRouteTableEntry 6 }

osprtMetric1  OBJECT-TYPE
    SYNTAX     Integer32
    MAX-ACCESS read-only
    STATUS     current
    DESCRIPTION
        "Primary routing metric for this persisted route.
        The semantics of this metric are determined by the
        routing protocol specified in the route's
        ipRouteProto value. If this property is not used,
        its value should be set to -1."
    ::= { win32IP4PersistedRouteTableEntry 7 }

osprtName  OBJECT-TYPE
    SYNTAX     WtcsDisplayString
    MAX-ACCESS read-only
    STATUS     current
    DESCRIPTION
        "Label by which the object is known. When
        subclassed, the property can be overridden to be a
        key property. This property is inherited from
        CIM_ManagedSystemElement."
    ::= { win32IP4PersistedRouteTableEntry 8 }

osprtNextHop  OBJECT-TYPE
    SYNTAX     WtcsDisplayString
    MAX-ACCESS read-only
    STATUS     current
    DESCRIPTION
        "IP address of the next hop of this persisted
        route. If the route is bound to an interface that
        is realized via a broadcast medium, this field
        contains the agent's IP address on that interface."
    ::= { win32IP4PersistedRouteTableEntry 9 }

osprtStatus  OBJECT-TYPE
    SYNTAX     INTEGER {
        ok(1),
        error(2),
        degraded(3),
        unknown(4),
        predFail(5),
        starting(6),
        stopping(7),
        service(8)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is on-line,
        yet the managed element is neither 'OK' nor in one
        of the other states. This property is inherited
        from CIM_ManagedSystemElement."
    ::= { win32IP4PersistedRouteTableEntry 10 }

win32IP4RouteTableTable OBJECT-TYPE
    SYNTAX     SEQUENCE OF Win32IP4RouteTableEntry
    MAX-ACCESS not-accessible
    STATUS     current
    DESCRIPTION
        "The Win32_IP4RouteTable WMI class represents
        information that governs the routing of network
        data packets. For example, Internet packets are
        usually sent to a gateway and local packets are
        routed directly by the client's computer.
        Administrators can use this information to trace
        problems associated with misrouted packets, and
        also direct a computer to a new gateway as
        necessary. This class is only applicable to IP4 and
        does not address IPX or IP6. It is intended to
        model only the information shown as a result of
        typing the route print command from the command
        prompt. This class was added for Windows Server
        2003 family."
    ::= { wmiNetworking 2 }

win32IP4RouteTableEntry OBJECT-TYPE
    SYNTAX     Win32IP4RouteTableEntry
    MAX-ACCESS not-accessible
    STATUS     current
    DESCRIPTION
        "None"
    INDEX      { osrtIndex }
    ::= { win32IP4RouteTableTable 1 }

Win32IP4RouteTableEntry ::= SEQUENCE {
    osrtIndex Integer32,
    osrtAge  Integer32,
    osrtCaption  WtcsDisplayString,
    osrtDescription  WtcsDisplayString,
    osrtDestination  WtcsDisplayString,
    osrtInformation  WtcsDisplayString,
    osrtInstallDate  DateAndTime,
    osrtInterfaceIndex  Integer32,
    osrtMask  WtcsDisplayString,
    osrtMetric1  Integer32,
    osrtMetric2  Integer32,
    osrtMetric3  Integer32,
    osrtMetric4  Integer32,
    osrtMetric5  Integer32,
    osrtName  WtcsDisplayString,
    osrtNextHop  WtcsDisplayString,
    osrtProtocol  INTEGER,
    osrtStatus  INTEGER,
    osrtType  INTEGER
}

osrtIndex OBJECT-TYPE
    SYNTAX     Integer32 (1..2147483647)
    MAX-ACCESS read-only
    STATUS     current
    DESCRIPTION
        "The value of this object uniquely identifies the
        instance entry for this class."
    ::= { win32IP4RouteTableEntry 1 }

osrtAge  OBJECT-TYPE
    SYNTAX     Integer32
    MAX-ACCESS read-only
    STATUS     current
    DESCRIPTION
        "Number of seconds since this route was last
        updated or otherwise determined to be correct.
        Whether the routing information is outdated can
        only be determined by knowing the routing protocol
        by which the route was learned."
    ::= { win32IP4RouteTableEntry 2 }

osrtCaption  OBJECT-TYPE
    SYNTAX     WtcsDisplayString (SIZE (0..64))
    MAX-ACCESS read-only
    STATUS     current
    DESCRIPTION
        "Short description (one-line string) of the object.
        This property is inherited from
        CIM_ManagedSystemElement."
    ::= { win32IP4RouteTableEntry 3 }

osrtDescription  OBJECT-TYPE
    SYNTAX     WtcsDisplayString
    MAX-ACCESS read-only
    STATUS     current
    DESCRIPTION
        "Description of the object. This property is
        inherited from CIM_ManagedSystemElement."
    ::= { win32IP4RouteTableEntry 4 }

osrtDestination  OBJECT-TYPE
    SYNTAX     WtcsDisplayString
    MAX-ACCESS read-only
    STATUS     current
    DESCRIPTION
        "Destination IP address for this route."
    ::= { win32IP4RouteTableEntry 5 }

osrtInformation  OBJECT-TYPE
    SYNTAX     WtcsDisplayString
    MAX-ACCESS read-only
    STATUS     current
    DESCRIPTION
        "Reference to MIB definitions specific to the
        particular routing protocol that is responsible for
        this route, as determined by the value specified in
        the route's ipRouteProto value. If this information
        is not present, its value should be set to the
        OBJECT IDENTIFIER {0 0}, which is a syntactically
        valid object identifier, and any conformant
        implementation of ASN.1 and BER must be able to
        generate and recognize this value."
    ::= { win32IP4RouteTableEntry 6 }

osrtInstallDate  OBJECT-TYPE
    SYNTAX     DateAndTime
    MAX-ACCESS read-only
    STATUS     current
    DESCRIPTION
        "Object was installed. This property does not need
        a value to indicate that the object is installed.
        This property is inherited from
        CIM_ManagedSystemElement."
    ::= { win32IP4RouteTableEntry 7 }

osrtInterfaceIndex  OBJECT-TYPE
    SYNTAX     Integer32
    MAX-ACCESS read-only
    STATUS     current
    DESCRIPTION
        "IP address of the next hop of this route. The
        value in this property is the same as the value in
        the InterfaceIndex property in the instances of
        Win32_NetworkAdapter and
        Win32_NetworkAdapterConfiguration that represent
        the network interface of the next hop of the route.
        In the case of a route bound to an interface that
        is realized using a broadcast medium, the value of
        this field is the agent's IP address on that
        interface."
    ::= { win32IP4RouteTableEntry 8 }

osrtMask  OBJECT-TYPE
    SYNTAX     WtcsDisplayString
    MAX-ACCESS read-only
    STATUS     current
    DESCRIPTION
        "Mask used in this entry. Masks should be joined
        with a logical AND with the destination address
        before being compared to the value in the
        ipRouteDest field."
    ::= { win32IP4RouteTableEntry 9 }

osrtMetric1  OBJECT-TYPE
    SYNTAX     Integer32
    MAX-ACCESS read-only
    STATUS     current
    DESCRIPTION
        "Primary routing metric for this route. The routing
        protocol specified in the ipRouteProto value for
        the route determines the interpretation of this
        property. Set the value of this property to -1 if
        it is not used."
    ::= { win32IP4RouteTableEntry 10 }

osrtMetric2  OBJECT-TYPE
    SYNTAX     Integer32
    MAX-ACCESS read-only
    STATUS     current
    DESCRIPTION
        "Alternate routing metric for this route. The
        routing protocol specified in the ipRouteProto
        value for the route determines the interpretation
        of this property. Set the value of this property to
        -1 if it is not used."
    ::= { win32IP4RouteTableEntry 11 }

osrtMetric3  OBJECT-TYPE
    SYNTAX     Integer32
    MAX-ACCESS read-only
    STATUS     current
    DESCRIPTION
        "Alternate routing metric for this route. The
        routing protocol specified in the ipRouteProto
        value for the route determines the interpretation
        of this property. Set the value of this property to
        -1 if it is not used."
    ::= { win32IP4RouteTableEntry 12 }

osrtMetric4  OBJECT-TYPE
    SYNTAX     Integer32
    MAX-ACCESS read-only
    STATUS     current
    DESCRIPTION
        "Alternate routing metric for this route. The
        routing protocol specified in the ipRouteProto
        value for the route determines the interpretation
        of this property. Set the value of this property to
        -1 if it is not used."
    ::= { win32IP4RouteTableEntry 13 }

osrtMetric5  OBJECT-TYPE
    SYNTAX     Integer32
    MAX-ACCESS read-only
    STATUS     current
    DESCRIPTION
        "Alternate routing metric for this route. The
        routing protocol specified in the ipRouteProto
        value for the route determines the interpretation
        of this property. Set the value of this property to
        -1 if it is not used."
    ::= { win32IP4RouteTableEntry 14 }

osrtName  OBJECT-TYPE
    SYNTAX     WtcsDisplayString
    MAX-ACCESS read-only
    STATUS     current
    DESCRIPTION
        "Label by which the object is known. When
        subclassed, the property can be overridden to be a
        key property. This property is inherited from
        CIM_ManagedSystemElement."
    ::= { win32IP4RouteTableEntry 15 }

osrtNextHop  OBJECT-TYPE
    SYNTAX     WtcsDisplayString
    MAX-ACCESS read-only
    STATUS     current
    DESCRIPTION
        "IP address of the next hop of this route. For a
        route that is bound to an interface realized via a
        broadcast medium, the value of this field is the
        agent's IP address on that interface."
    ::= { win32IP4RouteTableEntry 16 }

osrtProtocol  OBJECT-TYPE
    SYNTAX     INTEGER {
        other(1),
        local(2),
        netmgmt(3),
        icmp(4),
        egp(5),
        ggp(6),
        hello(7),
        rip(8),
        isis(9),
        esis(10),
        ciscoIgrp(11),
        bbnSpfIgp(12),
        ospf(13),
        bgp(14)
    }
    MAX-ACCESS read-only
    STATUS     current
    DESCRIPTION
        "Routing mechanism through which this route was
        learned. Inclusion of values for gateway routing
        protocols does not imply that hosts must support
        those protocols."
    ::= { win32IP4RouteTableEntry 17 }

osrtStatus  OBJECT-TYPE
    SYNTAX     INTEGER {
        ok(1),
        error(2),
        degraded(3),
        unknown(4),
        predFail(5),
        starting(6),
        stopping(7),
        service(8)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is on-line,
        yet the managed element is neither 'OK' nor in one
        of the other states. This property is inherited
        from the CIM_ManagedSystemElement class."
    ::= { win32IP4RouteTableEntry 18 }

osrtType  OBJECT-TYPE
    SYNTAX     INTEGER {
        other(1),
        invalid(2),
        direct(3),
        indirect(4)
    }
    MAX-ACCESS read-only
    STATUS     current
    DESCRIPTION
        "Type of route."
    ::= { win32IP4RouteTableEntry 19 }

win32NetworkClientTable OBJECT-TYPE
    SYNTAX     SEQUENCE OF Win32NetworkClientEntry
    MAX-ACCESS not-accessible
    STATUS     current
    DESCRIPTION
        "The Win32_NetworkClient WMI class represents a
        network client on a Windows system. Any computer
        system on the network with a client relationship to
        the system is a descendent (or member) of this
        class (for example, a computer running Windows 2000
        Workstation or Windows 98 that is part of a Windows
        2000 domain)."
    ::= { wmiNetworking 3 }

win32NetworkClientEntry OBJECT-TYPE
    SYNTAX     Win32NetworkClientEntry
    MAX-ACCESS not-accessible
    STATUS     current
    DESCRIPTION
        "None"
    INDEX      { osnclIndex }
    ::= { win32NetworkClientTable 1 }

Win32NetworkClientEntry ::= SEQUENCE {
    osnclIndex Integer32,
    osnclCaption  WtcsDisplayString,
    osnclDescription  WtcsDisplayString,
    osnclInstallDate  DateAndTime,
    osnclManufacturer  WtcsDisplayString,
    osnclName  WtcsDisplayString,
    osnclStatus  INTEGER
}

osnclIndex OBJECT-TYPE
    SYNTAX     Integer32 (1..2147483647)
    MAX-ACCESS read-only
    STATUS     current
    DESCRIPTION
        "The value of this object uniquely identifies the
        instance entry for this class."
    ::= { win32NetworkClientEntry 1 }

osnclCaption  OBJECT-TYPE
    SYNTAX     WtcsDisplayString
    MAX-ACCESS read-only
    STATUS     current
    DESCRIPTION
        "Short description (one-line string) of the
        object."
    ::= { win32NetworkClientEntry 2 }

osnclDescription  OBJECT-TYPE
    SYNTAX     WtcsDisplayString
    MAX-ACCESS read-only
    STATUS     current
    DESCRIPTION
        "Description of the object."
    ::= { win32NetworkClientEntry 3 }

osnclInstallDate  OBJECT-TYPE
    SYNTAX     DateAndTime
    MAX-ACCESS read-only
    STATUS     current
    DESCRIPTION
        "Object was installed. This property does not need
        a value to indicate that the object is installed."
    ::= { win32NetworkClientEntry 4 }

osnclManufacturer  OBJECT-TYPE
    SYNTAX     WtcsDisplayString
    MAX-ACCESS read-only
    STATUS     current
    DESCRIPTION
        "Name of the manufacturer of the network client
        running on the Windows system.
        Example: 'Microsoft Corporation'"
    ::= { win32NetworkClientEntry 5 }

osnclName  OBJECT-TYPE
    SYNTAX     WtcsDisplayString
    MAX-ACCESS read-only
    STATUS     current
    DESCRIPTION
        "Network name of the network client running on a
        Windows system.
        Example: 'Microsoft Windows Network'"
    ::= { win32NetworkClientEntry 6 }

osnclStatus  OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is on-line,
        yet the managed element is neither 'OK' nor in one
        of the other states."
    ::= { win32NetworkClientEntry 7 }

win32NetworkConnectionTable OBJECT-TYPE
    SYNTAX     SEQUENCE OF Win32NetworkConnectionEntry
    MAX-ACCESS not-accessible
    STATUS     current
    DESCRIPTION
        "The Win32_NetworkClient WMI class represents a
        network client on a Windows system. Any computer
        system on the network with a client relationship to
        the system is a descendent (or member) of this
        class (for example, a computer running Windows 2000
        Workstation or Windows 98 that is part of a Windows
        2000 domain)."
    ::= { wmiNetworking 4 }

win32NetworkConnectionEntry OBJECT-TYPE
    SYNTAX     Win32NetworkConnectionEntry
    MAX-ACCESS not-accessible
    STATUS     current
    DESCRIPTION
        "None"
    INDEX      { osncoIndex }
    ::= { win32NetworkConnectionTable 1 }

Win32NetworkConnectionEntry ::= SEQUENCE {
    osncoIndex Integer32,
    osncoAccessMask  WtcsDisplayString,
    osncoCaption  WtcsDisplayString,
    osncoComment  WtcsDisplayString,
    osncoConnectionState  INTEGER,
    osncoConnectionType  INTEGER,
    osncoDescription  WtcsDisplayString,
    osncoDisplayType  INTEGER,
    osncoInstallDate  DateAndTime,
    osncoLocalName  WtcsDisplayString,
    osncoName  WtcsDisplayString,
    osncoPersistent  TruthValue,
    osncoProviderName  WtcsDisplayString,
    osncoRemoteName  WtcsDisplayString,
    osncoRemotePath  WtcsDisplayString,
    osncoResourceType  INTEGER,
    osncoStatus  INTEGER,
    osncoUserName  WtcsDisplayString
}

osncoIndex OBJECT-TYPE
    SYNTAX     Integer32 (1..2147483647)
    MAX-ACCESS read-only
    STATUS     current
    DESCRIPTION
        "The value of this object uniquely identifies the
        instance entry for this class."
    ::= { win32NetworkConnectionEntry 1 }

osncoAccessMask  OBJECT-TYPE
    SYNTAX     WtcsDisplayString
    MAX-ACCESS read-only
    STATUS     current
    DESCRIPTION
        "List of access rights to the given file or
        directory held by the user or group on whose behalf
        the instance is returned. This property is only
        supported under Windows NT and Windows 2000. On
        Windows 98 and on Windows NT/Windows 2000 FAT
        volumes, the FULL_ACCESS value is returned instead,
        indicating no security has been set on the object.
        Value Meaning 
        0 FILE_DATA_READ (file)
        FILE_LIST_DIRECTORY (directory) 
        Grants the right to read data from the file. For a
        directory, this value grants the right to list the
        contents of the directory.
         
        1 FILE_WRITE_DATA (file)
        FILE_ADD_FILE (directory)
        Grants the right to write data to the file. For a
        directory, this value grants the right to create a
        file in the directory.
         
        2 FILE_APPEND_DATA (file)
        FILE_ADD_SUBDIRECTORY (directory)
        Grants the right to append data to the file. For a
        directory, this value grants the right to create a
        subdirectory.
         
        3 FILE_READ_EA 
        Grants the right to read extended attributes.
         
        4 FILE_WRITE_EA 
        Grants the right to write extended attributes.
         
        5 FILE_TRAVERSE 
        Grants the right to execute a file. For a
        directory, the directory can be traversed.
         
        6 FILE_DELETE_CHILD 
        Grants the right to delete a directory and all the
        files it contains (its children), even if the files
        are read-only.
         
        7 FILE_READ_ATTRIBUTES 
        Grants the right to read file attributes.
         
        8 FILE_WRITE_ATTRIBUTES 
        Grants the right to change file attributes.
         
        16 DELETE 
        Grants delete access.
         
        17 READ_CONTROL 
        Grants read access to the security descriptor and
        owner.
         
        18 WRITE_DAC 
        Grants write access to the discretionary ACL.
         
        19 WRITE_OWNER 
        Assigns the write owner.
         
        20 SYNCHRONIZE 
        Synchronizes access and allows a process to wait
        for an object to enter the signaled state.
         "
    ::= { win32NetworkConnectionEntry 2 }

osncoCaption  OBJECT-TYPE
    SYNTAX     WtcsDisplayString
    MAX-ACCESS read-only
    STATUS     current
    DESCRIPTION
        "Short description (one-line string) of the
        object."
    ::= { win32NetworkConnectionEntry 3 }

osncoComment  OBJECT-TYPE
    SYNTAX     WtcsDisplayString
    MAX-ACCESS read-only
    STATUS     current
    DESCRIPTION
        "Comment supplied by the network provider."
    ::= { win32NetworkConnectionEntry 4 }

osncoConnectionState  OBJECT-TYPE
    SYNTAX     INTEGER {
        connected(1),
        error(2),
        paused(3),
        disconnected(4),
        connecting(5),
        reconnecting(6)
    }
    MAX-ACCESS read-only
    STATUS     current
    DESCRIPTION
        "Current state of the network connection."
    ::= { win32NetworkConnectionEntry 5 }

osncoConnectionType  OBJECT-TYPE
    SYNTAX     INTEGER {
        currentConnection(1),
        persistentConnection(2)
    }
    MAX-ACCESS read-only
    STATUS     current
    DESCRIPTION
        "Persistence type of the connection used for
        connecting to the network."
    ::= { win32NetworkConnectionEntry 6 }

osncoDescription  OBJECT-TYPE
    SYNTAX     WtcsDisplayString
    MAX-ACCESS read-only
    STATUS     current
    DESCRIPTION
        "Description of the object."
    ::= { win32NetworkConnectionEntry 7 }

osncoDisplayType  OBJECT-TYPE
    SYNTAX     INTEGER {
        domain(1),
        generic(2),
        server(3),
        share(4)
    }
    MAX-ACCESS read-only
    STATUS     current
    DESCRIPTION
        "Network object should be displayed in a network
        browsing user interface."
    ::= { win32NetworkConnectionEntry 8 }

osncoInstallDate  OBJECT-TYPE
    SYNTAX     DateAndTime
    MAX-ACCESS read-only
    STATUS     current
    DESCRIPTION
        "Object was installed. This property does not need
        a value to indicate that the object is installed."
    ::= { win32NetworkConnectionEntry 9 }

osncoLocalName  OBJECT-TYPE
    SYNTAX     WtcsDisplayString
    MAX-ACCESS read-only
    STATUS     current
    DESCRIPTION
        "Local name of the connected network device.
        Example: 'c:\public'"
    ::= { win32NetworkConnectionEntry 10 }

osncoName  OBJECT-TYPE
    SYNTAX     WtcsDisplayString
    MAX-ACCESS read-only
    STATUS     current
    DESCRIPTION
        "Name of the current network connection. It is the
        combination of the values in RemoteName and
        LocalName.
        Example: '\\NTRELEASE (c:\public)'"
    ::= { win32NetworkConnectionEntry 11 }

osncoPersistent  OBJECT-TYPE
    SYNTAX     TruthValue
    MAX-ACCESS read-only
    STATUS     current
    DESCRIPTION
        "Connection will be reconnected automatically by
        the operating system on the next logon."
    ::= { win32NetworkConnectionEntry 12 }

osncoProviderName  OBJECT-TYPE
    SYNTAX     WtcsDisplayString
    MAX-ACCESS read-only
    STATUS     current
    DESCRIPTION
        "Name of the provider that owns the resource. This
        property can be NULL if the provider name is
        unknown."
    ::= { win32NetworkConnectionEntry 13 }

osncoRemoteName  OBJECT-TYPE
    SYNTAX     WtcsDisplayString
    MAX-ACCESS read-only
    STATUS     current
    DESCRIPTION
        "Remote network resource name for a network
        resource. For a current or persistent connection,
        RemoteName contains the network name associated
        with the name of the value in the LocalName
        property. The name in RemoteName must follow the
        network provider's naming conventions.
        Example: '\\NTRELEASE'"
    ::= { win32NetworkConnectionEntry 14 }

osncoRemotePath  OBJECT-TYPE
    SYNTAX     WtcsDisplayString
    MAX-ACCESS read-only
    STATUS     current
    DESCRIPTION
        "Full path to the network resource.
        Example: '\\infosrv1\public'"
    ::= { win32NetworkConnectionEntry 15 }

osncoResourceType  OBJECT-TYPE
    SYNTAX     INTEGER {
        disk(1),
        print(2),
        any(3)
    }
    MAX-ACCESS read-only
    STATUS     current
    DESCRIPTION
        "Type of resource to enumerate or connect to."
    ::= { win32NetworkConnectionEntry 16 }

osncoStatus  OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is on-line,
        yet the managed element is neither 'OK' nor in one
        of the other states."
    ::= { win32NetworkConnectionEntry 17 }

osncoUserName  OBJECT-TYPE
    SYNTAX     WtcsDisplayString
    MAX-ACCESS read-only
    STATUS     current
    DESCRIPTION
        "User name or the default user name used to
        establish a network connection.
        Example: 'SYSTEM'"
    ::= { win32NetworkConnectionEntry 18 }

win32NetworkProtocolTable OBJECT-TYPE
    SYNTAX     SEQUENCE OF Win32NetworkProtocolEntry
    MAX-ACCESS not-accessible
    STATUS     current
    DESCRIPTION
        "The Win32_NetworkProtocol WMI class represents a
        protocol and its network characteristics on a Win32
        computer system."
    ::= { wmiNetworking 5 }

win32NetworkProtocolEntry OBJECT-TYPE
    SYNTAX     Win32NetworkProtocolEntry
    MAX-ACCESS not-accessible
    STATUS     current
    DESCRIPTION
        "None"
    INDEX      { osnpIndex }
    ::= { win32NetworkProtocolTable 1 }

Win32NetworkProtocolEntry ::= SEQUENCE {
    osnpIndex Integer32,
    osnpCaption  WtcsDisplayString,
    osnpConnectionlessService  TruthValue,
    osnpDescription  WtcsDisplayString,
    osnpGuaranteesDelivery  TruthValue,
    osnpGuaranteesSequencing  TruthValue,
    osnpInstallDate  DateAndTime,
    osnpMaximumAddressSize  Gauge32,
    osnpMaximumMessageSize  Gauge32,
    osnpMessageOriented  TruthValue,
    osnpMinimumAddressSize  Gauge32,
    osnpName  WtcsDisplayString,
    osnpPseudoStreamOriented  TruthValue,
    osnpStatus  INTEGER,
    osnpSupportsBroadcasting  TruthValue,
    osnpSupportsConnectData  TruthValue,
    osnpSupportsDisconnectData  TruthValue,
    osnpSupportsEncryption  TruthValue,
    osnpSupportsExpeditedData  TruthValue,
    osnpSupportsFragmentation  TruthValue,
    osnpSupportsGracefulClosing  TruthValue,
    osnpSupportsGuaranteedBandwidth  TruthValue,
    osnpSupportsMulticasting  TruthValue,
    osnpSupportsQualityofService  TruthValue
}

osnpIndex OBJECT-TYPE
    SYNTAX     Integer32 (1..2147483647)
    MAX-ACCESS read-only
    STATUS     current
    DESCRIPTION
        "The value of this object uniquely identifies the
        instance entry for this class."
    ::= { win32NetworkProtocolEntry 1 }

osnpCaption  OBJECT-TYPE
    SYNTAX     WtcsDisplayString
    MAX-ACCESS read-only
    STATUS     current
    DESCRIPTION
        "Short description (one-line string) of the
        object."
    ::= { win32NetworkProtocolEntry 2 }

osnpConnectionlessService  OBJECT-TYPE
    SYNTAX     TruthValue
    MAX-ACCESS read-only
    STATUS     current
    DESCRIPTION
        "Protocol supports connectionless service. A
        connectionless (datagram) service describes a
        communications protocol or transport in which data
        packets are routed independently of each other and
        may follow different routes and arrive in a
        different order from that in which they were sent.
        Conversely, a connection-oriented service provides
        a virtual circuit through which data packets are
        received in the same order they were transmitted.
        If the connection between machines fails, the
        application is notified."
    ::= { win32NetworkProtocolEntry 3 }

osnpDescription  OBJECT-TYPE
    SYNTAX     WtcsDisplayString
    MAX-ACCESS read-only
    STATUS     current
    DESCRIPTION
        "Description of the object."
    ::= { win32NetworkProtocolEntry 4 }

osnpGuaranteesDelivery  OBJECT-TYPE
    SYNTAX     TruthValue
    MAX-ACCESS read-only
    STATUS     current
    DESCRIPTION
        "Protocol supports guaranteed delivery of data
        packets. If this flag is FALSE, there is no
        guarantee that all data sent will reach the
        intended destination."
    ::= { win32NetworkProtocolEntry 5 }

osnpGuaranteesSequencing  OBJECT-TYPE
    SYNTAX     TruthValue
    MAX-ACCESS read-only
    STATUS     current
    DESCRIPTION
        "Protocol guarantees that data will arrive in the
        order in which it was sent. Note that this
        characteristic does not guarantee delivery of the
        data, only its order."
    ::= { win32NetworkProtocolEntry 6 }

osnpInstallDate  OBJECT-TYPE
    SYNTAX     DateAndTime
    MAX-ACCESS read-only
    STATUS     current
    DESCRIPTION
        "Object was installed. This property does not need
        a value to indicate that the object is installed."
    ::= { win32NetworkProtocolEntry 7 }

osnpMaximumAddressSize  OBJECT-TYPE
    SYNTAX     Gauge32
    UNITS "Characters"
    MAX-ACCESS read-only
    STATUS     current
    DESCRIPTION
        "Maximum length of a socket address supported by
        the protocol. Socket addresses may be items like
        URLs (www.microsoft.com) or IP addresses
        (130.215.24.1)."
    ::= { win32NetworkProtocolEntry 8 }

osnpMaximumMessageSize  OBJECT-TYPE
    SYNTAX     Gauge32
    UNITS "Characters"
    MAX-ACCESS read-only
    STATUS     current
    DESCRIPTION
        "Maximum message size supported by the protocol.
        This is the maximum size of a message that can be
        sent from or received by the host. For protocols
        that do not support message framing, the actual
        maximum size of a message that can be sent to a
        given address may be less than this value."
    ::= { win32NetworkProtocolEntry 9 }

osnpMessageOriented  OBJECT-TYPE
    SYNTAX     TruthValue
    MAX-ACCESS read-only
    STATUS     current
    DESCRIPTION
        "Protocol is message-oriented. A message-oriented
        protocol uses packets of data to transfer
        information. Conversely, stream-oriented protocols
        transfer data as a continuous stream of bytes."
    ::= { win32NetworkProtocolEntry 10 }

osnpMinimumAddressSize  OBJECT-TYPE
    SYNTAX     Gauge32
    UNITS "Characters"
    MAX-ACCESS read-only
    STATUS     current
    DESCRIPTION
        "Minimum length of a socket address supported by
        the protocol."
    ::= { win32NetworkProtocolEntry 11 }

osnpName  OBJECT-TYPE
    SYNTAX     WtcsDisplayString
    MAX-ACCESS read-only
    STATUS     current
    DESCRIPTION
        "Name for the protocol.
        Example: 'TCP/IP'"
    ::= { win32NetworkProtocolEntry 12 }

osnpPseudoStreamOriented  OBJECT-TYPE
    SYNTAX     TruthValue
    MAX-ACCESS read-only
    STATUS     current
    DESCRIPTION
        "Protocol is a message-oriented protocol that can
        receive variable-length data packets or streamed
        data for all receive operations. This optional
        capability is useful when an application does not
        want the protocol to frame messages, and requires
        stream-oriented characteristics. If TRUE, the
        protocol is pseudo stream-oriented."
    ::= { win32NetworkProtocolEntry 13 }

osnpStatus  OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is on-line,
        yet the managed element is neither 'OK' nor in one
        of the other states."
    ::= { win32NetworkProtocolEntry 14 }

osnpSupportsBroadcasting  OBJECT-TYPE
    SYNTAX     TruthValue
    MAX-ACCESS read-only
    STATUS     current
    DESCRIPTION
        "Protocol supports a mechanism for broadcasting
        messages across the network."
    ::= { win32NetworkProtocolEntry 15 }

osnpSupportsConnectData  OBJECT-TYPE
    SYNTAX     TruthValue
    MAX-ACCESS read-only
    STATUS     current
    DESCRIPTION
        "Protocol allows data to be connected across the
        network."
    ::= { win32NetworkProtocolEntry 16 }

osnpSupportsDisconnectData  OBJECT-TYPE
    SYNTAX     TruthValue
    MAX-ACCESS read-only
    STATUS     current
    DESCRIPTION
        "Protocol allows data to be disconnected across the
        network."
    ::= { win32NetworkProtocolEntry 17 }

osnpSupportsEncryption  OBJECT-TYPE
    SYNTAX     TruthValue
    MAX-ACCESS read-only
    STATUS     current
    DESCRIPTION
        "Protocol supports data encryption."
    ::= { win32NetworkProtocolEntry 18 }

osnpSupportsExpeditedData  OBJECT-TYPE
    SYNTAX     TruthValue
    MAX-ACCESS read-only
    STATUS     current
    DESCRIPTION
        "Protocol supports expedited data (also known as
        urgent data) across the network. Expedited data can
        bypass flow control and receive priority over
        normal data packets."
    ::= { win32NetworkProtocolEntry 19 }

osnpSupportsFragmentation  OBJECT-TYPE
    SYNTAX     TruthValue
    MAX-ACCESS read-only
    STATUS     current
    DESCRIPTION
        "Protocol supports transmitting the data in
        fragments. Physical network maximum transfer unit
        (MTU) is hidden from applications. Each media type
        has a maximum frame size that cannot be exceeded.
        The link layer is responsible for discovering the
        MTU and reporting it to the protocols being used."
    ::= { win32NetworkProtocolEntry 20 }

osnpSupportsGracefulClosing  OBJECT-TYPE
    SYNTAX     TruthValue
    MAX-ACCESS read-only
    STATUS     current
    DESCRIPTION
        "Protocol supports two-phase close operations, also
        known as graceful close operations. If not, the
        protocol supports only abortive close operations."
    ::= { win32NetworkProtocolEntry 21 }

osnpSupportsGuaranteedBandwidth  OBJECT-TYPE
    SYNTAX     TruthValue
    MAX-ACCESS read-only
    STATUS     current
    DESCRIPTION
        "Protocol has a mechanism to establish and maintain
        a guaranteed bandwidth."
    ::= { win32NetworkProtocolEntry 22 }

osnpSupportsMulticasting  OBJECT-TYPE
    SYNTAX     TruthValue
    MAX-ACCESS read-only
    STATUS     current
    DESCRIPTION
        "Protocol supports multicasting."
    ::= { win32NetworkProtocolEntry 23 }

osnpSupportsQualityofService  OBJECT-TYPE
    SYNTAX     TruthValue
    MAX-ACCESS read-only
    STATUS     current
    DESCRIPTION
        "Protocol is capable of Quality of Service (QOS)
        support by the underlying layered service provider
        or transport carrier. QOS is a collection of
        components that enable differentiation and
        preferential treatment for subsets of data
        transmitted over the network. QOS loosely means
        subsets of data get higher priority or guaranteed
        service when traversing a network."
    ::= { win32NetworkProtocolEntry 24 }

win32NTDomainTable OBJECT-TYPE
    SYNTAX     SEQUENCE OF Win32NTDomainEntry
    MAX-ACCESS not-accessible
    STATUS     current
    DESCRIPTION
        "The Win32_NTDomain WMI class represents a Windows
        NT domain. This class is new for Windows XP."
    ::= { wmiNetworking 6 }

win32NTDomainEntry OBJECT-TYPE
    SYNTAX     Win32NTDomainEntry
    MAX-ACCESS not-accessible
    STATUS     current
    DESCRIPTION
        "None"
    INDEX      { osdoIndex }
    ::= { win32NTDomainTable 1 }

Win32NTDomainEntry ::= SEQUENCE {
    osdoIndex Integer32,
    osdoCaption  WtcsDisplayString,
    osdoClientSiteName  WtcsDisplayString,
    osdoCreationClassName  WtcsDisplayString,
    osdoDcSiteName  WtcsDisplayString,
    osdoDescription  WtcsDisplayString,
    osdoDNSForestName  WtcsDisplayString,
    osdoDomainControllerAddress  WtcsDisplayString,
    osdoDomainControllerAddressType  INTEGER,
    osdoDomainControllerName  WtcsDisplayString,
    osdoDomainGUID  WtcsDisplayString,
    osdoDomainName  WtcsDisplayString,
    osdoDSDirectoryServiceFlag  TruthValue,
    osdoDSDnsControllerFlag  TruthValue,
    osdoDSDnsDomainFlag  TruthValue,
    osdoDSDnsForestFlag  TruthValue,
    osdoDSGlobalCatalogFlag  TruthValue,
    osdoDSKerberosDistCenterFlag  TruthValue,
    osdoDSPriDomainControllerFlag  TruthValue,
    osdoDSTimeServiceFlag  TruthValue,
    osdoDSWritableFlag  TruthValue,
    osdoInstallDate  DateAndTime,
    osdoName  WtcsDisplayString,
    osdoNameFormat  WtcsDisplayString,
    osdoPrimaryOwnerContact  WtcsDisplayString,
    osdoPrimaryOwnerName  WtcsDisplayString,
    osdoRoles  WtcsDisplayString,
    osdoStatus  INTEGER
}

osdoIndex OBJECT-TYPE
    SYNTAX     Integer32 (1..2147483647)
    MAX-ACCESS read-only
    STATUS     current
    DESCRIPTION
        "The value of this object uniquely identifies the
        instance entry for this class."
    ::= { win32NTDomainEntry 1 }

osdoCaption  OBJECT-TYPE
    SYNTAX     WtcsDisplayString (SIZE (0..64))
    MAX-ACCESS read-only
    STATUS     current
    DESCRIPTION
        "Short description of the object. This property is
        inherited from CIM_ManagedSystemElement."
    ::= { win32NTDomainEntry 2 }

osdoClientSiteName  OBJECT-TYPE
    SYNTAX     WtcsDisplayString
    MAX-ACCESS read-only
    STATUS     current
    DESCRIPTION
        "Name of the site where the domain controller is
        configured. This value can be NULL."
    ::= { win32NTDomainEntry 3 }

osdoCreationClassName  OBJECT-TYPE
    SYNTAX     WtcsDisplayString
    MAX-ACCESS read-only
    STATUS     current
    DESCRIPTION
        "Name of the first concrete class in the
        inheritance chain that is used to create an
        instance. You can use this property with other
        properties of the class to identify all instances
        of the class and its subclasses. This property is
        inherited from CIM_System."
    ::= { win32NTDomainEntry 4 }

osdoDcSiteName  OBJECT-TYPE
    SYNTAX     WtcsDisplayString
    MAX-ACCESS read-only
    STATUS     current
    DESCRIPTION
        "Name of the site where the domain controller is
        located. This value can be NULL."
    ::= { win32NTDomainEntry 5 }

osdoDescription  OBJECT-TYPE
    SYNTAX     WtcsDisplayString
    MAX-ACCESS read-only
    STATUS     current
    DESCRIPTION
        "Comment that describes the link. This property is
        inherited from CIM_ManagedSystemElement."
    ::= { win32NTDomainEntry 6 }

osdoDNSForestName  OBJECT-TYPE
    SYNTAX     WtcsDisplayString
    MAX-ACCESS read-only
    STATUS     current
    DESCRIPTION
        "Name of the root of the DNS tree."
    ::= { win32NTDomainEntry 7 }

osdoDomainControllerAddress  OBJECT-TYPE
    SYNTAX     WtcsDisplayString
    MAX-ACCESS read-only
    STATUS     current
    DESCRIPTION
        "Address of the discovered domain controller."
    ::= { win32NTDomainEntry 8 }

osdoDomainControllerAddressType  OBJECT-TYPE
    SYNTAX     INTEGER {
        dnsINETADDRESS(1),
        dnsNETBIOSADDRESS(2)
    }
    MAX-ACCESS read-only
    STATUS     current
    DESCRIPTION
        "Type of address specified in the
        DomainControllerAddress property."
    ::= { win32NTDomainEntry 9 }

osdoDomainControllerName  OBJECT-TYPE
    SYNTAX     WtcsDisplayString
    MAX-ACCESS read-only
    STATUS     current
    DESCRIPTION
        "Computer name for the discovered domain
        controller."
    ::= { win32NTDomainEntry 10 }

osdoDomainGUID  OBJECT-TYPE
    SYNTAX     WtcsDisplayString
    MAX-ACCESS read-only
    STATUS     current
    DESCRIPTION
        "Globally unique identifier (GUID) of the domain
        controller. This property is 0 (zero) if the domain
        controller does not have a GUID."
    ::= { win32NTDomainEntry 11 }

osdoDomainName  OBJECT-TYPE
    SYNTAX     WtcsDisplayString
    MAX-ACCESS read-only
    STATUS     current
    DESCRIPTION
        "Name of the domain.
        Example: microsoft.com"
    ::= { win32NTDomainEntry 12 }

osdoDSDirectoryServiceFlag  OBJECT-TYPE
    SYNTAX     TruthValue
    MAX-ACCESS read-only
    STATUS     current
    DESCRIPTION
        "If TRUE, the domain controller is a directory
        service server."
    ::= { win32NTDomainEntry 13 }

osdoDSDnsControllerFlag  OBJECT-TYPE
    SYNTAX     TruthValue
    MAX-ACCESS read-only
    STATUS     current
    DESCRIPTION
        "If true the Domain Controller Name is in DNS
        format.
        Example: www.mynode.com or 135.5.33.19"
    ::= { win32NTDomainEntry 14 }

osdoDSDnsDomainFlag  OBJECT-TYPE
    SYNTAX     TruthValue
    MAX-ACCESS read-only
    STATUS     current
    DESCRIPTION
        "If TRUE, the DomainName value is in DNS format."
    ::= { win32NTDomainEntry 15 }

osdoDSDnsForestFlag  OBJECT-TYPE
    SYNTAX     TruthValue
    MAX-ACCESS read-only
    STATUS     current
    DESCRIPTION
        "If TRUE, the DNSForestName value is in DNS
        format."
    ::= { win32NTDomainEntry 16 }

osdoDSGlobalCatalogFlag  OBJECT-TYPE
    SYNTAX     TruthValue
    MAX-ACCESS read-only
    STATUS     current
    DESCRIPTION
        "If TRUE, the domain controller is a Global Catalog
        server for the DNSForestName value."
    ::= { win32NTDomainEntry 17 }

osdoDSKerberosDistCenterFlag  OBJECT-TYPE
    SYNTAX     TruthValue
    MAX-ACCESS read-only
    STATUS     current
    DESCRIPTION
        "If TRUE, the domain controller is a Kerberos Key
        Distribution Center for the domain."
    ::= { win32NTDomainEntry 18 }

osdoDSPriDomainControllerFlag  OBJECT-TYPE
    SYNTAX     TruthValue
    MAX-ACCESS read-only
    STATUS     current
    DESCRIPTION
        "If TRUE, the domain controller is the Primary
        Domain Controller."
    ::= { win32NTDomainEntry 19 }

osdoDSTimeServiceFlag  OBJECT-TYPE
    SYNTAX     TruthValue
    MAX-ACCESS read-only
    STATUS     current
    DESCRIPTION
        "If TRUE, the domain is running the Windows Time
        service."
    ::= { win32NTDomainEntry 20 }

osdoDSWritableFlag  OBJECT-TYPE
    SYNTAX     TruthValue
    MAX-ACCESS read-only
    STATUS     current
    DESCRIPTION
        "If TRUE, the domain controller hosts a writeable
        DS or Security Accounts Manager (SAM)."
    ::= { win32NTDomainEntry 21 }

osdoInstallDate  OBJECT-TYPE
    SYNTAX     DateAndTime
    MAX-ACCESS read-only
    STATUS     current
    DESCRIPTION
        "Date and time when an object is installed. An
        object does not need a value to indicate that it is
        installed. This property is inherited from
        CIM_ManagedSystemElement."
    ::= { win32NTDomainEntry 22 }

osdoName  OBJECT-TYPE
    SYNTAX     WtcsDisplayString
    MAX-ACCESS read-only
    STATUS     current
    DESCRIPTION
        "Name of an object. This property is inherited from
        CIM_ManagedSystemElement."
    ::= { win32NTDomainEntry 23 }

osdoNameFormat  OBJECT-TYPE
    SYNTAX     WtcsDisplayString
    MAX-ACCESS read-only
    STATUS     current
    DESCRIPTION
        "Format to generate the system name using the
        subclass heuristic. This property is inherited from
        CIM_System."
    ::= { win32NTDomainEntry 24 }

osdoPrimaryOwnerContact  OBJECT-TYPE
    SYNTAX     WtcsDisplayString
    MAX-ACCESS read-only
    STATUS     current
    DESCRIPTION
        "Contact information for the primary system owner.
        This property is inherited from CIM_System."
    ::= { win32NTDomainEntry 25 }

osdoPrimaryOwnerName  OBJECT-TYPE
    SYNTAX     WtcsDisplayString (SIZE (0..64))
    MAX-ACCESS read-only
    STATUS     current
    DESCRIPTION
        "Name of the primary system owner. This property is
        inherited from CIM_System."
    ::= { win32NTDomainEntry 26 }

osdoRoles  OBJECT-TYPE
    SYNTAX     WtcsDisplayString
    MAX-ACCESS read-only
    STATUS     current
    DESCRIPTION
        "Roles for this system in the IT environment. This
        property is inherited from CIM_System.
        Example: 'Switch' or 'Bridge'"
    ::= { win32NTDomainEntry 27 }

osdoStatus  OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of an object. Various operational
        and non-operational statuses can be defined.
        Operational statuses include: OK, Degraded, and
        Pred Fail, which is an element such as a
        SMART-enabled hard drive that may be functioning
        properly, but predicts a failure in the near
        future. Non-operational statuses include: Error,
        Starting, Stopping, and Service, which can apply
        during mirror resilvering of a disk, reloading a
        user permissions list, or other administrative
        work. Not all status work is online, but the
        managed element is not OK or in one of the other
        states. This property is inherited from
        CIM_ManagedSystemElement."
    ::= { win32NTDomainEntry 28 }

wmiOperatingSystemSettings OBJECT-IDENTITY
    STATUS     current
    DESCRIPTION
        "The Operating System Settings subcategory groups
        classes that represent the Operating System and its
        settings."
    ::= { wmiOperatingSystem 8 }

win32BootConfigurationTable OBJECT-TYPE
    SYNTAX     SEQUENCE OF Win32BootConfigurationEntry
    MAX-ACCESS not-accessible
    STATUS     current
    DESCRIPTION
        "The Win32_BootConfiguration WMI class represents
        the boot configuration of a Windows system."
    ::= { wmiOperatingSystemSettings 1 }

win32BootConfigurationEntry OBJECT-TYPE
    SYNTAX     Win32BootConfigurationEntry
    MAX-ACCESS not-accessible
    STATUS     current
    DESCRIPTION
        "None"
    INDEX      { osbcIndex }
    ::= { win32BootConfigurationTable 1 }

Win32BootConfigurationEntry ::= SEQUENCE {
    osbcIndex Integer32,
    osbcBootDirectory  WtcsDisplayString,
    osbcCaption  WtcsDisplayString,
    osbcConfigurationPath  WtcsDisplayString,
    osbcDescription  WtcsDisplayString,
    osbcLastDrive  WtcsDisplayString,
    osbcName  WtcsDisplayString,
    osbcScratchDirectory  WtcsDisplayString,
    osbcSettingID  WtcsDisplayString,
    osbcTempDirectory  WtcsDisplayString
}

osbcIndex OBJECT-TYPE
    SYNTAX     Integer32 (1..2147483647)
    MAX-ACCESS read-only
    STATUS     current
    DESCRIPTION
        "The value of this object uniquely identifies the
        instance entry for this class."
    ::= { win32BootConfigurationEntry 1 }

osbcBootDirectory  OBJECT-TYPE
    SYNTAX     WtcsDisplayString
    MAX-ACCESS read-only
    STATUS     current
    DESCRIPTION
        "Path to the system files required for booting the
        system.
        Example: 'C:\Windows'"
    ::= { win32BootConfigurationEntry 2 }

osbcCaption  OBJECT-TYPE
    SYNTAX     WtcsDisplayString (SIZE (0..64))
    MAX-ACCESS read-only
    STATUS     current
    DESCRIPTION
        "Short description (one-line string) of the
        CIM_Setting object. This property is inherited from
        CIM_Setting."
    ::= { win32BootConfigurationEntry 3 }

osbcConfigurationPath  OBJECT-TYPE
    SYNTAX     WtcsDisplayString
    MAX-ACCESS read-only
    STATUS     current
    DESCRIPTION
        "Path to the configuration files. This value may be
        similar to the value in the BootDirectory
        property."
    ::= { win32BootConfigurationEntry 4 }

osbcDescription  OBJECT-TYPE
    SYNTAX     WtcsDisplayString
    MAX-ACCESS read-only
    STATUS     current
    DESCRIPTION
        "Description of the CIM_Setting object. This
        property is inherited from CIM_Setting."
    ::= { win32BootConfigurationEntry 5 }

osbcLastDrive  OBJECT-TYPE
    SYNTAX     WtcsDisplayString
    MAX-ACCESS read-only
    STATUS     current
    DESCRIPTION
        "Last drive letter to which a physical drive is
        assigned.
        Example: 'E:'"
    ::= { win32BootConfigurationEntry 6 }

osbcName  OBJECT-TYPE
    SYNTAX     WtcsDisplayString (SIZE (0..256))
    MAX-ACCESS read-only
    STATUS     current
    DESCRIPTION
        "Name of the boot configuration. It is an
        identifier for the boot configuration."
    ::= { win32BootConfigurationEntry 7 }

osbcScratchDirectory  OBJECT-TYPE
    SYNTAX     WtcsDisplayString
    MAX-ACCESS read-only
    STATUS     current
    DESCRIPTION
        "Directory where temporary files can reside during
        boot time."
    ::= { win32BootConfigurationEntry 8 }

osbcSettingID  OBJECT-TYPE
    SYNTAX     WtcsDisplayString (SIZE (0..256))
    MAX-ACCESS read-only
    STATUS     current
    DESCRIPTION
        "Identifier by which the CIM_Setting object is
        known. This property is inherited from
        CIM_Setting."
    ::= { win32BootConfigurationEntry 9 }

osbcTempDirectory  OBJECT-TYPE
    SYNTAX     WtcsDisplayString
    MAX-ACCESS read-only
    STATUS     current
    DESCRIPTION
        "Directory where temporary files are stored.
        Example: 'C:\TEMP'"
    ::= { win32BootConfigurationEntry 10 }

win32ComputerSystemTable OBJECT-TYPE
    SYNTAX     SEQUENCE OF Win32ComputerSystemEntry
    MAX-ACCESS not-accessible
    STATUS     current
    DESCRIPTION
        "The Win32_ComputerSystem WMI class represents a
        computer operating system in a Windows
        environment."
    ::= { wmiOperatingSystemSettings 2 }

win32ComputerSystemEntry OBJECT-TYPE
    SYNTAX     Win32ComputerSystemEntry
    MAX-ACCESS not-accessible
    STATUS     current
    DESCRIPTION
        "None"
    INDEX      { oscsIndex }
    ::= { win32ComputerSystemTable 1 }

Win32ComputerSystemEntry ::= SEQUENCE {
    oscsIndex Integer32,
    oscsAdminPasswordStatus  INTEGER,
    oscsAutomaticResetBootOption  TruthValue,
    oscsAutomaticResetCapability  TruthValue,
    oscsBootOptionOnLimit  INTEGER,
    oscsBootOptionOnWatchDog  INTEGER,
    oscsBootROMSupported  TruthValue,
    oscsBootupState  INTEGER,
    oscsCaption  WtcsDisplayString,
    oscsChassisBootupState  INTEGER,
    oscsCreationClassName  WtcsDisplayString,
    oscsCurrentTimeZone  Integer32,
    oscsDaylightInEffect  TruthValue,
    oscsDescription  WtcsDisplayString,
    oscsDNSHostName  WtcsDisplayString,
    oscsDomain  WtcsDisplayString,
    oscsDomainRole  INTEGER,
    oscsEnableDaylightSavingsTime  TruthValue,
    oscsFrontPanelResetStatus  INTEGER,
    oscsInfraredSupported  TruthValue,
    oscsInitialLoadInfo  WtcsDisplayString,
    oscsInstallDate  DateAndTime,
    oscsKeyboardPasswordStatus  INTEGER,
    oscsLastLoadInfo  WtcsDisplayString,
    oscsManufacturer  WtcsDisplayString,
    oscsModel  WtcsDisplayString,
    oscsName  WtcsDisplayString,
    oscsNameFormat  INTEGER,
    oscsNetworkServerModeEnabled  TruthValue,
    oscsNumberOfProcessors  Gauge32,
    oscsOEMLogoBitmap  WtcsDisplayString,
    oscsOEMStringArray  WtcsDisplayString,
    oscsPartOfDomain  TruthValue,
    oscsPauseAfterReset  Integer32,
    oscsPowerManagementCapabilities  WtcsDisplayString,
    oscsPowerManagementSupported  TruthValue,
    oscsPowerOnPasswordStatus  INTEGER,
    oscsPowerState  INTEGER,
    oscsPowerSupplyState  INTEGER,
    oscsPrimaryOwnerContact  WtcsDisplayString,
    oscsPrimaryOwnerName  WtcsDisplayString,
    oscsResetCapability  INTEGER,
    oscsResetCount  Integer32,
    oscsResetLimit  Integer32,
    oscsRoles  WtcsDisplayString,
    oscsStatus  INTEGER,
    oscsSupportContactDescription  WtcsDisplayString,
    oscsSystemStartupDelay  Integer32,
    oscsSystemStartupOptions  WtcsDisplayString,
    oscsSystemStartupSetting  Integer32,
    oscsSystemType  INTEGER,
    oscsThermalState  INTEGER,
    oscsTotalPhysicalMemory  Gauge32,
    oscsUserName  WtcsDisplayString,
    oscsWakeUpType  INTEGER,
    oscsWorkgroup  WtcsDisplayString,
    oscsAutomaticManagedPagefile TruthValue,
    oscsNumberOfLogicalProcessors Integer32,
    oscsPCSystemType INTEGER
}

oscsIndex OBJECT-TYPE
    SYNTAX     Integer32 (1..2147483647)
    MAX-ACCESS read-only
    STATUS     current
    DESCRIPTION
        "The value of this object uniquely identifies the
        instance entry for this class."
    ::= { win32ComputerSystemEntry 1 }

oscsAdminPasswordStatus  OBJECT-TYPE
    SYNTAX     INTEGER {
        disabled(1),
        enabled(2),
        notImplemented(3),
        unknown(4)
    }
    MAX-ACCESS read-only
    STATUS     current
    DESCRIPTION
        "System hardware security settings for
        administrator password status."
    ::= { win32ComputerSystemEntry 2 }

oscsAutomaticResetBootOption  OBJECT-TYPE
    SYNTAX     TruthValue
    MAX-ACCESS read-only
    STATUS     current
    DESCRIPTION
        "Automatic reset boot option is enabled."
    ::= { win32ComputerSystemEntry 3 }

oscsAutomaticResetCapability  OBJECT-TYPE
    SYNTAX     TruthValue
    MAX-ACCESS read-only
    STATUS     current
    DESCRIPTION
        "Automatic reset is enabled. This capability is
        available on Windows XP, Windows 2000, and Windows
        NT, but not on Windows 98 or Windows 95. "
    ::= { win32ComputerSystemEntry 4 }

oscsBootOptionOnLimit  OBJECT-TYPE
    SYNTAX     INTEGER {
        reserved(1),
        operatingSystem(2),
        systemUtilities(3),
        doNotReboot(4)
    }
    MAX-ACCESS read-only
    STATUS     current
    DESCRIPTION
        "Boot option limit is ON. Identifies the system
        action when the ResetLimit value is reached."
    ::= { win32ComputerSystemEntry 5 }

oscsBootOptionOnWatchDog  OBJECT-TYPE
    SYNTAX     INTEGER {
        reserved(1),
        operatingSystem(2),
        systemUtilities(3),
        doNotReboot(4)
    }
    MAX-ACCESS read-only
    STATUS     current
    DESCRIPTION
        "Type of reboot action after the time on the
        watchdog timer is elapsed."
    ::= { win32ComputerSystemEntry 6 }

oscsBootROMSupported  OBJECT-TYPE
    SYNTAX     TruthValue
    MAX-ACCESS read-only
    STATUS     current
    DESCRIPTION
        "Indicates whether or not a boot ROM is supported."
    ::= { win32ComputerSystemEntry 7 }

oscsBootupState  OBJECT-TYPE
    SYNTAX     INTEGER {
        normalBoot(1),
        failsafeBoot(2),
        failsafeWithNetworkBoot(3)
    }
    MAX-ACCESS read-only
    STATUS     current
    DESCRIPTION
        "System is started. Fail-safe boot bypasses the
        user startup files also called SafeBoot."
    ::= { win32ComputerSystemEntry 8 }

oscsCaption  OBJECT-TYPE
    SYNTAX     WtcsDisplayString
    MAX-ACCESS read-only
    STATUS     current
    DESCRIPTION
        "Short description of the object a one-line string.
        This property is inherited from
        CIM_ManagedSystemElement."
    ::= { win32ComputerSystemEntry 9 }

oscsChassisBootupState  OBJECT-TYPE
    SYNTAX     INTEGER {
        other(1),
        unknown(2),
        safes(3),
        warning(4),
        critical(5),
        nonrecoverable(6)
    }
    MAX-ACCESS read-only
    STATUS     current
    DESCRIPTION
        "Bootup state of the chassis."
    ::= { win32ComputerSystemEntry 10 }

oscsCreationClassName  OBJECT-TYPE
    SYNTAX     WtcsDisplayString
    MAX-ACCESS read-only
    STATUS     current
    DESCRIPTION
        "Name of the first concrete class in the
        inheritance chain of an instance. You can use this
        property with other properties of the class to
        identify all instances of the class and its
        subclasses. This property is inherited from
        CIM_System"
    ::= { win32ComputerSystemEntry 11 }

oscsCurrentTimeZone  OBJECT-TYPE
    SYNTAX     Integer32
    UNITS "Minutes"
    MAX-ACCESS read-only
    STATUS     current
    DESCRIPTION
        "Amount of time the unitary computer system is
        offset from Universal Time Coordinate (UTC)."
    ::= { win32ComputerSystemEntry 12 }

oscsDaylightInEffect  OBJECT-TYPE
    SYNTAX     TruthValue
    MAX-ACCESS read-only
    STATUS     current
    DESCRIPTION
        "Daylight savings mode is ON."
    ::= { win32ComputerSystemEntry 13 }

oscsDescription  OBJECT-TYPE
    SYNTAX     WtcsDisplayString
    MAX-ACCESS read-only
    STATUS     current
    DESCRIPTION
        "Description of the object."
    ::= { win32ComputerSystemEntry 14 }

oscsDNSHostName  OBJECT-TYPE
    SYNTAX     WtcsDisplayString
    MAX-ACCESS read-only
    STATUS     current
    DESCRIPTION
        "Name of local computer according to the domain
        name server (DNS). This property is new for Windows
        Server 2003. "
    ::= { win32ComputerSystemEntry 15 }

oscsDomain  OBJECT-TYPE
    SYNTAX     WtcsDisplayString
    MAX-ACCESS read-only
    STATUS     current
    DESCRIPTION
        "Name of the domain to which a computer belongs.
        Note  If the computer is not part of a domain, then
        the name of the workgroup will be returned."
    ::= { win32ComputerSystemEntry 16 }

oscsDomainRole  OBJECT-TYPE
    SYNTAX     INTEGER {
        standaloneWorkstation(0),
        memberWorkstation(1),
        standaloneServer(2),
        memberServer(3),
        backupDomainController(4),
        primaryDomainController(5)
    }
    MAX-ACCESS read-only
    STATUS     current
    DESCRIPTION
        "Role of a computer in an assigned domain
        workgroup. A domain workgroup is a collection of
        computers on the same network. For example, a
        DomainRole property may show that a computer is a
        member workstation. This property is inherited from
        CIM_ManagedSystemElement."
    ::= { win32ComputerSystemEntry 17 }

oscsEnableDaylightSavingsTime  OBJECT-TYPE
    SYNTAX     TruthValue
    MAX-ACCESS read-only
    STATUS     current
    DESCRIPTION
        "Windows XP, Windows Server 2003:  Enables daylight
        savings time (DST) on a machine. A value of true
        indicates that the system time changes to an hour
        ahead or behind when DST starts or ends. A value of
        false indicates that the system time does not
        change to an hour ahead or behind when DST starts
        or ends. A value of NULL indicates that the DST
        status is unknown on a system. "
    ::= { win32ComputerSystemEntry 18 }

oscsFrontPanelResetStatus  OBJECT-TYPE
    SYNTAX     INTEGER {
        disabled(0),
        enabled(1),
        notImplemented(2),
        unknown(3)
    }
    MAX-ACCESS read-only
    STATUS     current
    DESCRIPTION
        "The following table identifies the hardware
        security settings for the reset button on a
        computer."
    ::= { win32ComputerSystemEntry 19 }

oscsInfraredSupported  OBJECT-TYPE
    SYNTAX     TruthValue
    MAX-ACCESS read-only
    STATUS     current
    DESCRIPTION
        "Infrared (IR) port exists on a computer system."
    ::= { win32ComputerSystemEntry 20 }

oscsInitialLoadInfo  OBJECT-TYPE
    SYNTAX     WtcsDisplayString
    MAX-ACCESS read-only
    STATUS     current
    DESCRIPTION
        "Data needed to find the initial load device or
        boot service to request the operating system start
        up. This property is inherited from
        CIM_UnitaryComputerSystem."
    ::= { win32ComputerSystemEntry 21 }

oscsInstallDate  OBJECT-TYPE
    SYNTAX     DateAndTime
    MAX-ACCESS read-only
    STATUS     current
    DESCRIPTION
        "Object is installed. An object does not need a
        value to indicate that it is installed. This
        property is inherited from
        CIM_ManagedSystemElement."
    ::= { win32ComputerSystemEntry 22 }

oscsKeyboardPasswordStatus  OBJECT-TYPE
    SYNTAX     INTEGER {
        disabled(0),
        enabled(1),
        notImplemented(2),
        unknown(3)
    }
    MAX-ACCESS read-only
    STATUS     current
    DESCRIPTION
        "System hardware security settings for Keyboard
        Password Status."
    ::= { win32ComputerSystemEntry 23 }

oscsLastLoadInfo  OBJECT-TYPE
    SYNTAX     WtcsDisplayString
    MAX-ACCESS read-only
    STATUS     current
    DESCRIPTION
        "Array entry of the InitialLoadInfo property that
        contains the data to boot the operating system that
        is loaded. This property is inherited from
        CIM_UnitaryComputerSystem."
    ::= { win32ComputerSystemEntry 24 }

oscsManufacturer  OBJECT-TYPE
    SYNTAX     WtcsDisplayString
    MAX-ACCESS read-only
    STATUS     current
    DESCRIPTION
        "Name of a computer manufacturer.
        Example: Adventure Works"
    ::= { win32ComputerSystemEntry 25 }

oscsModel  OBJECT-TYPE
    SYNTAX     WtcsDisplayString
    MAX-ACCESS read-only
    STATUS     current
    DESCRIPTION
        "Product name that a manufacturer gives to a
        computer. This property must have a value."
    ::= { win32ComputerSystemEntry 26 }

oscsName  OBJECT-TYPE
    SYNTAX     WtcsDisplayString
    MAX-ACCESS read-only
    STATUS     current
    DESCRIPTION
        "Key of a CIM_System instance in an enterprise
        environment. This property is inherited from
        CIM_ManagedSystemElement."
    ::= { win32ComputerSystemEntry 27 }

oscsNameFormat  OBJECT-TYPE
    SYNTAX     INTEGER {
        ip(2),
        dial(3),
        hid(4),
        nwa(5),
        hwa(6),
        x25(7),
        isdn(8),
        ipx(9),
        dcc(10),
        icd(11),
        e164(12),
        sna(13),
        osi(14),
        other(15)
    }
    MAX-ACCESS read-only
    STATUS     current
    DESCRIPTION
        "Computer system Name value that is generated
        automatically. The CIM_ComputerSystem object and
        its derivatives are top level objects of the Common
        Information Model (CIM). They provide the scope for
        several components. Unique CIM_System keys are
        required, but you can define a heuristic to create
        the CIM_ComputerSystem name that generates the same
        name, and is independent from the discovery
        protocol. This prevents inventory and management
        problems when the same asset or entity is
        discovered multiple times, but cannot be resolved
        to one object. Using a heuristic is recommended but
        not required.
        The heuristic is outlined in the CIM V2 Common
        Model specification, and assumes that the
        documented rules are used to determine and assign a
        name. The NameFormat values list defines the order
        to assign a computer system name. Several rules map
        to the same value.
        The CIM_ComputerSystem Name value that is
        calculated using the heuristic is the key value of
        the system. However, you can use aliases to assign
        a different name for CIM_ComputerSystem, which can
        be more unique to your company. This property is
        inherited from CIM_System."
    ::= { win32ComputerSystemEntry 28 }

oscsNetworkServerModeEnabled  OBJECT-TYPE
    SYNTAX     TruthValue
    MAX-ACCESS read-only
    STATUS     current
    DESCRIPTION
        "Network Server Mode is enabled."
    ::= { win32ComputerSystemEntry 29 }

oscsNumberOfProcessors  OBJECT-TYPE
    SYNTAX     Gauge32
    MAX-ACCESS read-only
    STATUS     current
    DESCRIPTION
        "Number of physical processors currently available
        on a system. This is the number of enabled
        processors for a system, which does not include the
        disabled processors. If a computer system has two
        physical processors each containing two logical
        processors, then the value of NumberOfProcessors is
        2 and NumberOfLogicalProcessors is 4. The
        processors may be multi-core or they may be
        hyperthreading processors. For more information,
        see Remarks.
        
        Windows Server 2003, Windows XP, and Windows 2000: 
        Because the NumberOfLogicalProcessors property is
        not available, NumberOfProcessors indicates the
        number of logical processors available in the
        system. In the case of a computer system that has
        two physical processors each containing two logical
        processors, the value of NumberOfProcessors is 4."
    ::= { win32ComputerSystemEntry 30 }

oscsOEMLogoBitmap  OBJECT-TYPE
    SYNTAX     WtcsDisplayString
    MAX-ACCESS read-only
    STATUS     current
    DESCRIPTION
        "List of data for a bitmap that the original
        equipment manufacturer (OEM) creates."
    ::= { win32ComputerSystemEntry 31 }

oscsOEMStringArray  OBJECT-TYPE
    SYNTAX     WtcsDisplayString
    MAX-ACCESS read-only
    STATUS     current
    DESCRIPTION
        "List of free form strings that an OEM defines. For
        example, an OEM defines the part numbers for system
        reference documents, manufacturer contact
        information, and so on."
    ::= { win32ComputerSystemEntry 32 }

oscsPartOfDomain  OBJECT-TYPE
    SYNTAX     TruthValue
    MAX-ACCESS read-only
    STATUS     current
    DESCRIPTION
        "Windows XP, Windows Server 2003:  If true, the
        computer is part of a domain or workgroup. If the
        value is NULL, the computer is not a part of a
        domain or workgroup, or the status is unknown. "
    ::= { win32ComputerSystemEntry 33 }

oscsPauseAfterReset  OBJECT-TYPE
    SYNTAX     Integer32
    UNITS "Milliseconds"
    MAX-ACCESS read-only
    STATUS     current
    DESCRIPTION
        "Time delay before a reboot is initiated in
        milliseconds. It is used after a system power
        cycle, local or remote system reset, and automatic
        system reset. A value of -1 (minus one) indicates
        that the pause value is unknown."
    ::= { win32ComputerSystemEntry 34 }

oscsPowerManagementCapabilities  OBJECT-TYPE
    SYNTAX     WtcsDisplayString
    MAX-ACCESS read-only
    STATUS     current
    DESCRIPTION
        "Specific power capabilities of a logical device.
        The Enabled value indicates that the power
        management features are currently enabled, but the
        exact setting is unknown or the information is
        unavailable. Power Saving Modes Entered
        Automatically indicates that a device can change
        its power state based on usage or other criteria.
        Power State Settable indicates that the
        SetPowerState method is supported. Power Cycling
        Supported indicates that the SetPowerState method
        can be invoked with the PowerState parameter set to
        5; Timed Power On Supported indicates that the
        SetPowerState method can be invoked with the
        PowerState parameter set to 5; and Time set to a
        specific date and time, or interval to power ON.
        This property is inherited from
        CIM_UnitaryComputerSystem.
        Value Meaning 
        0 Unknown 
        1 Not Supported 
        2 Disabled 
        3 Enabled 
        4 Power Saving Modes Entered Automatically 
        5 Power State Settable 
        6 Power Cycling Supported 
        7 Timed Power On Supported "
    ::= { win32ComputerSystemEntry 35 }

oscsPowerManagementSupported  OBJECT-TYPE
    SYNTAX     TruthValue
    MAX-ACCESS read-only
    STATUS     current
    DESCRIPTION
        "Device can be power-managed, for example, a device
        can be put into suspend mode, and so on. This
        property does not indicate that power management
        features are enabled currently, but it does
        indicate that the logical device is capable of
        power management. This property is inherited from
        CIM_UnitaryComputerSystem."
    ::= { win32ComputerSystemEntry 36 }

oscsPowerOnPasswordStatus  OBJECT-TYPE
    SYNTAX     INTEGER {
        disabled(0),
        enabled(1),
        notImplemented(2),
        unknown(3)
    }
    MAX-ACCESS read-only
    STATUS     current
    DESCRIPTION
        "System hardware security settings for Power On
        Password Status."
    ::= { win32ComputerSystemEntry 37 }

oscsPowerState  OBJECT-TYPE
    SYNTAX     INTEGER {
        unknown(0),
        fullPower(1),
        powerSaveLowPowerMode(2),
        powerSaveStandby(3),
        powerSaveUnknown(4),
        powerCycle(5),
        powerOff(6),
        powerSaveWarning(7)
    }
    MAX-ACCESS read-only
    STATUS     current
    DESCRIPTION
        "Current power state of a computer and its
        associated operating system. The power saving
        states have the following values: Value 4 (Unknown)
        indicates that the system is known to be in a power
        save mode, but its exact status in this mode is
        unknown; 2 (Low Power Mode) indicates that the
        system is in a power save state, but still
        functioning and may exhibit degraded performance; 3
        (Standby) indicates that the system is not
        functioning, but could be brought to full power
        quickly; and 7 (Warning) indicates that the
        computerSystem is in a warning state and a power
        save mode. This property is inherited from
        CIM_UnitaryComputerSystem."
    ::= { win32ComputerSystemEntry 38 }

oscsPowerSupplyState  OBJECT-TYPE
    SYNTAX     INTEGER {
        other(1),
        unknown(2),
        safe(3),
        warning(4),
        critical(5),
        nonrecoverable(6)
    }
    MAX-ACCESS read-only
    STATUS     current
    DESCRIPTION
        "State of the power supply or supplies when last
        booted."
    ::= { win32ComputerSystemEntry 39 }

oscsPrimaryOwnerContact  OBJECT-TYPE
    SYNTAX     WtcsDisplayString
    MAX-ACCESS read-only
    STATUS     current
    DESCRIPTION
        "Contact information for the primary system owner,
        for example, phone number, e-mail address, and so
        on. This property is inherited from CIM_System."
    ::= { win32ComputerSystemEntry 40 }

oscsPrimaryOwnerName  OBJECT-TYPE
    SYNTAX     WtcsDisplayString
    MAX-ACCESS read-only
    STATUS     current
    DESCRIPTION
        "Name of the primary system owner. This property is
        inherited from CIM_System."
    ::= { win32ComputerSystemEntry 41 }

oscsResetCapability  OBJECT-TYPE
    SYNTAX     INTEGER {
        other(1),
        unknown(2),
        disabled(3),
        enabled(4),
        nonrecoverable(5)
    }
    MAX-ACCESS read-only
    STATUS     current
    DESCRIPTION
        "If enabled, the value is 4 and the unitary
        computer system can be reset using the power and
        reset buttons. If disabled the value is 3, and a
        reset is not allowed. This property is inherited
        from CIM_UnitaryComputerSystem."
    ::= { win32ComputerSystemEntry 42 }

oscsResetCount  OBJECT-TYPE
    SYNTAX     Integer32
    MAX-ACCESS read-only
    STATUS     current
    DESCRIPTION
        "Number of automatic resets since the last reset. A
        value of -1 (minus one) indicates that the count is
        unknown."
    ::= { win32ComputerSystemEntry 43 }

oscsResetLimit  OBJECT-TYPE
    SYNTAX     Integer32
    MAX-ACCESS read-only
    STATUS     current
    DESCRIPTION
        "Number of consecutive times a system reset is
        attempted. A value of -1 (minus one) indicates that
        the limit is unknown."
    ::= { win32ComputerSystemEntry 44 }

oscsRoles  OBJECT-TYPE
    SYNTAX     WtcsDisplayString
    MAX-ACCESS read-only
    STATUS     current
    DESCRIPTION
        "List that specifies the roles of a system in the
        information technology environment. This property
        is inherited from CIM_System."
    ::= { win32ComputerSystemEntry 45 }

oscsStatus  OBJECT-TYPE
    SYNTAX     INTEGER {
        ok(1),
        error(2),
        degraded(3),
        unknown(4),
        predFail(5),
        starting(6),
        stopping(7),
        service(8)
    }
    MAX-ACCESS read-only
    STATUS     current
    DESCRIPTION
        "Current status of an object. Various operational
        and non-operational statuses can be defined.
        Operational statuses include: OK, Degraded, and
        Pred Fail, which is an element such as a
        SMART-enabled hard drive that may be functioning
        properly, but predicts a failure in the near
        future. Non-operational statuses include: Error,
        Starting, Stopping, and Service, which can apply
        during mirror resilvering of a disk, reloading a
        user permissions list, or other administrative
        work. Not all status work is online, but the
        managed element is not OK or in one of the other
        states. This property is inherited from
        CIM_ManagedSystemElement."
    ::= { win32ComputerSystemEntry 46 }

oscsSupportContactDescription  OBJECT-TYPE
    SYNTAX     WtcsDisplayString
    MAX-ACCESS read-only
    STATUS     current
    DESCRIPTION
        "List of the support contact information for the
        Windows operating system."
    ::= { win32ComputerSystemEntry 47 }

oscsSystemStartupDelay  OBJECT-TYPE
    SYNTAX     Integer32 (0..65535)
    UNITS "Seconds"
    MAX-ACCESS read-only
    STATUS     current
    DESCRIPTION
        "Time to delay before starting the Windows
        operating system in seconds."
    ::= { win32ComputerSystemEntry 48 }

oscsSystemStartupOptions  OBJECT-TYPE
    SYNTAX     WtcsDisplayString
    MAX-ACCESS read-only
    STATUS     current
    DESCRIPTION
        "List of the options for starting up the Windows
        operating system. This property must have a value."
    ::= { win32ComputerSystemEntry 49 }

oscsSystemStartupSetting  OBJECT-TYPE
    SYNTAX     Integer32 (0..255)
    MAX-ACCESS read-only
    STATUS     current
    DESCRIPTION
        "Index of the default start up profile. This value
        is calculated so that it usually returns 0 (zero),
        because at write-time the profile string is
        physically moved to the top of the list, which is
        how Windows NT determines the default value."
    ::= { win32ComputerSystemEntry 50 }

oscsSystemType  OBJECT-TYPE
    SYNTAX     INTEGER {
        x86BasedPC(1),
        mipsBasedPC(2),
        alphaBasedPC(3),
        powerPC(4),
        shxPC(5),
        strongARMPC(6),
        n64bitIntelPC(7),
        n64bitAlphaPC(8),
        unknown(9),
        x86Nec98PC(10)
    }
    MAX-ACCESS read-only
    STATUS     current
    DESCRIPTION
        "System running on the Windows computer. This
        property must have a value."
    ::= { win32ComputerSystemEntry 51 }

oscsThermalState  OBJECT-TYPE
    SYNTAX     INTEGER {
        other(1),
        unknown(2),
        safe(3),
        warning(4),
        critical(5),
        nonrecoverable(6)
    }
    MAX-ACCESS read-only
    STATUS     current
    DESCRIPTION
        "Thermal state of the system when last booted."
    ::= { win32ComputerSystemEntry 52 }

oscsTotalPhysicalMemory  OBJECT-TYPE
    SYNTAX     Gauge32
    UNITS "Bytes"
    MAX-ACCESS read-only
    STATUS     current
    DESCRIPTION
        "Total size of physical memory.
        Example: 67108864"
    ::= { win32ComputerSystemEntry 53 }

oscsUserName  OBJECT-TYPE
    SYNTAX     WtcsDisplayString
    MAX-ACCESS read-only
    STATUS     current
    DESCRIPTION
        "Name of a user that is logged on currently. This
        property must have a value. In a terminal services
        session, UserName returns the name of the user that
        is logged on to the console not the user logged on
        during the terminal service session.
        Example: jeffsmith"
    ::= { win32ComputerSystemEntry 54 }

oscsWakeUpType  OBJECT-TYPE
    SYNTAX     INTEGER {
        reserved(0),
        other(1),
        unknown(2),
        apmTimer(3),
        modemRing(4),
        lanRemote(5),
        powerSwitch(6),
        pciPME(7),
        acPowerRestored(8)
    }
    MAX-ACCESS read-only
    STATUS     current
    DESCRIPTION
        "Event that causes the system to power up."
    ::= { win32ComputerSystemEntry 55 }

oscsWorkgroup  OBJECT-TYPE
    SYNTAX     WtcsDisplayString
    MAX-ACCESS read-only
    STATUS     current
    DESCRIPTION
        "Windows Server 2003 and Windows XP:  Name of the
        workgroup for this computer. If the value of the
        PartOfDomain property is false, then the name of
        the workgroup is returned. "
    ::= { win32ComputerSystemEntry 56 }

oscsAutomaticManagedPagefile OBJECT-TYPE
    SYNTAX     TruthValue
    MAX-ACCESS read-only
    STATUS     current
    DESCRIPTION
        "If True, the system manages the page file."
    ::= { win32ComputerSystemEntry 57 }

oscsNumberOfLogicalProcessors OBJECT-TYPE
    SYNTAX     Integer32
    MAX-ACCESS read-only
    STATUS     current
    DESCRIPTION
        "Number of logical processors available on the
        computer.
        
        You can use NumberOfLogicalProcessors and
        NumberOfProcessors to determine if the computer is
        hyperthreading. For more information, see Remarks."
    ::= { win32ComputerSystemEntry 58 }

oscsPCSystemType OBJECT-TYPE
    SYNTAX     INTEGER {
        unspecified(0),
        desktop(1),
        mobile(2),
        workstation(3),
        enterpriseServer(4),
        sohoServer(5),
        appliancePC(6),
        performanceServer(7),
        maximum(8)
    }
    MAX-ACCESS read-only
    STATUS     current
    DESCRIPTION
        "Type of the computer in use, such as laptop,
        desktop, or Tablet."
    ::= { win32ComputerSystemEntry 59 }

win32ComputerSystemProductTable OBJECT-TYPE
    SYNTAX     SEQUENCE OF Win32ComputerSystemProductEntry
    MAX-ACCESS not-accessible
    STATUS     current
    DESCRIPTION
        "The Win32_ComputerSystemProduct WMI class
        represents a product. This includes software and
        hardware used on this computer system."
    ::= { wmiOperatingSystemSettings 3 }

win32ComputerSystemProductEntry OBJECT-TYPE
    SYNTAX     Win32ComputerSystemProductEntry
    MAX-ACCESS not-accessible
    STATUS     current
    DESCRIPTION
        "None"
    INDEX      { oscspIndex }
    ::= { win32ComputerSystemProductTable 1 }

Win32ComputerSystemProductEntry ::= SEQUENCE {
    oscspIndex Integer32,
    oscspCaption  WtcsDisplayString,
    oscspDescription  WtcsDisplayString,
    oscspIdentifyingNumber  WtcsDisplayString,
    oscspName  WtcsDisplayString,
    oscspSKUNumber  WtcsDisplayString,
    oscspUUID  WtcsDisplayString,
    oscspVendor  WtcsDisplayString,
    oscspVersion  WtcsDisplayString
}

oscspIndex OBJECT-TYPE
    SYNTAX     Integer32 (1..2147483647)
    MAX-ACCESS read-only
    STATUS     current
    DESCRIPTION
        "The value of this object uniquely identifies the
        instance entry for this class."
    ::= { win32ComputerSystemProductEntry 1 }

oscspCaption  OBJECT-TYPE
    SYNTAX     WtcsDisplayString (SIZE (0..64))
    MAX-ACCESS read-only
    STATUS     current
    DESCRIPTION
        "Short description of the object a one-line string.
        This property is inherited from CIM_Product."
    ::= { win32ComputerSystemProductEntry 2 }

oscspDescription  OBJECT-TYPE
    SYNTAX     WtcsDisplayString
    MAX-ACCESS read-only
    STATUS     current
    DESCRIPTION
        "Description of the product. This property is
        inherited from CIM_Product."
    ::= { win32ComputerSystemProductEntry 3 }

oscspIdentifyingNumber  OBJECT-TYPE
    SYNTAX     WtcsDisplayString (SIZE (0..64))
    MAX-ACCESS read-only
    STATUS     current
    DESCRIPTION
        "Product identification such as a serial number on
        software or a die number on a hardware chip. This
        property is inherited from CIM_Product."
    ::= { win32ComputerSystemProductEntry 4 }

oscspName  OBJECT-TYPE
    SYNTAX     WtcsDisplayString (SIZE (0..256))
    MAX-ACCESS read-only
    STATUS     current
    DESCRIPTION
        "Commonly used product name. This property is
        inherited from CIM_Product."
    ::= { win32ComputerSystemProductEntry 5 }

oscspSKUNumber  OBJECT-TYPE
    SYNTAX     WtcsDisplayString (SIZE (0..64))
    MAX-ACCESS read-only
    STATUS     current
    DESCRIPTION
        "Product SKU (stock-keeping unit) information. This
        property is inherited from CIM_Product."
    ::= { win32ComputerSystemProductEntry 6 }

oscspUUID  OBJECT-TYPE
    SYNTAX     WtcsDisplayString
    MAX-ACCESS read-only
    STATUS     current
    DESCRIPTION
        "Universally unique identifier (UUID) for this
        product. A UUID is a 128-bit identifier that is
        guaranteed to be different from other generated
        UUIDs. If a UUID is not available, a UUID of all
        zeros is used."
    ::= { win32ComputerSystemProductEntry 7 }

oscspVendor  OBJECT-TYPE
    SYNTAX     WtcsDisplayString (SIZE (0..256))
    MAX-ACCESS read-only
    STATUS     current
    DESCRIPTION
        "Name of the product supplier. Corresponds to the
        Vendor property in the product object in the
        Desktop Management Task Force (DMTF) Solution
        Exchange Standard. This property is inherited from
        CIM_Product."
    ::= { win32ComputerSystemProductEntry 8 }

oscspVersion  OBJECT-TYPE
    SYNTAX     WtcsDisplayString (SIZE (0..64))
    MAX-ACCESS read-only
    STATUS     current
    DESCRIPTION
        "Product version information. Corresponds to the
        Version property in the product object in the DMTF
        Solution Exchange Standard. This property is
        inherited from CIM_Product."
    ::= { win32ComputerSystemProductEntry 9 }

win32LoadOrderGroupTable OBJECT-TYPE
    SYNTAX     SEQUENCE OF Win32LoadOrderGroupEntry
    MAX-ACCESS not-accessible
    STATUS     current
    DESCRIPTION
        "The Win32_LoadOrderGroup WMI class represents a
        group of system services that define execution
        dependencies. The services must be initiated in the
        order specified by the Load Order Group, as the
        services are dependent on each other. These
        dependent services require the presence of the
        antecedent services to function correctly. The data
        in this class is derived by the provider from the
        registry key:
        System\CurrentControlSet\Control\GroupOrderList"
    ::= { wmiOperatingSystemSettings 4 }

win32LoadOrderGroupEntry OBJECT-TYPE
    SYNTAX     Win32LoadOrderGroupEntry
    MAX-ACCESS not-accessible
    STATUS     current
    DESCRIPTION
        "None"
    INDEX      { oslogIndex }
    ::= { win32LoadOrderGroupTable 1 }

Win32LoadOrderGroupEntry ::= SEQUENCE {
    oslogIndex Integer32,
    oslogCaption  WtcsDisplayString,
    oslogDescription  WtcsDisplayString,
    oslogDriverEnabled  TruthValue,
    oslogGroupOrder  Gauge32,
    oslogInstallDate  DateAndTime,
    oslogName  WtcsDisplayString,
    oslogStatus  INTEGER
}

oslogIndex OBJECT-TYPE
    SYNTAX     Integer32 (1..2147483647)
    MAX-ACCESS read-only
    STATUS     current
    DESCRIPTION
        "The value of this object uniquely identifies the
        instance entry for this class."
    ::= { win32LoadOrderGroupEntry 1 }

oslogCaption  OBJECT-TYPE
    SYNTAX     WtcsDisplayString
    MAX-ACCESS read-only
    STATUS     current
    DESCRIPTION
        "Short description (one-line string) of the
        object."
    ::= { win32LoadOrderGroupEntry 2 }

oslogDescription  OBJECT-TYPE
    SYNTAX     WtcsDisplayString
    MAX-ACCESS read-only
    STATUS     current
    DESCRIPTION
        "Description of the object."
    ::= { win32LoadOrderGroupEntry 3 }

oslogDriverEnabled  OBJECT-TYPE
    SYNTAX     TruthValue
    MAX-ACCESS read-only
    STATUS     current
    DESCRIPTION
        "Indicates whether this load order group can
        include drivers along with system services. "
    ::= { win32LoadOrderGroupEntry 4 }

oslogGroupOrder  OBJECT-TYPE
    SYNTAX     Gauge32
    MAX-ACCESS read-only
    STATUS     current
    DESCRIPTION
        "Sequence in which this group of services is loaded
        onto the operating system.
        Example: 2"
    ::= { win32LoadOrderGroupEntry 5 }

oslogInstallDate  OBJECT-TYPE
    SYNTAX     DateAndTime
    MAX-ACCESS read-only
    STATUS     current
    DESCRIPTION
        "Date object was installed. This property does not
        require a value to indicate that the object is
        installed."
    ::= { win32LoadOrderGroupEntry 6 }

oslogName  OBJECT-TYPE
    SYNTAX     WtcsDisplayString
    MAX-ACCESS read-only
    STATUS     current
    DESCRIPTION
        "Name of the load order group.
        Example: 'Primary disk'"
    ::= { win32LoadOrderGroupEntry 7 }

oslogStatus  OBJECT-TYPE
    SYNTAX     INTEGER {
        ok(1),
        error(2),
        degraded(3),
        unknown(4),
        predFail(5),
        starting(6),
        stopping(7),
        service(8)
    }
    MAX-ACCESS read-only
    STATUS     current
    DESCRIPTION
        "Current status of the object. Various operational
        and non-operational statuses can be defined.
        Operational statuses include: 'OK', 'Degraded', and
        'Pred Fail' (an element, such as a SMART-enabled
        hard drive, may function properly but predicts a
        failure in the near future). Non-operational
        statuses include: 'Error', 'Starting', 'Stopping',
        and 'Service'. The 'Service' status applies to
        administrative work, such as mirror-resilvering of
        a disk or reload of a user permissions list. Not
        all such work is on-line, yet the managed element
        is neither 'OK' nor in one of the other states."
    ::= { win32LoadOrderGroupEntry 8 }

win32OperatingSystemTable OBJECT-TYPE
    SYNTAX     SEQUENCE OF Win32OperatingSystemEntry
    MAX-ACCESS not-accessible
    STATUS     current
    DESCRIPTION
        "The Win32_OperatingSystem WMI class represents an
        operating system installed on a Windows computer
        system. Any operating system that can be installed
        on a Windows system is a descendent or member of
        this class. If a computer has multiple operating
        systems installed, this class returns only an
        instance for the currently active operating
        system."
    ::= { wmiOperatingSystemSettings 5 }

win32OperatingSystemEntry OBJECT-TYPE
    SYNTAX     Win32OperatingSystemEntry
    MAX-ACCESS not-accessible
    STATUS     current
    DESCRIPTION
        "None"
    INDEX      { ososIndex }
    ::= { win32OperatingSystemTable 1 }

Win32OperatingSystemEntry ::= SEQUENCE {
    ososIndex Integer32,
    ososBootDevice  WtcsDisplayString,
    ososBuildNumber  WtcsDisplayString,
    ososBuildType  WtcsDisplayString,
    ososCaption  WtcsDisplayString,
    ososCodeSet  WtcsDisplayString,
    ososCountryCode  WtcsDisplayString,
    ososCreationClassName  WtcsDisplayString,
    ososCSCreationClassName  WtcsDisplayString,
    ososCSDVersion  WtcsDisplayString,
    ososCSName  WtcsDisplayString,
    ososCurrentTimeZone  Integer32,
    ososDataExecPrevention32BitAppl TruthValue,
    ososDataExecPreventionAvailable  TruthValue,
    ososDataExecPreventionDrivers  TruthValue,
    ososDebug  TruthValue,
    ososDescription  WtcsDisplayString,
    ososDistributed  TruthValue,
    ososEncryptionLevel  Gauge32,
    ososForegroundApplicationBoost  INTEGER,
    ososFreePhysicalMemory  Gauge32,
    ososFreeSpaceInPagingFiles  Gauge32,
    ososFreeVirtualMemory  Gauge32,
    ososInstallDate  DateAndTime,
    ososLargeSystemCache  INTEGER,
    ososLastBootUpTime  DateAndTime,
    ososLocalDateTime  DateAndTime,
    ososLocale  WtcsDisplayString,
    ososManufacturer  WtcsDisplayString,
    ososMaxNumberOfProcesses  Gauge32,
    ososMaxProcessMemorySize  Gauge32,
    ososName  WtcsDisplayString,
    ososNumberOfLicensedUsers  Gauge32,
    ososNumberOfProcesses  Gauge32,
    ososNumberOfUsers  Gauge32,
    ososOrganization  WtcsDisplayString,
    ososOSLanguage  INTEGER,
    ososOSProductSuite  Gauge32,
    ososOSType  INTEGER,
    ososOtherTypeDescription  WtcsDisplayString,
    ososPAEEnabled  TruthValue,
    ososPlusProductID  WtcsDisplayString,
    ososPlusVersionNumber  WtcsDisplayString,
    ososPrimary  TruthValue,
    ososProductType  INTEGER,
    ososQuantumLength  INTEGER,
    ososQuantumType  INTEGER,
    ososRegisteredUser  WtcsDisplayString,
    ososSerialNumber  WtcsDisplayString,
    ososServicePackMajorVersion  Integer32,
    ososServicePackMinorVersion  Integer32,
    ososSizeStoredInPagingFiles  Gauge32,
    ososStatus  INTEGER,
    ososSuiteMask  Gauge32,
    ososSystemDevice  WtcsDisplayString,
    ososSystemDirectory  WtcsDisplayString,
    ososSystemDrive  WtcsDisplayString,
    ososTotalSwapSpaceSize  Gauge32,
    ososTotalVirtualMemorySize  Gauge32,
    ososTotalVisibleMemorySize  Gauge32,
    ososVersion  WtcsDisplayString,
    ososWindowsDirectory  WtcsDisplayString
}

ososIndex OBJECT-TYPE
    SYNTAX     Integer32 (1..2147483647)
    MAX-ACCESS read-only
    STATUS     current
    DESCRIPTION
        "The value of this object uniquely identifies the
        instance entry for this class."
    ::= { win32OperatingSystemEntry 1 }

ososBootDevice  OBJECT-TYPE
    SYNTAX     WtcsDisplayString
    MAX-ACCESS read-only
    STATUS     current
    DESCRIPTION
        "Name of the disk drive from which the Windows
        operating system boots.
        Example: '\\Device\Harddisk0'"
    ::= { win32OperatingSystemEntry 2 }

ososBuildNumber  OBJECT-TYPE
    SYNTAX     WtcsDisplayString
    MAX-ACCESS read-only
    STATUS     current
    DESCRIPTION
        "Build number of an operating system. It can be
        used for more precise version information than
        product release version numbers.
        Example: '1381'"
    ::= { win32OperatingSystemEntry 3 }

ososBuildType  OBJECT-TYPE
    SYNTAX     WtcsDisplayString
    MAX-ACCESS read-only
    STATUS     current
    DESCRIPTION
        "Type of build used for an operating system.
        Examples: 'retail build', 'checked build'"
    ::= { win32OperatingSystemEntry 4 }

ososCaption  OBJECT-TYPE
    SYNTAX     WtcsDisplayString
    MAX-ACCESS read-only
    STATUS     current
    DESCRIPTION
        "Short description of the object a one-line string.
        The string includes the operating system version.
        For example, 'Microsoft Windows XP Professional
        Version = 5.1.2500'. This property can be
        localized."
    ::= { win32OperatingSystemEntry 5 }

ososCodeSet  OBJECT-TYPE
    SYNTAX     WtcsDisplayString (SIZE (0..6))
    MAX-ACCESS read-only
    STATUS     current
    DESCRIPTION
        "Code page value an operating system uses. A code
        page contains a character table that an operating
        system uses to translate strings for different
        languages. The American National Standards
        Institute (ANSI) lists values that represent
        defined code pages. If an operating system does not
        use an ANSI code page, this member is set to 0
        (zero). The CodeSet string can use up to six
        characters to define the code page value.
        Example: '1255'"
    ::= { win32OperatingSystemEntry 6 }

ososCountryCode  OBJECT-TYPE
    SYNTAX     WtcsDisplayString
    MAX-ACCESS read-only
    STATUS     current
    DESCRIPTION
        "Code for the country/region that an operating
        system uses. Values are based on international
        phone dialing prefixes also referred to as IBM
        country/region codes. The property can use up to
        six characters to define the country/region code
        value.
        Example: '1' (United States)"
    ::= { win32OperatingSystemEntry 7 }

ososCreationClassName  OBJECT-TYPE
    SYNTAX     WtcsDisplayString (SIZE (0..256))
    MAX-ACCESS read-only
    STATUS     current
    DESCRIPTION
        "Name of the first concrete class that appears in
        the inheritance chain used in the creation of an
        instance. When used with other key properties of
        the class, the property allows all instances of
        this class and its subclasses to be identified
        uniquely."
    ::= { win32OperatingSystemEntry 8 }

ososCSCreationClassName  OBJECT-TYPE
    SYNTAX     WtcsDisplayString
    MAX-ACCESS read-only
    STATUS     current
    DESCRIPTION
        "Creation class name of the scoping computer
        system."
    ::= { win32OperatingSystemEntry 9 }

ososCSDVersion  OBJECT-TYPE
    SYNTAX     WtcsDisplayString
    MAX-ACCESS read-only
    STATUS     current
    DESCRIPTION
        "Null-terminated string that indicates the latest
        service pack installed on a computer system. If no
        service pack is installed, the string is NULL. For
        computers running Windows 95, this property
        contains a null-terminated string that provides
        arbitrary additional information about the
        operating system.
        Example: 'Service Pack 3'"
    ::= { win32OperatingSystemEntry 10 }

ososCSName  OBJECT-TYPE
    SYNTAX     WtcsDisplayString
    MAX-ACCESS read-only
    STATUS     current
    DESCRIPTION
        "Name of the scoping computer system."
    ::= { win32OperatingSystemEntry 11 }

ososCurrentTimeZone  OBJECT-TYPE
    SYNTAX     Integer32
    MAX-ACCESS read-only
    STATUS     current
    DESCRIPTION
        "Number of minutes an operating system is offset
        from Greenwich mean time (GMT). The number is
        positive, negative, or zero."
    ::= { win32OperatingSystemEntry 12 }

ososDataExecPrevention32BitAppl OBJECT-TYPE
    SYNTAX     TruthValue
    MAX-ACCESS read-only
    STATUS     current
    DESCRIPTION
        "When the data execution prevention hardware
        feature is available, then if TRUE, this property
        indicates that the feature is set to work for
        32-bit applications. On 64-bit computers, the data
        execution prevention feature is configured in the
        Boot.ini file and the properties in
        Win32_OperatingSystem are set accordingly. This
        property is set to FALSE on 32-bit computers.
        Windows XP SP1 and earlier:  This property is not
        available.
        Windows Server 2003 and earlier:  This property is
        not available."
    ::= { win32OperatingSystemEntry 13 }

ososDataExecPreventionAvailable  OBJECT-TYPE
    SYNTAX     TruthValue
    MAX-ACCESS read-only
    STATUS     current
    DESCRIPTION
        "Data execution prevention is an AMD 64-bit
        hardware feature to prevent buffer overrun attacks
        by stopping the execution of code on data type
        memory pages. If TRUE, then this feature is
        available. On 64-bit computers, the data execution
        prevention feature is configured in the Boot.ini
        file and the properties in Win32_OperatingSystem
        are set accordingly. This property is set to FALSE
        on 32-bit computers.
        Windows XP SP1 and earlier:  This property is not
        available.
        Windows Server 2003 and earlier:  This property is
        not available."
    ::= { win32OperatingSystemEntry 14 }

ososDataExecPreventionDrivers  OBJECT-TYPE
    SYNTAX     TruthValue
    MAX-ACCESS read-only
    STATUS     current
    DESCRIPTION
        "When the data execution prevention hardware
        feature is available, then if TRUE, this property
        indicates that the feature is set to work for
        drivers. On 64-bit computers, the data execution
        prevention feature is configured in the Boot.ini
        file and the properties in Win32_OperatingSystem
        are set accordingly. This property is set to FALSE
        on 32-bit computers.
        Windows XP SP1 and earlier:  This property is not
        available.
        Windows Server 2003 and earlier:  This property is
        not available."
    ::= { win32OperatingSystemEntry 15 }

ososDebug  OBJECT-TYPE
    SYNTAX     TruthValue
    MAX-ACCESS read-only
    STATUS     current
    DESCRIPTION
        "Operating system is a checked (debug) build. If
        TRUE, the debugging version of User.exe is
        installed. Checked builds provide error checking,
        argument verification, and system debugging code.
        Additional code in a checked binary generates a
        kernel debugger error message and breaks into the
        debugger. This helps immediately determine the
        cause and location of the error. Performance
        suffers in a checked build due to the additional
        code that is executed."
    ::= { win32OperatingSystemEntry 16 }

ososDescription  OBJECT-TYPE
    SYNTAX     WtcsDisplayString
    MAX-ACCESS read-only
    STATUS     current
    DESCRIPTION
        "Description of the Windows operating system. Some
        user interfaces (those that allow editing of this
        description) limit its length to 48 characters."
    ::= { win32OperatingSystemEntry 17 }

ososDistributed  OBJECT-TYPE
    SYNTAX     TruthValue
    MAX-ACCESS read-only
    STATUS     current
    DESCRIPTION
        "Operating system is distributed across several
        computer system nodes. If so, these nodes should be
        grouped as a cluster."
    ::= { win32OperatingSystemEntry 18 }

ososEncryptionLevel  OBJECT-TYPE
    SYNTAX     Gauge32
    MAX-ACCESS read-only
    STATUS     current
    DESCRIPTION
        "Windows Server 2003, Windows XP:  Encryption level
        for secure transactions 40-bit, 128-bit, or n-bit.
        "
    ::= { win32OperatingSystemEntry 19 }

ososForegroundApplicationBoost  OBJECT-TYPE
    SYNTAX     INTEGER {
        none(0),
        minimum(1),
        maximum(2)
    }
    MAX-ACCESS read-only
    STATUS     current
    DESCRIPTION
        "Increase in priority given to the foreground
        application. On computer systems running Windows NT
        4.0 and Windows 2000, application boost is
        implemented by giving an application more execution
        time slices (quantum lengths). A
        ForegroundApplicationBoost value of 0 (zero)
        indicates the system boosts the quantum length by
        6; if 1, then 12; and if 2 then 18. On Windows NT
        3.51 and earlier, application boost is implemented
        by increasing the scheduling priority. For these
        systems, the scheduling priority is increased by
        the value of this property. The default value is
        2."
    ::= { win32OperatingSystemEntry 20 }

ososFreePhysicalMemory  OBJECT-TYPE
    SYNTAX     Gauge32
    MAX-ACCESS read-only
    STATUS     current
    DESCRIPTION
        "Number of kilobytes of physical memory currently
        unused and available."
    ::= { win32OperatingSystemEntry 21 }

ososFreeSpaceInPagingFiles  OBJECT-TYPE
    SYNTAX     Gauge32
    MAX-ACCESS read-only
    STATUS     current
    DESCRIPTION
        "Number of kilobytes that can be mapped into the
        operating system paging files without causing any
        other pages to be swapped out."
    ::= { win32OperatingSystemEntry 22 }

ososFreeVirtualMemory  OBJECT-TYPE
    SYNTAX     Gauge32
    MAX-ACCESS read-only
    STATUS     current
    DESCRIPTION
        "Number of kilobytes of virtual memory currently
        unused and available. For example, this may be
        calculated by adding the amount of free RAM to the
        amount of free paging space, that is, adding the
        FreePhysicalMemory and FreeSpaceInPagingFiles
        properties."
    ::= { win32OperatingSystemEntry 23 }

ososInstallDate  OBJECT-TYPE
    SYNTAX     DateAndTime
    MAX-ACCESS read-only
    STATUS     current
    DESCRIPTION
        "Date object was installed. This property does not
        require a value to indicate that the object is
        installed."
    ::= { win32OperatingSystemEntry 24 }

ososLargeSystemCache  OBJECT-TYPE
    SYNTAX     INTEGER {
        optimizeMemoryForApplications(0),
        optimizeMemoryForSystemPerform(1)
    }
    MAX-ACCESS read-only
    STATUS     current
    DESCRIPTION
        "Indicates whether or not to optimize memory for
        applications or system performance.
        Windows  2000 and earlier:  This property is not
        available."
    ::= { win32OperatingSystemEntry 25 }

ososLastBootUpTime  OBJECT-TYPE
    SYNTAX     DateAndTime
    MAX-ACCESS read-only
    STATUS     current
    DESCRIPTION
        "Operating system was last booted."
    ::= { win32OperatingSystemEntry 26 }

ososLocalDateTime  OBJECT-TYPE
    SYNTAX     DateAndTime
    MAX-ACCESS read-only
    STATUS     current
    DESCRIPTION
        "Operating system's version of the local date and
        time of day."
    ::= { win32OperatingSystemEntry 27 }

ososLocale  OBJECT-TYPE
    SYNTAX     WtcsDisplayString
    MAX-ACCESS read-only
    STATUS     current
    DESCRIPTION
        "Language identifier used by the operating system.
        A language identifier is a standard international
        numeric abbreviation for a country/region. Each
        language has a unique language identifier (LANGID),
        a 16-bit value that consists of a primary language
        identifier and a secondary language identifier."
    ::= { win32OperatingSystemEntry 28 }

ososManufacturer  OBJECT-TYPE
    SYNTAX     WtcsDisplayString
    MAX-ACCESS read-only
    STATUS     current
    DESCRIPTION
        "Name of the operating system manufacturer. For
        Windows systems, this value is 'Microsoft
        Corporation'."
    ::= { win32OperatingSystemEntry 29 }

ososMaxNumberOfProcesses  OBJECT-TYPE
    SYNTAX     Gauge32
    MAX-ACCESS read-only
    STATUS     current
    DESCRIPTION
        "Maximum number of process contexts the operating
        system can support. If there is no fixed maximum,
        the value should be 0 (zero). On systems that have
        a fixed maximum, this object can help diagnose
        failures that occur when the maximum is reached if
        unknown, enter -1."
    ::= { win32OperatingSystemEntry 30 }

ososMaxProcessMemorySize  OBJECT-TYPE
    SYNTAX     Gauge32
    MAX-ACCESS read-only
    STATUS     current
    DESCRIPTION
        "Maximum number of kilobytes of memory that can be
        allocated to a process. For operating systems with
        no virtual memory, typically this value is equal to
        the total amount of physical memory minus the
        memory used by the BIOS and OS. For some operating
        systems, this value may be infinity, in which case
        0 (zero) should be entered. In other cases, this
        value could be a constant, for example, 2G or 4G."
    ::= { win32OperatingSystemEntry 31 }

ososName  OBJECT-TYPE
    SYNTAX     WtcsDisplayString
    MAX-ACCESS read-only
    STATUS     current
    DESCRIPTION
        "Operating system instance within a computer
        system."
    ::= { win32OperatingSystemEntry 32 }

ososNumberOfLicensedUsers  OBJECT-TYPE
    SYNTAX     Gauge32
    MAX-ACCESS read-only
    STATUS     current
    DESCRIPTION
        "Number of user licenses for the operating system.
        If unlimited, enter 0 (zero). If unknown, enter
        -1."
    ::= { win32OperatingSystemEntry 33 }

ososNumberOfProcesses  OBJECT-TYPE
    SYNTAX     Gauge32
    MAX-ACCESS read-only
    STATUS     current
    DESCRIPTION
        "Number of process contexts currently loaded or
        running on the operating system."
    ::= { win32OperatingSystemEntry 34 }

ososNumberOfUsers  OBJECT-TYPE
    SYNTAX     Gauge32
    MAX-ACCESS read-only
    STATUS     current
    DESCRIPTION
        "Number of user sessions for which the operating
        system is storing state information currently. "
    ::= { win32OperatingSystemEntry 35 }

ososOrganization  OBJECT-TYPE
    SYNTAX     WtcsDisplayString
    MAX-ACCESS read-only
    STATUS     current
    DESCRIPTION
        "Company name for the registered user of the
        operating system.
        Example: 'Microsoft Corporation'"
    ::= { win32OperatingSystemEntry 36 }

ososOSLanguage  OBJECT-TYPE
    SYNTAX     INTEGER {
        arabic(1),
        chinese(4),
        english(9),
        arabicSaudiArabia(1025),
        bulgarian(1026),
        catalan(1027),
        chineseTaiwan(1028),
        czech(1029),
        danish(1030),
        germanGermany(1031),
        greek(1032),
        englishUnitedStates(1033),
        spanishTraditionalSort(1034),
        finnish(1035),
        frenchFrance(1036),
        hebrew(1037),
        hungarian(1038),
        icelandic(1039),
        italianItaly(1040),
        japanese(1041),
        korean(1042),
        dutchNetherlands(1043),
        norwegianBokmal(1044),
        polish(1045),
        portugueseBrazil(1046),
        rhaetoRomanic(1047),
        romanian(1048),
        russian(1049),
        croatian(1050),
        slovak(1051),
        albanian(1052),
        swedish(1053),
        thai(1054),
        turkish(1055),
        urdu(1056),
        indonesian(1057),
        ukrainian(1058),
        belarusian(1059),
        slovenian(1060),
        estonian(1061),
        latvian(1062),
        lithuanian(1063),
        farsi(1065),
        vietnamese(1066),
        basque(1069),
        serbian(1070),
        macedonianFYROM(1071),
        sutu(1072),
        tsonga(1073),
        tswana(1074),
        xhosa(1076),
        zulu(1077),
        afrikaans(1078),
        faeroese(1080),
        hindi(1081),
        maltese(1082),
        gaelic(1084),
        yiddish(1085),
        malayMalaysia(1086),
        arabicIraq(2049),
        chinesePRC(2052),
        germanSwitzerland(2055),
        englishUnitedKingdom(2057),
        spanishMexico(2058),
        frenchBelgium(2060),
        italianSwitzerland(2064),
        dutchBelgium(2067),
        norwegianNynorsk(2068),
        portuguesePortugal(2070),
        romanianMoldova(2072),
        russianMoldova(2073),
        serbianLatin(2074),
        swedishFinland(2077),
        arabicEgypt(3073),
        chineseHongKongSAR(3076),
        germanAustria(3079),
        englishAustralia(3081),
        spanishInternationalSort(3082),
        frenchCanada(3084),
        serbianCyrillic(3098),
        arabicLibya(4097),
        chineseSingapore(4100),
        germanLuxembourg(4103),
        englishCanada(4105),
        spanishGuatemala(4106),
        frenchSwitzerland(4108),
        arabicAlgeria(5121),
        germanLiechtenstein(5127),
        englishNewZealand(5129),
        spanishCostaRica(5130),
        frenchLuxembourg(5132),
        arabicMorocco(6145),
        englishIreland(6153),
        spanishPanama(6154),
        arabicTunisia(7169),
        englishSouthAfrica(7177),
        spanishDominicanRepublic(7178),
        arabicOman(8193),
        englishJamaica(8201),
        spanishVenezuela(8202),
        arabicYemen(9217),
        spanishColombia(9226),
        arabicSyria(10241),
        englishBelize(10249),
        spanishPeru(10250),
        arabicJordan(11265),
        englishTrinidad(11273),
        spanishArgentina(11274),
        arabicLebanon(12289),
        spanishEcuador(12298),
        arabicKuwait(13313),
        spanishChile(13322),
        arabicUAE(14337),
        spanishUruguay(14346),
        arabicBahrain(15361),
        spanishParaguay(15370),
        arabicQatar(16385),
        spanishBolivia(16394),
        spanishElSalvador(17418),
        spanishHonduras(18442),
        spanishNicaragua(19466),
        spanishPuertoRico(20490)
    }
    MAX-ACCESS read-only
    STATUS     current
    DESCRIPTION
        "Language version of the operating system
        installed."
    ::= { win32OperatingSystemEntry 37 }

ososOSProductSuite  OBJECT-TYPE
    SYNTAX     Gauge32
    MAX-ACCESS read-only
    STATUS     current
    DESCRIPTION
        "Installed and licensed system product additions to
        the operating system. For example, the value of 146
        (0x92) for OSProductSuite indicates Enterprise,
        Terminal Server, and Data Center (bits one, four,
        and seven set). The following table identifies the
        possible values.
        
        Value Meaning
        0x1 Small Business
        0x2 Enterprise
        0x4 BackOffice
        0x8 Communication Server
        0x10 Terminal Server
        0x20 Small Business (Restricted)
        0x40 Embedded NT
        0x80 Data Center"
    ::= { win32OperatingSystemEntry 38 }

ososOSType  OBJECT-TYPE
    SYNTAX     INTEGER {
        unknown(0),
        other(1),
        macros(2),
        attunix(3),
        dgux(4),
        decnt(5),
        digitalUnix(6),
        openVMS(7),
        hpux(8),
        aix(9),
        mvs(10),
        os400(11),
        os2(12),
        javaVM(13),
        msdos(14),
        win3x(15),
        win95(16),
        win98(17),
        winnt(18),
        wince(19),
        ncr3000(20),
        netWare(21),
        osf(22),
        dcOS(23),
        reliantUNIX(24),
        scoUnixWare(25),
        scoOpenServer(26),
        sequent(27),
        irix(28),
        solaris(29),
        sunOS(30),
        u6000(31),
        aseries(32),
        tandemNSK(33),
        tandemNT(34),
        bs2000(35),
        linux(36),
        lynx(37),
        xenix(38),
        vmESA(39),
        interactiveUNIX(40),
        bsdunix(41),
        freeBSD(42),
        netBSD(43),
        gnuHurd(44),
        os9(45),
        machKernel(46),
        inferno(47),
        qnx(48),
        epoc(49),
        ixWorks(50),
        vxWorks(51),
        miNT(52),
        beOS(53),
        hpMPE(54),
        nextStep(55),
        palmPilot(56),
        rhapsody(57)
    }
    MAX-ACCESS read-only
    STATUS     current
    DESCRIPTION
        "Type of operating system."
    ::= { win32OperatingSystemEntry 39 }

ososOtherTypeDescription  OBJECT-TYPE
    SYNTAX     WtcsDisplayString
    MAX-ACCESS read-only
    STATUS     current
    DESCRIPTION
        "Manufacturer and operating system type that is
        used when the operating system property OSType is
        set to 1 (Other). The format of the string inserted
        in OtherTypeDescription should be similar in format
        to the value strings defined for OSType. The
        OtherTypeDescription property should be set to NULL
        when OSType is any value other than 1."
    ::= { win32OperatingSystemEntry 40 }

ososPAEEnabled  OBJECT-TYPE
    SYNTAX     TruthValue
    MAX-ACCESS read-only
    STATUS     current
    DESCRIPTION
        "Physical Address Extension (PAE) is enabled by the
        operating system running on Intel processors. PAE
        allows applications to address more than 4 GB of
        physical memory. When PAE is enabled, the operating
        system uses three-level linear address translation
        rather than two-level. Providing more physical
        memory to an application reduces the need to swap
        memory to the page file and increases performance.
        To enable, PAE, use the /PAE switch in the Boot.ini
        file.
        Windows XP and earlier:  The PAEEnabled property is
        not available."
    ::= { win32OperatingSystemEntry 41 }

ososPlusProductID  OBJECT-TYPE
    SYNTAX     WtcsDisplayString
    MAX-ACCESS read-only
    STATUS     current
    DESCRIPTION
        "Identification number for the Windows Plus!
        operating system enhancement software if
        installed."
    ::= { win32OperatingSystemEntry 42 }

ososPlusVersionNumber  OBJECT-TYPE
    SYNTAX     WtcsDisplayString
    MAX-ACCESS read-only
    STATUS     current
    DESCRIPTION
        "Version number of the Windows Plus! operating
        system enhancement software if installed."
    ::= { win32OperatingSystemEntry 43 }

ososPrimary  OBJECT-TYPE
    SYNTAX     TruthValue
    MAX-ACCESS read-only
    STATUS     current
    DESCRIPTION
        "Primary operating system."
    ::= { win32OperatingSystemEntry 44 }

ososProductType  OBJECT-TYPE
    SYNTAX     INTEGER {
        workStation(1),
        domainController(2),
        server(3)
    }
    MAX-ACCESS read-only
    STATUS     current
    DESCRIPTION
        "Additional information about the system."
    ::= { win32OperatingSystemEntry 45 }

ososQuantumLength  OBJECT-TYPE
    SYNTAX     INTEGER {
        unknown(1),
        oneTick(2),
        twoTicks(3)
    }
    MAX-ACCESS read-only
    STATUS     current
    DESCRIPTION
        "Number of clock ticks per quantum. A quantum is a
        unit of execution time that the scheduler is
        allowed to give to an application before switching
        to other applications. When a thread runs one
        quantum, the kernel preempts it and moves it to the
        end of a queue for applications with equal
        priorities. The actual length of a thread's quantum
        varies across different Windows platforms Windows
        NT/Windows 2000 only."
    ::= { win32OperatingSystemEntry 46 }

ososQuantumType  OBJECT-TYPE
    SYNTAX     INTEGER {
        unknown(1),
        fixed(2),
        variable(3)
    }
    MAX-ACCESS read-only
    STATUS     current
    DESCRIPTION
        "Length type of quantums. Windows NT 4.0
        Workstation/Windows 2000 defaults to
        variable-length quantums where the foreground
        application has a longer quantum than the
        background applications. Windows NT server defaults
        to fixed-length quantums. A quantum is a unit of
        execution time that the scheduler is allowed to
        give to an application before switching to another
        application. When a thread runs one quantum, the
        kernel preempts it and moves it to the end of a
        queue for applications with equal priorities. The
        actual length of a thread's quantum varies across
        different Windows platforms. For Windows NT/Windows
        2000 only."
    ::= { win32OperatingSystemEntry 47 }

ososRegisteredUser  OBJECT-TYPE
    SYNTAX     WtcsDisplayString
    MAX-ACCESS read-only
    STATUS     current
    DESCRIPTION
        "Name of the registered user of the operating
        system.
        Example: 'Ben Smith'"
    ::= { win32OperatingSystemEntry 48 }

ososSerialNumber  OBJECT-TYPE
    SYNTAX     WtcsDisplayString
    MAX-ACCESS read-only
    STATUS     current
    DESCRIPTION
        "Operating system product serial identification
        number.
        Example: '10497-OEM-0031416-71674'"
    ::= { win32OperatingSystemEntry 49 }

ososServicePackMajorVersion  OBJECT-TYPE
    SYNTAX     Integer32 (0..65535)
    MAX-ACCESS read-only
    STATUS     current
    DESCRIPTION
        "Major version number of the service pack installed
        on the computer system. If no service pack has been
        installed, the value is 0 (zero). 
        Windows NT 4.0, Windows Me/98/95:  This property is
        present but the value is NULL."
    ::= { win32OperatingSystemEntry 50 }

ososServicePackMinorVersion  OBJECT-TYPE
    SYNTAX     Integer32 (0..65535)
    MAX-ACCESS read-only
    STATUS     current
    DESCRIPTION
        "Minor version number of the service pack installed
        on the computer system. If no service pack has been
        installed, the value is 0 (zero). 
        Windows NT 4.0, Windows Me/98/95:  This property is
        present but the value is NULL."
    ::= { win32OperatingSystemEntry 51 }

ososSizeStoredInPagingFiles  OBJECT-TYPE
    SYNTAX     Gauge32
    MAX-ACCESS read-only
    STATUS     current
    DESCRIPTION
        "Total number of kilobytes that can be stored in
        the operating system's paging files 0 (zero)
        indicates that there are no paging files. Note that
        this number does not represent the actual physical
        size of the paging file on disk."
    ::= { win32OperatingSystemEntry 52 }

ososStatus  OBJECT-TYPE
    SYNTAX     INTEGER {
        ok(1),
        error(2),
        degraded(3),
        unknown(4),
        predFail(5),
        starting(6),
        stopping(7),
        service(8)
    }
    MAX-ACCESS read-only
    STATUS     current
    DESCRIPTION
        "Current status of the object. Various operational
        and non-operational statuses can be defined.
        Operational statuses include: 'OK', 'Degraded', and
        'Pred Fail' (an element, such as a SMART-enabled
        hard drive may function properly, but predicts a
        failure in the near future). Non-operational
        statuses include: 'Error', 'Starting', 'Stopping',
        and 'Service'. The 'Service' status applies to
        administrative work, such as mirror-resilvering of
        a disk, reload of a user permissions list, or other
        administrative work. Not all such work is online,
        but the managed element is neither 'OK' nor in one
        of the other states."
    ::= { win32OperatingSystemEntry 53 }

ososSuiteMask  OBJECT-TYPE
    SYNTAX     Gauge32
    MAX-ACCESS read-only
    STATUS     current
    DESCRIPTION
        "Bit flags that identify the product suites
        available on the system.
        Windows 2000 Server and earlier, Windows 2000 and
        earlier:   This property is not available.
        For example, to specify both Personal and Back
        Office you set SuiteMask to 4 | 512 or 516.
        The following table identifies the possible values.
        Value Meaning 
        1 Small Business 
        2 Enterprise 
        4 Back Office 
        8 Communications 
        16 Terminal 
        32 Small Business Restricted 
        64 Embedded NT 
        128 Data Center 
        256 Single User 
        512 Personal 
        1024 Blade "
    ::= { win32OperatingSystemEntry 54 }

ososSystemDevice  OBJECT-TYPE
    SYNTAX     WtcsDisplayString
    MAX-ACCESS read-only
    STATUS     current
    DESCRIPTION
        "Physical disk partition on which the operating
        system is installed."
    ::= { win32OperatingSystemEntry 55 }

ososSystemDirectory  OBJECT-TYPE
    SYNTAX     WtcsDisplayString
    MAX-ACCESS read-only
    STATUS     current
    DESCRIPTION
        "System directory of the operating system.
        Example: 'C:\WINDOWS\SYSTEM32'"
    ::= { win32OperatingSystemEntry 56 }

ososSystemDrive  OBJECT-TYPE
    SYNTAX     WtcsDisplayString
    MAX-ACCESS read-only
    STATUS     current
    DESCRIPTION
        "Letter of the disk drive on which the operating
        system resides. 
        Example: 'C:'
        Windows 2000 Server and earlier, Windows 2000 and
        earlier:   This property is not available."
    ::= { win32OperatingSystemEntry 57 }

ososTotalSwapSpaceSize  OBJECT-TYPE
    SYNTAX     Gauge32
    MAX-ACCESS read-only
    STATUS     current
    DESCRIPTION
        "Total swap space in kilobytes. This value may be
        NULL (unspecified) if swap space is not
        distinguished from page files. However, some
        operating systems distinguish these concepts. For
        example, in UNIX, whole processes can be swapped
        out when the free page list falls and remains below
        a specified amount."
    ::= { win32OperatingSystemEntry 58 }

ososTotalVirtualMemorySize  OBJECT-TYPE
    SYNTAX     Gauge32
    MAX-ACCESS read-only
    STATUS     current
    DESCRIPTION
        "Number of kilobytes of virtual memory. For
        example, this may be calculated by adding the
        amount of total RAM to the amount of paging space,
        that is, adding the amount of memory in or
        aggregated by the computer system to the property,
        SizeStoredInPagingFiles."
    ::= { win32OperatingSystemEntry 59 }

ososTotalVisibleMemorySize  OBJECT-TYPE
    SYNTAX     Gauge32
    MAX-ACCESS read-only
    STATUS     current
    DESCRIPTION
        "Total amount of physical memory available to the
        operating system. This value does not necessarily
        indicate the true amount of physical memory, but
        what is reported to the operating system as
        available to it."
    ::= { win32OperatingSystemEntry 60 }

ososVersion  OBJECT-TYPE
    SYNTAX     WtcsDisplayString
    MAX-ACCESS read-only
    STATUS     current
    DESCRIPTION
        "Version number of the operating system.
        Example: '4.0'"
    ::= { win32OperatingSystemEntry 61 }

ososWindowsDirectory  OBJECT-TYPE
    SYNTAX     WtcsDisplayString
    MAX-ACCESS read-only
    STATUS     current
    DESCRIPTION
        "Windows directory of the operating system.
        Example: 'C:\WINDOWS'"
    ::= { win32OperatingSystemEntry 62 }

win32OSRecoveryConfigTable OBJECT-TYPE
    SYNTAX     SEQUENCE OF Win32OSRecoveryConfigEntry
    MAX-ACCESS not-accessible
    STATUS     current
    DESCRIPTION
        "The Win32_OSRecoveryConfiguration WMI class
        represents the types of information that will be
        gathered from memory when the operating system
        fails. This includes boot failures and system
        crashes."
    ::= { wmiOperatingSystemSettings 6 }

win32OSRecoveryConfigEntry OBJECT-TYPE
    SYNTAX     Win32OSRecoveryConfigEntry
    MAX-ACCESS not-accessible
    STATUS     current
    DESCRIPTION
        "None"
    INDEX      { osrcIndex }
    ::= { win32OSRecoveryConfigTable 1 }

Win32OSRecoveryConfigEntry ::= SEQUENCE {
    osrcIndex Integer32,
    osrcAutoReboot  TruthValue,
    osrcCaption  WtcsDisplayString,
    osrcDebugFilePath  WtcsDisplayString,
    osrcDebugInfoType  INTEGER,
    osrcDescription  WtcsDisplayString,
    osrcExpandedDebugFilePath  WtcsDisplayString,
    osrcExpandedMiniDumpDirectory  WtcsDisplayString,
    osrcKernelDumpOnly  TruthValue,
    osrcMiniDumpDirectory  WtcsDisplayString,
    osrcName  WtcsDisplayString,
    osrcOverwriteExistingDebugFile  TruthValue,
    osrcSendAdminAlert  TruthValue,
    osrcSettingID  WtcsDisplayString,
    osrcWriteDebugInfo  TruthValue,
    osrcWriteToSystemLog  TruthValue
}

osrcIndex OBJECT-TYPE
    SYNTAX     Integer32 (1..2147483647)
    MAX-ACCESS read-only
    STATUS     current
    DESCRIPTION
        "The value of this object uniquely identifies the
        instance entry for this class."
    ::= { win32OSRecoveryConfigEntry 1 }

osrcAutoReboot  OBJECT-TYPE
    SYNTAX     TruthValue
    MAX-ACCESS read-only
    STATUS     current
    DESCRIPTION
        "System will automatically reboot during a recovery
        operation."
    ::= { win32OSRecoveryConfigEntry 2 }

osrcCaption  OBJECT-TYPE
    SYNTAX     WtcsDisplayString
    MAX-ACCESS read-only
    STATUS     current
    DESCRIPTION
        "Short description of the CIM_Setting object a
        one-line string."
    ::= { win32OSRecoveryConfigEntry 3 }

osrcDebugFilePath  OBJECT-TYPE
    SYNTAX     WtcsDisplayString
    MAX-ACCESS read-only
    STATUS     current
    DESCRIPTION
        "Full path to the debug file. A debug file is
        created with the memory state of the computer after
        a computer failure.
        Example: 'C:\WinNT\Memory.dmp'"
    ::= { win32OSRecoveryConfigEntry 4 }

osrcDebugInfoType  OBJECT-TYPE
    SYNTAX     INTEGER {
        none(0),
        completeMemoryDump(1),
        kernelMemoryDump(2),
        smallMemoryDump(3)
    }
    MAX-ACCESS read-only
    STATUS     current
    DESCRIPTION
        "Windows XP, Windows Server 2003:  Type of
        debugging information written to the log file."
    ::= { win32OSRecoveryConfigEntry 5 }

osrcDescription  OBJECT-TYPE
    SYNTAX     WtcsDisplayString
    MAX-ACCESS read-only
    STATUS     current
    DESCRIPTION
        "Description of the CIM_Setting object."
    ::= { win32OSRecoveryConfigEntry 6 }

osrcExpandedDebugFilePath  OBJECT-TYPE
    SYNTAX     WtcsDisplayString
    MAX-ACCESS read-only
    STATUS     current
    DESCRIPTION
        "Windows XP, Windows Server 2003:  Expanded version
        of the DebugFilePath property. 
        Example: 'C:\WinNT\Memory.dmp'"
    ::= { win32OSRecoveryConfigEntry 7 }

osrcExpandedMiniDumpDirectory  OBJECT-TYPE
    SYNTAX     WtcsDisplayString
    MAX-ACCESS read-only
    STATUS     current
    DESCRIPTION
        "Windows XP, Windows Server 2003:  Expanded version
        of the MiniDumpDirectory property. 
        Example: 'C:\WinNT\MiniDump'"
    ::= { win32OSRecoveryConfigEntry 8 }

osrcKernelDumpOnly  OBJECT-TYPE
    SYNTAX     TruthValue
    MAX-ACCESS read-only
    STATUS     current
    DESCRIPTION
        "Only kernel debug information will be written to
        the debug log file. If TRUE, then only the state of
        the kernel is written to a file in the event of a
        system failure. If FALSE, the system will try to
        log the state of the memory, and any devices that
        can provide information about the system when it
        failed."
    ::= { win32OSRecoveryConfigEntry 9 }

osrcMiniDumpDirectory  OBJECT-TYPE
    SYNTAX     WtcsDisplayString
    MAX-ACCESS read-only
    STATUS     current
    DESCRIPTION
        "Windows XP, Windows Server 2003:  Directory where
        small memory dump files will be recorded and
        accumulated.
        Example: '%systemRoot%\MiniDump'"
    ::= { win32OSRecoveryConfigEntry 10 }

osrcName  OBJECT-TYPE
    SYNTAX     WtcsDisplayString (SIZE (0..256))
    MAX-ACCESS read-only
    STATUS     current
    DESCRIPTION
        "Identifying name for this instance of the
        Win32_OSRecoveryConfiguration class."
    ::= { win32OSRecoveryConfigEntry 11 }

osrcOverwriteExistingDebugFile  OBJECT-TYPE
    SYNTAX     TruthValue
    MAX-ACCESS read-only
    STATUS     current
    DESCRIPTION
        "New log file will overwrite an existing one."
    ::= { win32OSRecoveryConfigEntry 12 }

osrcSendAdminAlert  OBJECT-TYPE
    SYNTAX     TruthValue
    MAX-ACCESS read-only
    STATUS     current
    DESCRIPTION
        "Alert message will be sent to the system
        administrator in the event of an operating system
        failure."
    ::= { win32OSRecoveryConfigEntry 13 }

osrcSettingID  OBJECT-TYPE
    SYNTAX     WtcsDisplayString
    MAX-ACCESS read-only
    STATUS     current
    DESCRIPTION
        "Identifier by which the CIM_Setting object is
        known."
    ::= { win32OSRecoveryConfigEntry 14 }

osrcWriteDebugInfo  OBJECT-TYPE
    SYNTAX     TruthValue
    MAX-ACCESS read-only
    STATUS     current
    DESCRIPTION
        "Debugging information is to be written to a log
        file."
    ::= { win32OSRecoveryConfigEntry 15 }

osrcWriteToSystemLog  OBJECT-TYPE
    SYNTAX     TruthValue
    MAX-ACCESS read-only
    STATUS     current
    DESCRIPTION
        "Events will be written to a system log."
    ::= { win32OSRecoveryConfigEntry 16 }

win32QuickFixEngineeringTable OBJECT-TYPE
    SYNTAX     SEQUENCE OF Win32QuickFixEngineeringEntry
    MAX-ACCESS not-accessible
    STATUS     current
    DESCRIPTION
        "The Win32_QuickFixEngineering WMI class represents
        system-wide Quick Fix Engineering (QFE) or updates
        that have been applied to the current operating
        system."
    ::= { wmiOperatingSystemSettings 7 }

win32QuickFixEngineeringEntry OBJECT-TYPE
    SYNTAX     Win32QuickFixEngineeringEntry
    MAX-ACCESS not-accessible
    STATUS     current
    DESCRIPTION
        "None"
    INDEX      { osqfeIndex }
    ::= { win32QuickFixEngineeringTable 1 }

Win32QuickFixEngineeringEntry ::= SEQUENCE {
    osqfeIndex Integer32,
    osqfeCaption  WtcsDisplayString,
    osqfeCSName  WtcsDisplayString,
    osqfeDescription  WtcsDisplayString,
    osqfeFixComments  WtcsDisplayString,
    osqfeHotFixID  WtcsDisplayString,
    osqfeInstallDate  DateAndTime,
    osqfeInstalledBy  WtcsDisplayString,
    osqfeInstalledOn  WtcsDisplayString,
    osqfeName  WtcsDisplayString,
    osqfeServicePackInEffect  WtcsDisplayString,
    osqfeStatus  INTEGER
}

osqfeIndex OBJECT-TYPE
    SYNTAX     Integer32 (1..2147483647)
    MAX-ACCESS read-only
    STATUS     current
    DESCRIPTION
        "The value of this object uniquely identifies the
        instance entry for this class."
    ::= { win32QuickFixEngineeringEntry 1 }

osqfeCaption  OBJECT-TYPE
    SYNTAX     WtcsDisplayString
    MAX-ACCESS read-only
    STATUS     current
    DESCRIPTION
        "Short textual description (one-line string) of the
        object."
    ::= { win32QuickFixEngineeringEntry 2 }

osqfeCSName  OBJECT-TYPE
    SYNTAX     WtcsDisplayString (SIZE (0..256))
    MAX-ACCESS read-only
    STATUS     current
    DESCRIPTION
        "Local name of the computer system. The value for
        this property comes from the CIM_ComputerSystem
        class."
    ::= { win32QuickFixEngineeringEntry 3 }

osqfeDescription  OBJECT-TYPE
    SYNTAX     WtcsDisplayString
    MAX-ACCESS read-only
    STATUS     current
    DESCRIPTION
        "Description of the object."
    ::= { win32QuickFixEngineeringEntry 4 }

osqfeFixComments  OBJECT-TYPE
    SYNTAX     WtcsDisplayString
    MAX-ACCESS read-only
    STATUS     current
    DESCRIPTION
        "Additional comments relating to the update. This
        property represents data found in the Windows
        registry key:
        HKEY_LOCAL_MACHINE
             SOFTWARE
                  Microsoft
                       Windows NT
                            CurrentVersion
                                 Hotfix"
    ::= { win32QuickFixEngineeringEntry 5 }

osqfeHotFixID  OBJECT-TYPE
    SYNTAX     WtcsDisplayString (SIZE (0..260))
    MAX-ACCESS read-only
    STATUS     current
    DESCRIPTION
        "Unique identifier associated with a particular
        QFE. This property represents data found in the
        Windows registry key:
        HKEY_LOCAL_MACHINE
             SOFTWARE
                  Microsoft
                       Windows NT
                            CurrentVersion
                                 Hotfix"
    ::= { win32QuickFixEngineeringEntry 6 }

osqfeInstallDate  OBJECT-TYPE
    SYNTAX     DateAndTime
    MAX-ACCESS read-only
    STATUS     current
    DESCRIPTION
        "Object was installed. This property does not need
        a value to indicate that the object is installed."
    ::= { win32QuickFixEngineeringEntry 7 }

osqfeInstalledBy  OBJECT-TYPE
    SYNTAX     WtcsDisplayString
    MAX-ACCESS read-only
    STATUS     current
    DESCRIPTION
        "Person who installed the update. If this value is
        unknown, the property will be empty. This property
        represents data found in the Windows registry key:
        HKEY_LOCAL_MACHINE
             SOFTWARE
                  Microsoft
                       Windows NT
                            CurrentVersion
                                 Hotfix"
    ::= { win32QuickFixEngineeringEntry 8 }

osqfeInstalledOn  OBJECT-TYPE
    SYNTAX     WtcsDisplayString
    MAX-ACCESS read-only
    STATUS     current
    DESCRIPTION
        "Update was installed. If this value is unknown,
        the property will be empty. This property
        represents data found in the Windows registry key:
        HKEY_LOCAL_MACHINE
             SOFTWARE
                  Microsoft
                       Windows NT
                            CurrentVersion
                                 Hotfix"
    ::= { win32QuickFixEngineeringEntry 9 }

osqfeName  OBJECT-TYPE
    SYNTAX     WtcsDisplayString
    MAX-ACCESS read-only
    STATUS     current
    DESCRIPTION
        "Label by which the object is known. When
        subclassed, the property can be overridden to be a
        key property."
    ::= { win32QuickFixEngineeringEntry 10 }

osqfeServicePackInEffect  OBJECT-TYPE
    SYNTAX     WtcsDisplayString (SIZE (0..260))
    MAX-ACCESS read-only
    STATUS     current
    DESCRIPTION
        "Service pack in effect when the update was
        applied. If no service pack has been applied, the
        property takes on the value SP0. If it cannot be
        determined what service pack was in effect, this
        property will be NULL. This property represents
        data found in the Windows registry key:
        HKEY_LOCAL_MACHINE
             SOFTWARE
                  Microsoft
                       Windows NT
                            CurrentVersion
                                 Hotfix"
    ::= { win32QuickFixEngineeringEntry 11 }

osqfeStatus  OBJECT-TYPE
    SYNTAX     INTEGER {
        ok(1),
        error(2),
        degraded(3),
        unknown(4),
        predFail(5),
        starting(6),
        stopping(7),
        service(8)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is on-line,
        yet the managed element is neither 'OK' nor in one
        of the other states."
    ::= { win32QuickFixEngineeringEntry 12 }

win32StartupCommandTable OBJECT-TYPE
    SYNTAX     SEQUENCE OF Win32StartupCommandEntry
    MAX-ACCESS not-accessible
    STATUS     current
    DESCRIPTION
        "The Win32_StartupCommand WMI class represents a
        command that runs automatically when a user logs
        onto the computer system."
    ::= { wmiOperatingSystemSettings 8 }

win32StartupCommandEntry OBJECT-TYPE
    SYNTAX     Win32StartupCommandEntry
    MAX-ACCESS not-accessible
    STATUS     current
    DESCRIPTION
        "None"
    INDEX      { osscIndex }
    ::= { win32StartupCommandTable 1 }

Win32StartupCommandEntry ::= SEQUENCE {
    osscIndex Integer32,
    osscCaption  WtcsDisplayString,
    osscCommand  WtcsDisplayString,
    osscDescription  WtcsDisplayString,
    osscLocation  WtcsDisplayString,
    osscName  WtcsDisplayString,
    osscSettingID  WtcsDisplayString,
    osscUser  WtcsDisplayString
}

osscIndex OBJECT-TYPE
    SYNTAX     Integer32 (1..2147483647)
    MAX-ACCESS read-only
    STATUS     current
    DESCRIPTION
        "The value of this object uniquely identifies the
        instance entry for this class."
    ::= { win32StartupCommandEntry 1 }

osscCaption  OBJECT-TYPE
    SYNTAX     WtcsDisplayString
    MAX-ACCESS read-only
    STATUS     current
    DESCRIPTION
        "Short description (one-line string) of the
        CIM_Setting object."
    ::= { win32StartupCommandEntry 2 }

osscCommand  OBJECT-TYPE
    SYNTAX     WtcsDisplayString
    MAX-ACCESS read-only
    STATUS     current
    DESCRIPTION
        "Command run by the startup command.
        Example: 'c:\winnt\notepad.exe myfile.txt'"
    ::= { win32StartupCommandEntry 3 }

osscDescription  OBJECT-TYPE
    SYNTAX     WtcsDisplayString
    MAX-ACCESS read-only
    STATUS     current
    DESCRIPTION
        "Description of the CIM_Setting object."
    ::= { win32StartupCommandEntry 4 }

osscLocation  OBJECT-TYPE
    SYNTAX     WtcsDisplayString
    MAX-ACCESS read-only
    STATUS     current
    DESCRIPTION
        "Path where the startup command resides on the disk
        file system."
    ::= { win32StartupCommandEntry 5 }

osscName  OBJECT-TYPE
    SYNTAX     WtcsDisplayString
    MAX-ACCESS read-only
    STATUS     current
    DESCRIPTION
        "File name of the startup command.
        Example: 'FindFast'"
    ::= { win32StartupCommandEntry 6 }

osscSettingID  OBJECT-TYPE
    SYNTAX     WtcsDisplayString
    MAX-ACCESS read-only
    STATUS     current
    DESCRIPTION
        "Identifier by which the CIM_Setting object is
        known."
    ::= { win32StartupCommandEntry 7 }

osscUser  OBJECT-TYPE
    SYNTAX     WtcsDisplayString
    MAX-ACCESS read-only
    STATUS     current
    DESCRIPTION
        "User name for whom this startup command will run.
        Example: 'mydomain\myname'"
    ::= { win32StartupCommandEntry 8 }

win32Shutdown OBJECT-TYPE
    SYNTAX     INTEGER {
        logOff(0),
        shutdown(1),
        reboot(2),
        forcedLogOff(4),
        forceShutdown(5),
        forcedReboot(6),
        powerOff(8),
        forcedPowerOff(12)
    }
    MAX-ACCESS read-write
    STATUS     current
    DESCRIPTION
        "This OID can only be written to and cannot be
        read! The Win32Shutdown WMI class method provides
        the full set of shutdown options supported by Win32
        operating systems. Using Force in conjunction with
        Shutdown or Reboot on a remote computer immediately
        shuts down everything (including WMI, COM, and so
        on), or reboots the remote computer. This results
        in an indeterminate return value."
    ::= { wmiOperatingSystemSettings 9 }

win32WinSATTable OBJECT-TYPE
    SYNTAX     SEQUENCE OF Win32WinSAT
    MAX-ACCESS not-accessible
    STATUS     current
    DESCRIPTION
        "Defines summary assessment information for the
        most recent formal assessment."
    ::= { wmiOperatingSystemSettings 10 }

win32WinSATEntry OBJECT-TYPE
    SYNTAX     Win32WinSAT
    MAX-ACCESS not-accessible
    STATUS     current
    DESCRIPTION
        "None"
    INDEX      { ossatIndex }
    ::= { win32WinSATTable 1 }

Win32WinSAT ::= SEQUENCE {
    ossatIndex Integer32,
    ossatCPUScore Integer32,
    ossatD3DScore Integer32,
    ossatDiskScore Integer32,
    ossatGraphicsScore Integer32,
    ossatMemoryScore Integer32,
    ossatTimeTaken WtcsDisplayString,
    ossatAssessmentState INTEGER,
    ossatSPRLevel Integer32
}

ossatIndex OBJECT-TYPE
    SYNTAX     Integer32 (1..2147483647)
    MAX-ACCESS read-only
    STATUS     current
    DESCRIPTION
        "The value of this object uniquely identifies the
        instance entry for this class."
    ::= { win32WinSATEntry 1 }

ossatCPUScore OBJECT-TYPE
    SYNTAX     Integer32
    MAX-ACCESS read-only
    STATUS     current
    DESCRIPTION
        "A score for the processors on the computer."
    ::= { win32WinSATEntry 2 }

ossatD3DScore OBJECT-TYPE
    SYNTAX     Integer32
    MAX-ACCESS read-only
    STATUS     current
    DESCRIPTION
        "A score for the three-dimensional graphics
        (gaming) capabilities of the computer."
    ::= { win32WinSATEntry 3 }

ossatDiskScore OBJECT-TYPE
    SYNTAX     Integer32
    MAX-ACCESS read-only
    STATUS     current
    DESCRIPTION
        "A score for the sequential read throughput on the
        primary hard disk on the computer."
    ::= { win32WinSATEntry 4 }

ossatGraphicsScore OBJECT-TYPE
    SYNTAX     Integer32
    MAX-ACCESS read-only
    STATUS     current
    DESCRIPTION
        "A score for the graphics capabilities of the
        computer."
    ::= { win32WinSATEntry 5 }

ossatMemoryScore OBJECT-TYPE
    SYNTAX     Integer32
    MAX-ACCESS read-only
    STATUS     current
    DESCRIPTION
        "A score for the memory throughput and capacity of
        the computer."
    ::= { win32WinSATEntry 6 }

ossatTimeTaken OBJECT-TYPE
    SYNTAX     WtcsDisplayString
    MAX-ACCESS read-only
    STATUS     current
    DESCRIPTION
        "This property must be set to
        'MostRecentAssessment' in the WHERE clause of your
        WQL query."
    ::= { win32WinSATEntry 7 }

ossatAssessmentState OBJECT-TYPE
    SYNTAX     INTEGER {
        stateUknown(0),
        valid(1),
        incoherentWithHardware(2),
        noAssessmentAvailable(3),
        invalid(4)
    }
    MAX-ACCESS read-only
    STATUS     current
    DESCRIPTION
        "State of the assessment. For a description of the
        possible values, see the WINSAT_ASSESSMENT_STATE
        enumeration."
    ::= { win32WinSATEntry 8 }

ossatSPRLevel OBJECT-TYPE
    SYNTAX     Integer32
    MAX-ACCESS read-only
    STATUS     current
    DESCRIPTION
        "Base score for the computer. For details on the
        score value, see
        http://msdn2.microsoft.com/en-us/library/aa969193.a
        spx"
    ::= { win32WinSATEntry 9 }

wmiProcesses OBJECT-IDENTITY
    STATUS     current
    DESCRIPTION
        "The Processes subcategory groups classes that
        represent system processes and threads."
    ::= { wmiOperatingSystem 9 }

win32ProcessTable OBJECT-TYPE
    SYNTAX     SEQUENCE OF Win32ProcessEntry
    MAX-ACCESS not-accessible
    STATUS     current
    DESCRIPTION
        "The Win32_Process WMI class represents a sequence
        of events on a Windows operating system. A
        descendent or member of this class is a sequence
        that consists of an interaction of one or more
        processors or interpreters, some executable code,
        and a set of inputs, for example, a client
        application running on a Windows system."
    ::= { wmiProcesses 1 }

win32ProcessEntry OBJECT-TYPE
    SYNTAX     Win32ProcessEntry
    MAX-ACCESS not-accessible
    STATUS     current
    DESCRIPTION
        "None"
    INDEX      { ospsIndex }
    ::= { win32ProcessTable 1 }

Win32ProcessEntry ::= SEQUENCE {
    ospsIndex Integer32,
    ospsCaption  WtcsDisplayString,
    ospsCommandLine  WtcsDisplayString,
    ospsCreationClassName  WtcsDisplayString,
    ospsCreationDate  DateAndTime,
    ospsCSCreationClassName  WtcsDisplayString,
    ospsCSName  WtcsDisplayString,
    ospsDescription  WtcsDisplayString,
    ospsExecutablePath  WtcsDisplayString,
    ospsExecutionState  Integer32,
    ospsHandle  WtcsDisplayString,
    ospsHandleCount  Gauge32,
    ospsInstallDate  DateAndTime,
    ospsKernelModeTime  Counter64,
    ospsMaximumWorkingSetSize  Gauge32,
    ospsMinimumWorkingSetSize  Gauge32,
    ospsName  WtcsDisplayString,
    ospsOSCreationClassName  WtcsDisplayString,
    ospsOSName  WtcsDisplayString,
    ospsOtherOperationCount  Counter64,
    ospsOtherTransferCount  Counter64,
    ospsPageFaults  Gauge32,
    ospsPageFileUsage  Gauge32,
    ospsParentProcessId  Gauge32,
    ospsPeakPageFileUsage  Gauge32,
    ospsPeakVirtualSize  Gauge32,
    ospsPeakWorkingSetSize  Gauge32,
    ospsPriority  Gauge32,
    ospsPrivatePageCount  Gauge32,
    ospsProcessId  Gauge32,
    ospsQuotaNonPagedPoolUsage  Gauge32,
    ospsQuotaPagedPoolUsage  Gauge32,
    ospsQuotaPeakNonPagedPoolUsage  Gauge32,
    ospsQuotaPeakPagedPoolUsage  Gauge32,
    ospsReadOperationCount  Counter64,
    ospsReadTransferCount  Counter64,
    ospsSessionId  Gauge32,
    ospsStatus  WtcsDisplayString,
    ospsTerminationDate  DateAndTime,
    ospsThreadCount  Gauge32,
    ospsUserModeTime  Counter64,
    ospsVirtualSize  Gauge32,
    ospsWindowsVersion  WtcsDisplayString,
    ospsWorkingSetSize  Gauge32,
    ospsWriteOperationCount  Counter64,
    ospsWriteTransferCount  Counter64
}

ospsIndex OBJECT-TYPE
    SYNTAX     Integer32 (1..2147483647)
    MAX-ACCESS read-only
    STATUS     current
    DESCRIPTION
        "The value of this object uniquely identifies the
        instance entry for this class."
    ::= { win32ProcessEntry 1 }

ospsCaption  OBJECT-TYPE
    SYNTAX     WtcsDisplayString
    MAX-ACCESS read-only
    STATUS     current
    DESCRIPTION
        "Short description of an object a one-line string."
    ::= { win32ProcessEntry 2 }

ospsCommandLine  OBJECT-TYPE
    SYNTAX     WtcsDisplayString
    MAX-ACCESS read-only
    STATUS     current
    DESCRIPTION
        "Command line used to start a specific process, if
        applicable. This property is new for Windows XP."
    ::= { win32ProcessEntry 3 }

ospsCreationClassName  OBJECT-TYPE
    SYNTAX     WtcsDisplayString (SIZE (0..256))
    MAX-ACCESS read-only
    STATUS     current
    DESCRIPTION
        "Name of the first concrete class in the
        inheritance chain that is used to create an
        instance. You can use this property with other key
        properties of the class to identify uniquely all
        instances of the class and its subclasses. This
        property is inherited from CIM_System"
    ::= { win32ProcessEntry 4 }

ospsCreationDate  OBJECT-TYPE
    SYNTAX     DateAndTime
    MAX-ACCESS read-only
    STATUS     current
    DESCRIPTION
        "Date the process begins executing."
    ::= { win32ProcessEntry 5 }

ospsCSCreationClassName  OBJECT-TYPE
    SYNTAX     WtcsDisplayString
    MAX-ACCESS read-only
    STATUS     current
    DESCRIPTION
        "Creation class name of the scoping computer
        system."
    ::= { win32ProcessEntry 6 }

ospsCSName  OBJECT-TYPE
    SYNTAX     WtcsDisplayString
    MAX-ACCESS read-only
    STATUS     current
    DESCRIPTION
        "Name of the scoping computer system."
    ::= { win32ProcessEntry 7 }

ospsDescription  OBJECT-TYPE
    SYNTAX     WtcsDisplayString
    MAX-ACCESS read-only
    STATUS     current
    DESCRIPTION
        "Description of an object."
    ::= { win32ProcessEntry 8 }

ospsExecutablePath  OBJECT-TYPE
    SYNTAX     WtcsDisplayString
    MAX-ACCESS read-only
    STATUS     current
    DESCRIPTION
        "Path to the executable file of the process.
        Example: C:\WINDOWS\EXPLORER.EXE"
    ::= { win32ProcessEntry 9 }

ospsExecutionState  OBJECT-TYPE
    SYNTAX     Integer32 (0..65535)
    MAX-ACCESS read-only
    STATUS     current
    DESCRIPTION
        "This property is not implemented and does not get
        populated for any instance of this class. This
        property is always NULL."
    ::= { win32ProcessEntry 10 }

ospsHandle  OBJECT-TYPE
    SYNTAX     WtcsDisplayString
    MAX-ACCESS read-only
    STATUS     current
    DESCRIPTION
        "Process identifier."
    ::= { win32ProcessEntry 11 }

ospsHandleCount  OBJECT-TYPE
    SYNTAX     Gauge32
    MAX-ACCESS read-only
    STATUS     current
    DESCRIPTION
        "Total number of open handles owned by the process.
        HandleCount is the sum of the handles currently
        open by each thread in this process. A handle is
        used to examine or modify the system resources.
        Each handle has an entry in a table that is
        maintained internally. Entries contain the
        addresses of the resources and data to identify the
        resource type."
    ::= { win32ProcessEntry 12 }

ospsInstallDate  OBJECT-TYPE
    SYNTAX     DateAndTime
    MAX-ACCESS read-only
    STATUS     current
    DESCRIPTION
        "Date an object is installed. The object may be
        installed without a value being written to this
        property."
    ::= { win32ProcessEntry 13 }

ospsKernelModeTime  OBJECT-TYPE
    SYNTAX     Counter64
    UNITS "100ns"
    MAX-ACCESS read-only
    STATUS     current
    DESCRIPTION
        "Time in kernel mode, in 100 nanosecond units. If
        this information is not available, use a value of 0
        (zero)."
    ::= { win32ProcessEntry 14 }

ospsMaximumWorkingSetSize  OBJECT-TYPE
    SYNTAX     Gauge32
    UNITS "Kilobytes"
    MAX-ACCESS read-only
    STATUS     current
    DESCRIPTION
        "Maximum working set size of the process. The
        working set of a process is the set of memory pages
        visible to the process in physical RAM. These pages
        are resident, and available for an application to
        use without triggering a page fault.
        Example: 1413120"
    ::= { win32ProcessEntry 15 }

ospsMinimumWorkingSetSize  OBJECT-TYPE
    SYNTAX     Gauge32
    UNITS "Kilobytes"
    MAX-ACCESS read-only
    STATUS     current
    DESCRIPTION
        "Minimum working set size of the process. The
        working set of a process is the set of memory pages
        visible to the process in physical RAM. These pages
        are resident and available for an application to
        use without triggering a page fault.
        Example: 20480"
    ::= { win32ProcessEntry 16 }

ospsName  OBJECT-TYPE
    SYNTAX     WtcsDisplayString
    MAX-ACCESS read-only
    STATUS     current
    DESCRIPTION
        "Label for an object. When inherited by a subclass,
        the property can be overridden to be a key
        property."
    ::= { win32ProcessEntry 17 }

ospsOSCreationClassName  OBJECT-TYPE
    SYNTAX     WtcsDisplayString
    MAX-ACCESS read-only
    STATUS     current
    DESCRIPTION
        "Creation class name of the scoping operating
        system."
    ::= { win32ProcessEntry 18 }

ospsOSName  OBJECT-TYPE
    SYNTAX     WtcsDisplayString
    MAX-ACCESS read-only
    STATUS     current
    DESCRIPTION
        "Name of the scoping operating system."
    ::= { win32ProcessEntry 19 }

ospsOtherOperationCount  OBJECT-TYPE
    SYNTAX     Counter64
    MAX-ACCESS read-only
    STATUS     current
    DESCRIPTION
        "Number of I/O operations performed that are not
        read or write operations."
    ::= { win32ProcessEntry 20 }

ospsOtherTransferCount  OBJECT-TYPE
    SYNTAX     Counter64
    UNITS "Bytes"
    MAX-ACCESS read-only
    STATUS     current
    DESCRIPTION
        "Amount of data transferred during operations that
        are not read or write operations."
    ::= { win32ProcessEntry 21 }

ospsPageFaults  OBJECT-TYPE
    SYNTAX     Gauge32
    MAX-ACCESS read-only
    STATUS     current
    DESCRIPTION
        "Number of page faults that a process generates.
        Example: 10"
    ::= { win32ProcessEntry 22 }

ospsPageFileUsage  OBJECT-TYPE
    SYNTAX     Gauge32
    UNITS "Kilobytes"
    MAX-ACCESS read-only
    STATUS     current
    DESCRIPTION
        "Amount of page file space that a process is using
        currently. 
        Example: 102435"
    ::= { win32ProcessEntry 23 }

ospsParentProcessId  OBJECT-TYPE
    SYNTAX     Gauge32
    MAX-ACCESS read-only
    STATUS     current
    DESCRIPTION
        "Unique identifier of the process that creates a
        process. Process identifier numbers are reused, so
        they only identify a process for the lifetime of
        that process. It is possible that the process
        identified by ParentProcessId is terminated, so
        ParentProcessId may not refer to a running process.
        It is also possible that ParentProcessId
        incorrectly refers to a process that reuses a
        process identifier. You can use the CreationDate
        property to determine whether the specified parent
        was created after the process represented by this
        Win32_Process instance was created."
    ::= { win32ProcessEntry 24 }

ospsPeakPageFileUsage  OBJECT-TYPE
    SYNTAX     Gauge32
    UNITS "Kilobytes"
    MAX-ACCESS read-only
    STATUS     current
    DESCRIPTION
        "Maximum amount of page file space used during the
        life of a process.
        Example: 102367"
    ::= { win32ProcessEntry 25 }

ospsPeakVirtualSize  OBJECT-TYPE
    SYNTAX     Gauge32
    UNITS "Bytes"
    MAX-ACCESS read-only
    STATUS     current
    DESCRIPTION
        "Maximum virtual address space a process uses at
        any one time. Using virtual address space does not
        necessarily imply corresponding use of either disk
        or main memory pages. However, virtual space is
        finite, and by using too much the process might not
        be able to load libraries."
    ::= { win32ProcessEntry 26 }

ospsPeakWorkingSetSize  OBJECT-TYPE
    SYNTAX     Gauge32
    UNITS "Kilobytes"
    MAX-ACCESS read-only
    STATUS     current
    DESCRIPTION
        "Peak working set size of a process.
        Example: 1413120"
    ::= { win32ProcessEntry 27 }

ospsPriority  OBJECT-TYPE
    SYNTAX     Gauge32
    MAX-ACCESS read-only
    STATUS     current
    DESCRIPTION
        "Scheduling priority of a process within an
        operating system. The higher the value, the higher
        priority a process receives. Priority values can
        range from 0 (zero), which is the lowest priority
        to 31, which is highest priority.
        Example: 7"
    ::= { win32ProcessEntry 28 }

ospsPrivatePageCount  OBJECT-TYPE
    SYNTAX     Gauge32
    MAX-ACCESS read-only
    STATUS     current
    DESCRIPTION
        "Current number of pages allocated that are
        accessible only to the process represented by this
        Win32_Process instance."
    ::= { win32ProcessEntry 29 }

ospsProcessId  OBJECT-TYPE
    SYNTAX     Gauge32
    MAX-ACCESS read-only
    STATUS     current
    DESCRIPTION
        "Global process identifier that you can use to
        identify a process. The value is valid from the
        time a process is created until it is terminated."
    ::= { win32ProcessEntry 30 }

ospsQuotaNonPagedPoolUsage  OBJECT-TYPE
    SYNTAX     Gauge32
    MAX-ACCESS read-only
    STATUS     current
    DESCRIPTION
        "Quota amount of non-paged pool usage for a
        process.
        Example: 15"
    ::= { win32ProcessEntry 31 }

ospsQuotaPagedPoolUsage  OBJECT-TYPE
    SYNTAX     Gauge32
    MAX-ACCESS read-only
    STATUS     current
    DESCRIPTION
        "Quota amount of paged pool usage for a process.
        Example: 22"
    ::= { win32ProcessEntry 32 }

ospsQuotaPeakNonPagedPoolUsage  OBJECT-TYPE
    SYNTAX     Gauge32
    MAX-ACCESS read-only
    STATUS     current
    DESCRIPTION
        "Peak quota amount of non-paged pool usage for a
        process.
        Example: 31"
    ::= { win32ProcessEntry 33 }

ospsQuotaPeakPagedPoolUsage  OBJECT-TYPE
    SYNTAX     Gauge32
    MAX-ACCESS read-only
    STATUS     current
    DESCRIPTION
        "Peak quota amount of paged pool usage for a
        process.
        Example: 31"
    ::= { win32ProcessEntry 34 }

ospsReadOperationCount  OBJECT-TYPE
    SYNTAX     Counter64
    MAX-ACCESS read-only
    STATUS     current
    DESCRIPTION
        "Number of read operations performed."
    ::= { win32ProcessEntry 35 }

ospsReadTransferCount  OBJECT-TYPE
    SYNTAX     Counter64
    UNITS "Bytes"
    MAX-ACCESS read-only
    STATUS     current
    DESCRIPTION
        "Amount of data read."
    ::= { win32ProcessEntry 36 }

ospsSessionId  OBJECT-TYPE
    SYNTAX     Gauge32
    MAX-ACCESS read-only
    STATUS     current
    DESCRIPTION
        "Unique identifier that an operating system
        generates when a session is created. A session
        spans a period of time from log on until log off
        from a specific system."
    ::= { win32ProcessEntry 37 }

ospsStatus  OBJECT-TYPE
    SYNTAX     WtcsDisplayString
    MAX-ACCESS read-only
    STATUS     current
    DESCRIPTION
        "This property is not implemented and does not get
        populated for any instance of this class. It is
        always NULL. "
    ::= { win32ProcessEntry 38 }

ospsTerminationDate  OBJECT-TYPE
    SYNTAX     DateAndTime
    MAX-ACCESS read-only
    STATUS     current
    DESCRIPTION
        "Process was stopped or terminated. To get the
        termination time, a handle to the process must be
        held open. Otherwise, this property returns NULL."
    ::= { win32ProcessEntry 39 }

ospsThreadCount  OBJECT-TYPE
    SYNTAX     Gauge32
    MAX-ACCESS read-only
    STATUS     current
    DESCRIPTION
        "Number of active threads in a process. An
        instruction is the basic unit of execution in a
        processor, and a thread is the object that executes
        an instruction. Each running process has at least
        one thread. This property is for computers running
        Windows NT only."
    ::= { win32ProcessEntry 40 }

ospsUserModeTime  OBJECT-TYPE
    SYNTAX     Counter64
    UNITS "100ns"
    MAX-ACCESS read-only
    STATUS     current
    DESCRIPTION
        "Time in user mode, in 100 nanosecond units. If
        this information is not available, use a value of 0
        (zero)."
    ::= { win32ProcessEntry 41 }

ospsVirtualSize  OBJECT-TYPE
    SYNTAX     Gauge32
    UNITS "Bytes"
    MAX-ACCESS read-only
    STATUS     current
    DESCRIPTION
        "Current size of the virtual address space that a
        process is using. Using virtual address space does
        not necessarily imply corresponding use of either
        disk or main memory pages. Virtual space is finite,
        and by using too much, the process might not be
        able to load libraries."
    ::= { win32ProcessEntry 42 }

ospsWindowsVersion  OBJECT-TYPE
    SYNTAX     WtcsDisplayString
    MAX-ACCESS read-only
    STATUS     current
    DESCRIPTION
        "Version of Windows in which the process is
        running.
        Example: 4.0"
    ::= { win32ProcessEntry 43 }

ospsWorkingSetSize  OBJECT-TYPE
    SYNTAX     Gauge32
    MAX-ACCESS read-only
    STATUS     current
    DESCRIPTION
        "Amount of memory in bytes that a process needs to
        execute efficiently for an operating system that
        uses page-based memory management. If the system
        does not have enough memory (less than the working
        set size), thrashing occurs. If the size of the
        working set is not known, use NULL or 0 (zero). If
        working set data is provided, you can monitor the
        information to understand the changing memory
        requirements of a process."
    ::= { win32ProcessEntry 44 }

ospsWriteOperationCount  OBJECT-TYPE
    SYNTAX     Counter64
    MAX-ACCESS read-only
    STATUS     current
    DESCRIPTION
        "Number of write operations performed."
    ::= { win32ProcessEntry 45 }

ospsWriteTransferCount  OBJECT-TYPE
    SYNTAX     Counter64
    UNITS "Bytes"
    MAX-ACCESS read-only
    STATUS     current
    DESCRIPTION
        "Amount of data written."
    ::= { win32ProcessEntry 46 }

win32ThreadTable OBJECT-TYPE
    SYNTAX     SEQUENCE OF Win32ThreadEntry
    MAX-ACCESS not-accessible
    STATUS     current
    DESCRIPTION
        "The Win32_Thread WMI class represents a thread of
        execution. While a process must have one thread of
        execution, the process can create other threads to
        execute tasks in parallel. Threads share the
        process environment, thus multiple threads under
        the same process use less memory than the same
        number of processes."
    ::= { wmiProcesses 2 }

win32ThreadEntry OBJECT-TYPE
    SYNTAX     Win32ThreadEntry
    MAX-ACCESS not-accessible
    STATUS     current
    DESCRIPTION
        "None"
    INDEX      { ostdIndex }
    ::= { win32ThreadTable 1 }

Win32ThreadEntry ::= SEQUENCE {
    ostdIndex Integer32,
    ostdCaption  WtcsDisplayString,
    ostdCreationClassName  WtcsDisplayString,
    ostdCSCreationClassName  WtcsDisplayString,
    ostdCSName  WtcsDisplayString,
    ostdDescription  WtcsDisplayString,
    ostdElapsedTime  Counter64,
    ostdExecutionState  INTEGER,
    ostdHandle  WtcsDisplayString,
    ostdInstallDate  DateAndTime,
    ostdKernelModeTime  Counter64,
    ostdName  WtcsDisplayString,
    ostdOSCreationClassName  WtcsDisplayString,
    ostdOSName  WtcsDisplayString,
    ostdPriority  Gauge32,
    ostdPriorityBase  Gauge32,
    ostdProcessCreationClassName  WtcsDisplayString,
    ostdProcessHandle  WtcsDisplayString,
    ostdStartAddress  Gauge32,
    ostdStatus  INTEGER,
    ostdThreadState  INTEGER,
    ostdThreadWaitReason  INTEGER,
    ostdUserModeTime  Counter64
}

ostdIndex OBJECT-TYPE
    SYNTAX     Integer32 (1..2147483647)
    MAX-ACCESS read-only
    STATUS     current
    DESCRIPTION
        "The value of this object uniquely identifies the
        instance entry for this class."
    ::= { win32ThreadEntry 1 }

ostdCaption  OBJECT-TYPE
    SYNTAX     WtcsDisplayString (SIZE (0..64))
    MAX-ACCESS read-only
    STATUS     current
    DESCRIPTION
        "Short description (one-line string) of the
        object."
    ::= { win32ThreadEntry 2 }

ostdCreationClassName  OBJECT-TYPE
    SYNTAX     WtcsDisplayString (SIZE (0..256))
    MAX-ACCESS read-only
    STATUS     current
    DESCRIPTION
        "Name of the first concrete class to appear in the
        inheritance chain used in the creation of an
        instance. When used with the other key properties
        of the class, the property allows all instances of
        this class and its subclasses to be uniquely
        identified."
    ::= { win32ThreadEntry 3 }

ostdCSCreationClassName  OBJECT-TYPE
    SYNTAX     WtcsDisplayString (SIZE (0..256))
    MAX-ACCESS read-only
    STATUS     current
    DESCRIPTION
        "Creation class name of the scoping computer
        system."
    ::= { win32ThreadEntry 4 }

ostdCSName  OBJECT-TYPE
    SYNTAX     WtcsDisplayString (SIZE (0..256))
    MAX-ACCESS read-only
    STATUS     current
    DESCRIPTION
        "Name of the scoping computer system."
    ::= { win32ThreadEntry 5 }

ostdDescription  OBJECT-TYPE
    SYNTAX     WtcsDisplayString
    MAX-ACCESS read-only
    STATUS     current
    DESCRIPTION
        "Description of the object."
    ::= { win32ThreadEntry 6 }

ostdElapsedTime  OBJECT-TYPE
    SYNTAX     Counter64
    UNITS "Milliseconds"
    MAX-ACCESS read-only
    STATUS     current
    DESCRIPTION
        "Total execution time given to this thread since
        its creation."
    ::= { win32ThreadEntry 7 }

ostdExecutionState  OBJECT-TYPE
    SYNTAX     INTEGER {
        unknown(0),
        other(1),
        ready(2),
        running(3),
        blocked(4),
        suspendedBlocked(5),
        suspendedReady(6)
    }
    MAX-ACCESS read-only
    STATUS     current
    DESCRIPTION
        "Current operating condition of the thread."
    ::= { win32ThreadEntry 8 }

ostdHandle  OBJECT-TYPE
    SYNTAX     WtcsDisplayString (SIZE (0..256))
    MAX-ACCESS read-only
    STATUS     current
    DESCRIPTION
        "Handle to a thread. The handle has full access
        rights by default. With the correct security
        access, the handle can be used in any function that
        accepts a thread handle. Depending on the
        inheritance flag specified when it is created, this
        handle can be inherited by child processes."
    ::= { win32ThreadEntry 9 }

ostdInstallDate  OBJECT-TYPE
    SYNTAX     DateAndTime
    MAX-ACCESS read-only
    STATUS     current
    DESCRIPTION
        "Object was installed. This property does not need
        a value to indicate that the object is installed."
    ::= { win32ThreadEntry 10 }

ostdKernelModeTime  OBJECT-TYPE
    SYNTAX     Counter64
    UNITS "100ns"
    MAX-ACCESS read-only
    STATUS     current
    DESCRIPTION
        "Time in kernel mode, in 100 nanoseconds. If this
        information is not available, a value of 0 should
        be used."
    ::= { win32ThreadEntry 11 }

ostdName  OBJECT-TYPE
    SYNTAX     WtcsDisplayString
    MAX-ACCESS read-only
    STATUS     current
    DESCRIPTION
        "Label by which the object is known. When
        subclassed, the property can be overridden to be a
        key property."
    ::= { win32ThreadEntry 12 }

ostdOSCreationClassName  OBJECT-TYPE
    SYNTAX     WtcsDisplayString
    MAX-ACCESS read-only
    STATUS     current
    DESCRIPTION
        "Creation class name of the scoping operating
        system."
    ::= { win32ThreadEntry 13 }

ostdOSName  OBJECT-TYPE
    SYNTAX     WtcsDisplayString (SIZE (0..256))
    MAX-ACCESS read-only
    STATUS     current
    DESCRIPTION
        "Name of the scoping operating system."
    ::= { win32ThreadEntry 14 }

ostdPriority  OBJECT-TYPE
    SYNTAX     Gauge32
    MAX-ACCESS read-only
    STATUS     current
    DESCRIPTION
        "Dynamic priority of the thread. Each thread has a
        dynamic priority that the scheduler uses to
        determine which thread to execute. Initially, a
        thread's dynamic priority is the same as its base
        priority. The system can raise and lower the
        dynamic priority, to ensure that it is responsive
        (guaranteeing that no threads are starved for
        processor time). The system does not boost the
        priority of threads with a base priority level
        between 16 and 31. Only threads with a base
        priority between 0 and 15 receive dynamic priority
        boosts. Higher numbers indicate higher priorities."
    ::= { win32ThreadEntry 15 }

ostdPriorityBase  OBJECT-TYPE
    SYNTAX     Gauge32
    MAX-ACCESS read-only
    STATUS     current
    DESCRIPTION
        "Current base priority of a thread. The operating
        system may raise the thread's dynamic priority
        above the base priority if the thread is handling
        user input, or lower it toward the base priority if
        the thread becomes compute-bound. The PriorityBase
        property can have a value between 0 and 31."
    ::= { win32ThreadEntry 16 }

ostdProcessCreationClassName  OBJECT-TYPE
    SYNTAX     WtcsDisplayString (SIZE (0..256))
    MAX-ACCESS read-only
    STATUS     current
    DESCRIPTION
        "Value of the scoping process CreationClassName
        property."
    ::= { win32ThreadEntry 17 }

ostdProcessHandle  OBJECT-TYPE
    SYNTAX     WtcsDisplayString (SIZE (0..256))
    MAX-ACCESS read-only
    STATUS     current
    DESCRIPTION
        "Process that created the thread. The contents of
        this property can be used by Windows API elements."
    ::= { win32ThreadEntry 18 }

ostdStartAddress  OBJECT-TYPE
    SYNTAX     Gauge32
    MAX-ACCESS read-only
    STATUS     current
    DESCRIPTION
        "Starting address of the thread. Because any
        application with appropriate access to the thread
        can change the thread's context, this value may
        only be an approximation of the thread's starting
        address."
    ::= { win32ThreadEntry 19 }

ostdStatus  OBJECT-TYPE
    SYNTAX     INTEGER {
        ok(1),
        error(2),
        degraded(3),
        unknown(4),
        predFail(5),
        starting(6),
        stopping(7),
        service(8)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is on-line,
        yet the managed element is neither 'OK' nor in one
        of the other states."
    ::= { win32ThreadEntry 20 }

ostdThreadState  OBJECT-TYPE
    SYNTAX     INTEGER {
        initialized(0), -- recognized by the microkernel
        ready(1), -- prepared to run on next available processor
        running(2), -- executing
        standby(3), -- about to run, only one thread may be in this state at a time
        terminated(4), -- finished executing
        waiting(5), -- not ready for the processor, when ready, it will be rescheduled
        transition(6), -- thread is waiting for resources other than the processor
        unknown(7) -- thread state is unknown
    }
    MAX-ACCESS read-only
    STATUS     current
    DESCRIPTION
        "Current execution state for the thread."
    ::= { win32ThreadEntry 21 }

ostdThreadWaitReason  OBJECT-TYPE
    SYNTAX     INTEGER {
        executive(0),
        freePage(1),
        pageIn(2),
        poolAllocation(3),
        executionDelay(4),
        freePage2(5),
        pageIn2(6),
        executive2(7),
        freePage3(8),
        pageIn3(9),
        poolAllocation2(10),
        executionDelay2(11),
        freePage4(12),
        pageIn4(13),
        eventPairHigh(14),
        eventPairLow(15),
        lpcreceive(16),
        lpcreply(17),
        virtualMemory(18),
        pageOut(19),
        unknown(20)
    }
    MAX-ACCESS read-only
    STATUS     current
    DESCRIPTION
        "Reason why the thread is waiting. The value is
        only valid if the ThreadState member is set to
        Waiting (6). Event pairs allow communication with
        protected subsystems ."
    ::= { win32ThreadEntry 22 }

ostdUserModeTime  OBJECT-TYPE
    SYNTAX     Counter64
    UNITS "100ns"
    MAX-ACCESS read-only
    STATUS     current
    DESCRIPTION
        "Time in user mode, in 100 nanoseconds. If this
        information is not available, a value of 0 should
        be used."
    ::= { win32ThreadEntry 23 }

win32CreateProcess OBJECT-TYPE
    SYNTAX     WtcsDisplayString (SIZE (0..256))
    MAX-ACCESS read-write
    STATUS     current
    DESCRIPTION
        "This OID can only be written to and cannot be
        read! Creates a new process. For security reasons,
        the script/program to be executed must reside in
        'spawn' directory under the SNMP Informant-OS
        installation."
    ::= { wmiProcesses 3 }

wmiSchedulerJobs OBJECT-IDENTITY
    STATUS     current
    DESCRIPTION
        "The Scheduler Jobs subcategory groups classes that
        represent scheduled job settings."
    ::= { wmiOperatingSystem 10 }

win32CurrentTimeTable OBJECT-TYPE
    SYNTAX     SEQUENCE OF Win32CurrentTimeEntry
    MAX-ACCESS not-accessible
    STATUS     current
    DESCRIPTION
        "The Win32_CurrentTime abstract is a singleton WMI
        class that describes a point in time by using the
        component items such as milliseconds, seconds,
        minutes, hours, days, days of the week, week in the
        month, months, quarters, and years."
    ::= { wmiSchedulerJobs 1 }

win32CurrentTimeEntry OBJECT-TYPE
    SYNTAX     Win32CurrentTimeEntry
    MAX-ACCESS not-accessible
    STATUS     current
    DESCRIPTION
        "None"
    INDEX      { osctIndex }
    ::= { win32CurrentTimeTable 1 }

Win32CurrentTimeEntry ::= SEQUENCE {
    osctIndex Integer32,
    osctDay  Gauge32,
    osctDayOfWeek  Gauge32,
    osctHour  Gauge32,
    osctMilliseconds  Gauge32,
    osctMinute  Gauge32,
    osctMonth  Gauge32,
    osctQuarter  Gauge32,
    osctSecond  Gauge32,
    osctWeekInMonth  Gauge32,
    osctYear  Gauge32
}

osctIndex OBJECT-TYPE
    SYNTAX     Integer32 (1..2147483647)
    MAX-ACCESS read-only
    STATUS     current
    DESCRIPTION
        "The value of this object uniquely identifies the
        instance entry for this class."
    ::= { win32CurrentTimeEntry 1 }

osctDay  OBJECT-TYPE
    SYNTAX     Gauge32
    MAX-ACCESS read-only
    STATUS     current
    DESCRIPTION
        "Current day that matches the query (1-31)."
    ::= { win32CurrentTimeEntry 2 }

osctDayOfWeek  OBJECT-TYPE
    SYNTAX     Gauge32
    MAX-ACCESS read-only
    STATUS     current
    DESCRIPTION
        "Current day of the current week that match the
        query (0-6). By convention, the value 0 (zero) is
        always Sunday, regardless of the culture or the
        locale set on the machine."
    ::= { win32CurrentTimeEntry 3 }

osctHour  OBJECT-TYPE
    SYNTAX     Gauge32
    MAX-ACCESS read-only
    STATUS     current
    DESCRIPTION
        "Current hour of the current day (0-23)."
    ::= { win32CurrentTimeEntry 4 }

osctMilliseconds  OBJECT-TYPE
    SYNTAX     Gauge32
    MAX-ACCESS read-only
    STATUS     current
    DESCRIPTION
        "Not used."
    ::= { win32CurrentTimeEntry 5 }

osctMinute  OBJECT-TYPE
    SYNTAX     Gauge32
    MAX-ACCESS read-only
    STATUS     current
    DESCRIPTION
        "Current minute (0-59)."
    ::= { win32CurrentTimeEntry 6 }

osctMonth  OBJECT-TYPE
    SYNTAX     Gauge32
    MAX-ACCESS read-only
    STATUS     current
    DESCRIPTION
        "Current month that matches the query (1-12)."
    ::= { win32CurrentTimeEntry 7 }

osctQuarter  OBJECT-TYPE
    SYNTAX     Gauge32
    MAX-ACCESS read-only
    STATUS     current
    DESCRIPTION
        "Current quarter of the current year (1-4)."
    ::= { win32CurrentTimeEntry 8 }

osctSecond  OBJECT-TYPE
    SYNTAX     Gauge32
    MAX-ACCESS read-only
    STATUS     current
    DESCRIPTION
        "Current second of the current minute (0-59)."
    ::= { win32CurrentTimeEntry 9 }

osctWeekInMonth  OBJECT-TYPE
    SYNTAX     Gauge32
    MAX-ACCESS read-only
    STATUS     current
    DESCRIPTION
        "Current week (1-6) in the current month (1-12)."
    ::= { win32CurrentTimeEntry 10 }

osctYear  OBJECT-TYPE
    SYNTAX     Gauge32
    MAX-ACCESS read-only
    STATUS     current
    DESCRIPTION
        "Current year that matches the query (4 digits)."
    ::= { win32CurrentTimeEntry 11 }

win32ScheduledJobTable OBJECT-TYPE
    SYNTAX     SEQUENCE OF Win32ScheduledJobEntry
    MAX-ACCESS not-accessible
    STATUS     current
    DESCRIPTION
        "The Win32_ScheduledJob WMI class represents a job
        created with the AT command in a command window
        from Start, Run, or from Control Panel, Scheduled
        Jobs. You can enumerate or delete any existing jobs
        that are displayed in the Control Panel, Scheduled
        Jobs dialog box by using the Win32_ScheduledJob
        instances. This class is only instrumented on
        Windows NT 4.0 and later. 
        
        Each job scheduled against the schedule service is
        stored persistently (the scheduler can start a job
        after a reboot), and is executed at the specified
        time and day of the week or month. If the computer
        is not active or if the scheduled service is not
        running at the specified job time, the schedule
        service runs the specified job on the next day at
        the specified time.
        
        Jobs are scheduled according to Universal
        Coordinated Time (UTC) with bias offset from
        Greenwich mean time (GMT), which means that a job
        can be specified using any time zone. The
        Win32_ScheduledJob class returns the local time
        with UTC offset when enumerating an object, and
        converts to local time when creating new jobs. For
        example, a job specified to run on a computer in
        Boston at 10:30 P.M. Monday PST time will be
        scheduled to run locally at 1:30 A.M. Tuesday EST.
        Note that a client must take into account whether
        or not daylight savings time is in operation on the
        local computer, and if it is, then subtract a bias
        of 60 minutes from the UTC offset."
    ::= { wmiSchedulerJobs 2 }

win32ScheduledJobEntry OBJECT-TYPE
    SYNTAX     Win32ScheduledJobEntry
    MAX-ACCESS not-accessible
    STATUS     current
    DESCRIPTION
        "None"
    INDEX      { ossjIndex }
    ::= { win32ScheduledJobTable 1 }

Win32ScheduledJobEntry ::= SEQUENCE {
    ossjIndex Integer32,
    ossjCaption  WtcsDisplayString,
    ossjCommand  WtcsDisplayString,
    ossjDaysOfMonth  Gauge32,
    ossjDaysOfWeek  Gauge32,
    ossjDescription  WtcsDisplayString,
    ossjElapsedTime  DateAndTime,
    ossjInstallDate  DateAndTime,
    ossjInteractWithDesktop  TruthValue,
    ossjJobId  Gauge32,
    ossjJobStatus  INTEGER,
    ossjName  WtcsDisplayString,
    ossjNotify  WtcsDisplayString,
    ossjOwner  WtcsDisplayString,
    ossjPriority  Gauge32,
    ossjRunRepeatedly  TruthValue,
    ossjStartTime  DateAndTime,
    ossjStatus  INTEGER,
    ossjTimeSubmitted  DateAndTime,
    ossjUntilTime  DateAndTime
}

ossjIndex OBJECT-TYPE
    SYNTAX     Integer32 (1..2147483647)
    MAX-ACCESS read-only
    STATUS     current
    DESCRIPTION
        "The value of this object uniquely identifies the
        instance entry for this class."
    ::= { win32ScheduledJobEntry 1 }

ossjCaption  OBJECT-TYPE
    SYNTAX     WtcsDisplayString
    MAX-ACCESS read-only
    STATUS     current
    DESCRIPTION
        "Short description of the object a one-line
        string."
    ::= { win32ScheduledJobEntry 2 }

ossjCommand  OBJECT-TYPE
    SYNTAX     WtcsDisplayString
    MAX-ACCESS read-only
    STATUS     current
    DESCRIPTION
        "Name of the command, batch program, or binary file
        (and command line arguments) that the schedule
        service uses to invoke the job.
        Example: 'defrag /q /f'"
    ::= { win32ScheduledJobEntry 3 }

ossjDaysOfMonth  OBJECT-TYPE
    SYNTAX     Gauge32
    MAX-ACCESS read-only
    STATUS     current
    DESCRIPTION
        "Days of the month when the job is scheduled to
        run. If a job is scheduled to run on multiple days
        of the month, these values can be joined in a
        logical OR. For example, if a job is to run on the
        1st and 16th of each month, the value of the
        DaysOfMonth property would be 1 OR 32768.
        
        Value Meaning 
        0x1 1st
        0x2 2nd
        0x4 3rd
        0x8 4th
        0x10 5th
        0x20 6th
        0x40 7th
        0x80 8th
        0x100 9th
        0x200 10th
        0x400 11th
        0x800 12th
        0x1000 13th
        0x2000 14th
        0x4000 15th
        0x8000 16th
        0x10000 17th
        0x20000 18th
        0x40000 19th
        0x80000 20th
        0x100000 21st
        0x200000 22nd
        0x400000 23rd
        0x800000 24th
        0x1000000 25th
        0x2000000 26th
        0x4000000 27th
        0x8000000 28th
        0x10000000 29th
        0x20000000 30th
        0x40000000 31st"
    ::= { win32ScheduledJobEntry 4 }

ossjDaysOfWeek  OBJECT-TYPE
    SYNTAX     Gauge32
    MAX-ACCESS read-only
    STATUS     current
    DESCRIPTION
        "Days of the week when a job is scheduled to run.
        If a job is scheduled to run on multiple days of
        the week, the values can be joined in a logical OR.
        For example, if a job is scheduled to run on
        Mondays, Wednesdays, and Fridays the value of the
        DaysOfWeek property would be 1 OR 4 OR 16.
        
        Value Meaning 
        0x1 Monday 
        0x2 Tuesday 
        0x4 Wednesday 
        0x8 Thursday 
        0x10 Friday 
        0x20 Saturday 
        0x40 Sunday"
    ::= { win32ScheduledJobEntry 5 }

ossjDescription  OBJECT-TYPE
    SYNTAX     WtcsDisplayString
    MAX-ACCESS read-only
    STATUS     current
    DESCRIPTION
        "Description of the object."
    ::= { win32ScheduledJobEntry 6 }

ossjElapsedTime  OBJECT-TYPE
    SYNTAX     DateAndTime
    MAX-ACCESS read-only
    STATUS     current
    DESCRIPTION
        "Length of time that the job has been executing."
    ::= { win32ScheduledJobEntry 7 }

ossjInstallDate  OBJECT-TYPE
    SYNTAX     DateAndTime
    MAX-ACCESS read-only
    STATUS     current
    DESCRIPTION
        "Object was installed. This property does not need
        a value to indicate that the object is installed."
    ::= { win32ScheduledJobEntry 8 }

ossjInteractWithDesktop  OBJECT-TYPE
    SYNTAX     TruthValue
    MAX-ACCESS read-only
    STATUS     current
    DESCRIPTION
        "Specified job is interactive, which means that a
        user can give input to a scheduled job while it is
        executing."
    ::= { win32ScheduledJobEntry 9 }

ossjJobId  OBJECT-TYPE
    SYNTAX     Gauge32
    MAX-ACCESS read-only
    STATUS     current
    DESCRIPTION
        "Identifying number of the job. It is used by
        methods as a handle to one job being scheduled on
        this computer."
    ::= { win32ScheduledJobEntry 10 }

ossjJobStatus  OBJECT-TYPE
    SYNTAX     INTEGER {
        success(1),
        failure(2)
    }
    MAX-ACCESS read-only
    STATUS     current
    DESCRIPTION
        "Status of execution the last time this job was
        scheduled to run."
    ::= { win32ScheduledJobEntry 11 }

ossjName  OBJECT-TYPE
    SYNTAX     WtcsDisplayString
    MAX-ACCESS read-only
    STATUS     current
    DESCRIPTION
        "Label by which the object is known. When
        subclassed, the property can be overridden to be a
        key property."
    ::= { win32ScheduledJobEntry 12 }

ossjNotify  OBJECT-TYPE
    SYNTAX     WtcsDisplayString
    MAX-ACCESS read-only
    STATUS     current
    DESCRIPTION
        "User to be notified when job completes or fails."
    ::= { win32ScheduledJobEntry 13 }

ossjOwner  OBJECT-TYPE
    SYNTAX     WtcsDisplayString
    MAX-ACCESS read-only
    STATUS     current
    DESCRIPTION
        "User that submitted the job."
    ::= { win32ScheduledJobEntry 14 }

ossjPriority  OBJECT-TYPE
    SYNTAX     Gauge32
    MAX-ACCESS read-only
    STATUS     current
    DESCRIPTION
        "Urgency or importance of execution of a job. "
    ::= { win32ScheduledJobEntry 15 }

ossjRunRepeatedly  OBJECT-TYPE
    SYNTAX     TruthValue
    MAX-ACCESS read-only
    STATUS     current
    DESCRIPTION
        "Scheduled job runs repeatedly on the days that the
        job is scheduled. If FALSE, then the job is run one
        time."
    ::= { win32ScheduledJobEntry 16 }

ossjStartTime  OBJECT-TYPE
    SYNTAX     DateAndTime
    MAX-ACCESS read-only
    STATUS     current
    DESCRIPTION
        "UTC time to run the job, in the form of
        YYYYMMDDHHMMSS.MMMMMM(+-)OOO, where YYYYMMDD must
        be replaced by ********. The replacement is
        necessary because the scheduling service only
        allows jobs to be configured to run one time, or
        run on a day of the month or week. A job cannot be
        run on a specific date.
        Example: ********123000.000000-420 implies 12:30
        P.M. PST with daylight savings time in effect."
    ::= { win32ScheduledJobEntry 17 }

ossjStatus  OBJECT-TYPE
    SYNTAX     INTEGER {
        ok(1),
        error(2),
        degraded(3),
        unknown(4),
        predFail(5),
        starting(6),
        stopping(7),
        service(8)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is on-line,
        yet the managed element is neither 'OK' nor in one
        of the other states."
    ::= { win32ScheduledJobEntry 18 }

ossjTimeSubmitted  OBJECT-TYPE
    SYNTAX     DateAndTime
    MAX-ACCESS read-only
    STATUS     current
    DESCRIPTION
        "Time the job is submitted."
    ::= { win32ScheduledJobEntry 19 }

ossjUntilTime  OBJECT-TYPE
    SYNTAX     DateAndTime
    MAX-ACCESS read-only
    STATUS     current
    DESCRIPTION
        "Time after which the job is invalid or must be
        stopped."
    ::= { win32ScheduledJobEntry 20 }

wmiServices OBJECT-IDENTITY
    STATUS     current
    DESCRIPTION
        "The Services subcategory groups classes that
        represent services and base services."
    ::= { wmiOperatingSystem 11 }

win32ServiceTable OBJECT-TYPE
    SYNTAX     SEQUENCE OF Win32ServiceEntry
    MAX-ACCESS not-accessible
    STATUS     current
    DESCRIPTION
        "The Win32_Service WMI class represents a service
        on a Windows computer system. A service application
        conforms to the interface rules of the Service
        Control Manager (SCM), and can be started by a user
        automatically at system boot through the Services
        control panel utility, or by an application that
        uses the service functions included in the Windows
        API. Services can execute when no user is logged on
        to the system."
    ::= { wmiServices 1 }

win32ServiceEntry OBJECT-TYPE
    SYNTAX     Win32ServiceEntry
    MAX-ACCESS not-accessible
    STATUS     current
    DESCRIPTION
        "None"
    INDEX      { ossvcIndex }
    ::= { win32ServiceTable 1 }

Win32ServiceEntry ::= SEQUENCE {
    ossvcIndex Integer32,
    ossvcAcceptPause  TruthValue,
    ossvcAcceptStop  TruthValue,
    ossvcCaption  WtcsDisplayString,
    ossvcCheckPoint  Gauge32,
    ossvcCreationClassName  WtcsDisplayString,
    ossvcDescription  WtcsDisplayString,
    ossvcDesktopInteract  TruthValue,
    ossvcDisplayName  WtcsDisplayString,
    ossvcErrorControl  WtcsDisplayString,
    ossvcExitCode  Gauge32,
    ossvcInstallDate  DateAndTime,
    ossvcName  WtcsDisplayString,
    ossvcPathName  WtcsDisplayString,
    ossvcProcessId  Gauge32,
    ossvcServiceSpecificExitCode  Gauge32,
    ossvcServiceType  INTEGER,
    ossvcStarted  TruthValue,
    ossvcStartMode  WtcsDisplayString,
    ossvcStartName  WtcsDisplayString,
    ossvcState  INTEGER,
    ossvcStatus  INTEGER,
    ossvcSystemCreationClassName  WtcsDisplayString,
    ossvcSystemName  WtcsDisplayString,
    ossvcTagId  Gauge32,
    ossvcWaitHint  Gauge32
}

ossvcIndex OBJECT-TYPE
    SYNTAX     Integer32 (1..2147483647)
    MAX-ACCESS read-only
    STATUS     current
    DESCRIPTION
        "The value of this object uniquely identifies the
        instance entry for this class."
    ::= { win32ServiceEntry 1 }

ossvcAcceptPause  OBJECT-TYPE
    SYNTAX     TruthValue
    MAX-ACCESS read-only
    STATUS     current
    DESCRIPTION
        "Service can be paused."
    ::= { win32ServiceEntry 2 }

ossvcAcceptStop  OBJECT-TYPE
    SYNTAX     TruthValue
    MAX-ACCESS read-only
    STATUS     current
    DESCRIPTION
        "Service can be stopped."
    ::= { win32ServiceEntry 3 }

ossvcCaption  OBJECT-TYPE
    SYNTAX     WtcsDisplayString
    MAX-ACCESS read-only
    STATUS     current
    DESCRIPTION
        "Short description of the object a one-line
        string."
    ::= { win32ServiceEntry 4 }

ossvcCheckPoint  OBJECT-TYPE
    SYNTAX     Gauge32
    MAX-ACCESS read-only
    STATUS     current
    DESCRIPTION
        "Value that the service increments periodically to
        report its progress during a long start, stop,
        pause, or continue operation. For example, the
        service increments this value as it completes each
        step of its initialization when it is starting up.
        The user interface program that invokes the
        operation on the service uses this value to track
        the progress of the service during a lengthy
        operation. This value is not valid and should be
        zero when the service does not have a start, stop,
        pause, or continue operation pending. "
    ::= { win32ServiceEntry 5 }

ossvcCreationClassName  OBJECT-TYPE
    SYNTAX     WtcsDisplayString (SIZE (0..256))
    MAX-ACCESS read-only
    STATUS     current
    DESCRIPTION
        "Name of the first concrete class to appear in the
        inheritance chain used in the creation of an
        instance. When used with the other key properties
        of the class, the property allows all instances of
        this class and its subclasses to be uniquely
        identified."
    ::= { win32ServiceEntry 6 }

ossvcDescription  OBJECT-TYPE
    SYNTAX     WtcsDisplayString
    MAX-ACCESS read-only
    STATUS     current
    DESCRIPTION
        "Description of the object."
    ::= { win32ServiceEntry 7 }

ossvcDesktopInteract  OBJECT-TYPE
    SYNTAX     TruthValue
    MAX-ACCESS read-only
    STATUS     current
    DESCRIPTION
        "Service can create or communicate with windows on
        the desktop."
    ::= { win32ServiceEntry 8 }

ossvcDisplayName  OBJECT-TYPE
    SYNTAX     WtcsDisplayString
    MAX-ACCESS read-only
    STATUS     current
    DESCRIPTION
        "Display name of the service. This string has a
        maximum length of 256 characters. The name is
        case-preserved in the Service Control Manager.
        However, DisplayName comparisons are always
        case-insensitive. Constraint: accepts the same
        value as the Name property.
        Example: 'Atdisk'"
    ::= { win32ServiceEntry 9 }

ossvcErrorControl  OBJECT-TYPE
    SYNTAX     WtcsDisplayString
    MAX-ACCESS read-only
    STATUS     current
    DESCRIPTION
        "Severity of the error if this service fails to
        start during startup. The value indicates the
        action taken by the startup program if failure
        occurs. All errors are logged by the computer
        system.
        Value Meaning 
        'Ignore' User is not notified. 
        'Normal' User is notified. 
        'Severe' System is restarted with the
        last-known-good configuration. 
        'Critical' System attempts to restart with a good
        configuration. 
        'Unknown' Severity of the error is unknown. "
    ::= { win32ServiceEntry 10 }

ossvcExitCode  OBJECT-TYPE
    SYNTAX     Gauge32
    MAX-ACCESS read-only
    STATUS     current
    DESCRIPTION
        "Windows error code defining any problems
        encountered in starting or stopping the service.
        This property is set to
        ERROR_SERVICE_SPECIFIC_ERROR (1066) when the error
        is unique to the service represented by this class,
        and information about the error is available in the
        ServiceSpecificExitCode property. The service sets
        this value to NO_ERROR when running, and again upon
        normal termination."
    ::= { win32ServiceEntry 11 }

ossvcInstallDate  OBJECT-TYPE
    SYNTAX     DateAndTime
    MAX-ACCESS read-only
    STATUS     current
    DESCRIPTION
        "Date object is installed. This property does not
        need a value to indicate that the object is
        installed."
    ::= { win32ServiceEntry 12 }

ossvcName  OBJECT-TYPE
    SYNTAX     WtcsDisplayString
    MAX-ACCESS read-only
    STATUS     current
    DESCRIPTION
        "Unique identifier of the service that provides an
        indication of the functionality that is managed.
        This functionality is described in more detail in
        the Description property of the object."
    ::= { win32ServiceEntry 13 }

ossvcPathName  OBJECT-TYPE
    SYNTAX     WtcsDisplayString
    MAX-ACCESS read-only
    STATUS     current
    DESCRIPTION
        "Fully-qualified path to the service binary file
        that implements the service. 
        Example: '\SystemRoot\System32\drivers\afd.sys'"
    ::= { win32ServiceEntry 14 }

ossvcProcessId  OBJECT-TYPE
    SYNTAX     Gauge32
    MAX-ACCESS read-only
    STATUS     current
    DESCRIPTION
        "Process identifier of the service. 
        Example: 324"
    ::= { win32ServiceEntry 15 }

ossvcServiceSpecificExitCode  OBJECT-TYPE
    SYNTAX     Gauge32
    MAX-ACCESS read-only
    STATUS     current
    DESCRIPTION
        "Service-specific error code for errors that occur
        while the service is either starting or stopping.
        The exit codes are defined by the service
        represented by this class. This value is only set
        when the ExitCode property value is
        ERROR_SERVICE_SPECIFIC_ERROR (1066)."
    ::= { win32ServiceEntry 16 }

ossvcServiceType  OBJECT-TYPE
    SYNTAX     INTEGER {
        kernelDriver(1),
        fileSystemDriver(2),
        adapter(3),
        recognizerDriver(4),
        ownProcess(5),
        shareProcess(6),
        interactiveProcess(7)
    }
    MAX-ACCESS read-only
    STATUS     current
    DESCRIPTION
        "Type of service provided to calling processes."
    ::= { win32ServiceEntry 17 }

ossvcStarted  OBJECT-TYPE
    SYNTAX     TruthValue
    MAX-ACCESS read-only
    STATUS     current
    DESCRIPTION
        "Service has been started."
    ::= { win32ServiceEntry 18 }

ossvcStartMode  OBJECT-TYPE
    SYNTAX     WtcsDisplayString
    MAX-ACCESS read-only
    STATUS     current
    DESCRIPTION
        "Start mode of the Windows base service.
        Value Meaning 
        'Boot' Device driver started by the operating
        system loader (valid only for driver services) 
        'System' Device driver started by the IoInitSystem
        method (valid only for driver services) 
        'Auto' Service to be started automatically by the
        service control manager during system startup 
        'Manual' Service to be started by the service
        control manager when a process calls the
        StartService method 
        'Disabled' Service that cannot be started "
    ::= { win32ServiceEntry 19 }

ossvcStartName  OBJECT-TYPE
    SYNTAX     WtcsDisplayString
    MAX-ACCESS read-only
    STATUS     current
    DESCRIPTION
        "Account name under which a service runs. Depending
        on the service type, the account name may be in the
        form of DomainName\Username. The service process is
        logged by using one of these two forms when it
        runs. If the account belongs to the built-in
        domain, then .\Username can be specified. For
        kernel or system level drivers, StartName contains
        the driver object name (that is, \FileSystem\Rdr or
        \Driver\Xns) which the input and output (I/O)
        system uses to load the device driver.
        Additionally, if NULL is specified, the driver runs
        with a default object name created by the I/O
        system based on the service name. Example:
        'DWDOM\Admin'
        Windows XP:  You may use UPN format
        (Username@DomainName) to specify the StartName.
        Windows 2000:  To change from a specified user to
        the LocalSystem account, use .\LocalSystem."
    ::= { win32ServiceEntry 20 }

ossvcState  OBJECT-TYPE
    SYNTAX     INTEGER {
        stopped(1),
        startPending(2),
        stopPending(3),
        running(4),
        continuePending(5),
        pausePending(6),
        paused(7),
        unknown(8)
    }
    MAX-ACCESS read-write
    STATUS     current
    DESCRIPTION
        "Current state of the base service. Setting the
        state to stopped, running, or paused will either
        stop, start (or resume), or pause the service."
    ::= { win32ServiceEntry 21 }

ossvcStatus  OBJECT-TYPE
    SYNTAX     INTEGER {
        ok(1),
        error(2),
        degraded(3),
        unknown(4),
        predFail(5),
        starting(6),
        stopping(7),
        service(8)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is on-line,
        yet the managed element is neither 'OK' nor in one
        of the other states."
    ::= { win32ServiceEntry 22 }

ossvcSystemCreationClassName  OBJECT-TYPE
    SYNTAX     WtcsDisplayString
    MAX-ACCESS read-only
    STATUS     current
    DESCRIPTION
        "Type name of the system that hosts this service."
    ::= { win32ServiceEntry 23 }

ossvcSystemName  OBJECT-TYPE
    SYNTAX     WtcsDisplayString
    MAX-ACCESS read-only
    STATUS     current
    DESCRIPTION
        "Name of the system that hosts this service."
    ::= { win32ServiceEntry 24 }

ossvcTagId  OBJECT-TYPE
    SYNTAX     Gauge32
    MAX-ACCESS read-only
    STATUS     current
    DESCRIPTION
        "Unique tag value for this service in the group. A
        value of 0 (zero) indicates that the service does
        not have a tag. A tag can be used to order service
        startup within a load order group by specifying a
        tag order vector in the registry located at:
        HKEY_LOCAL_MACHINE\System\CurrentControlSet\Control
        \GroupOrderList. Tags are only evaluated for Kernel
        Driver and File System Driver start type services
        that have Boot or System start modes."
    ::= { win32ServiceEntry 25 }

ossvcWaitHint  OBJECT-TYPE
    SYNTAX     Gauge32
    MAX-ACCESS read-only
    STATUS     current
    DESCRIPTION
        "Estimated time required (in milliseconds) for a
        pending start, stop, pause, or continue operation.
        After the specified amount of time has elapsed, the
        service makes its next call to the SetServiceStatus
        method with either an incremented CheckPoint value
        or a change in CurrentState. If the amount of time
        specified by WaitHint passes, and CheckPoint has
        not been incremented, or CurrentState has not
        changed, the service control manager or service
        control program assumes that an error has
        occurred."
    ::= { win32ServiceEntry 26 }

wmiShares OBJECT-IDENTITY
    STATUS     current
    DESCRIPTION
        "The Shares subcategory groups classes that
        represent details of shared resources such as
        printers and folders."
    ::= { wmiOperatingSystem 12 }

win32DFSNodeTable OBJECT-TYPE
    SYNTAX     SEQUENCE OF Win32DFSNodeEntry
    MAX-ACCESS not-accessible
    STATUS     current
    DESCRIPTION
        "The Win32_DFSNode WMI class represents a root or
        junction node of a domain-based or stand-alone
        distributed file system (DFS). The DFS root is also
        represented by this class because the root is also
        a node. Each link has one or more targets or actual
        share paths for the storage defined by the
        Win32_DFSTarget class. This class is new for
        Windows Server 2003."
    ::= { wmiShares 1 }

win32DFSNodeEntry OBJECT-TYPE
    SYNTAX     Win32DFSNodeEntry
    MAX-ACCESS not-accessible
    STATUS     current
    DESCRIPTION
        "None"
    INDEX      { osdfsnIndex }
    ::= { win32DFSNodeTable 1 }

Win32DFSNodeEntry ::= SEQUENCE {
    osdfsnIndex Integer32,
    osdfsnCaption  WtcsDisplayString,
    osdfsnDescription  WtcsDisplayString,
    osdfsnInstallDate  DateAndTime,
    osdfsnName  WtcsDisplayString,
    osdfsnRoot  TruthValue,
    osdfsnState  INTEGER,
    osdfsnStatus  INTEGER,
    osdfsnTimeout  Gauge32
}

osdfsnIndex OBJECT-TYPE
    SYNTAX     Integer32 (1..2147483647)
    MAX-ACCESS read-only
    STATUS     current
    DESCRIPTION
        "The value of this object uniquely identifies the
        instance entry for this class."
    ::= { win32DFSNodeEntry 1 }

osdfsnCaption  OBJECT-TYPE
    SYNTAX     WtcsDisplayString (SIZE (0..64))
    MAX-ACCESS read-only
    STATUS     current
    DESCRIPTION
        "Short description of the object a one-line string.
        This property is inherited from
        CIM_ManagedSystemElement."
    ::= { win32DFSNodeEntry 2 }

osdfsnDescription  OBJECT-TYPE
    SYNTAX     WtcsDisplayString
    MAX-ACCESS read-only
    STATUS     current
    DESCRIPTION
        "Comment that describes the link. This property is
        inherited from CIM_ManagedSystemElement."
    ::= { win32DFSNodeEntry 3 }

osdfsnInstallDate  OBJECT-TYPE
    SYNTAX     DateAndTime
    MAX-ACCESS read-only
    STATUS     current
    DESCRIPTION
        "Date that an object is installed. This property
        does not need a value to indicate that the object
        is installed. This property is inherited from
        CIM_ManagedSystemElement. "
    ::= { win32DFSNodeEntry 4 }

osdfsnName  OBJECT-TYPE
    SYNTAX     WtcsDisplayString
    MAX-ACCESS read-only
    STATUS     current
    DESCRIPTION
        "Identifier for the DFS node. It is the same as the
        entry path of a node, based on the Universal Naming
        Convention (UNC). It can take one of the following
        two forms:
        \\\\DfsServerName\\ShareName\\PathToLink
        \\\\DomainName\\FtDfsName\\PathToLink
        where
        DfsServerName is the name of a server that hosts
        the DFS root volume.
        ShareName is the name of the share published on the
        host server.
        PathToLink is the path to the physical share.
        DomainName is the name of the domain that hosts the
        DFS root volume.
        FtDfsName is the name of the fault-tolerant DFS
        root published.
        PathToLink is the path to the physical share.
        This property overrides the Name property in
        CIM_ManagedSystemElement."
    ::= { win32DFSNodeEntry 5 }

osdfsnRoot  OBJECT-TYPE
    SYNTAX     TruthValue
    MAX-ACCESS read-only
    STATUS     current
    DESCRIPTION
        "Indicate whether the node is a DFS root or a link.
        A value of TRUE indicates that the node is a root."
    ::= { win32DFSNodeEntry 6 }

osdfsnState  OBJECT-TYPE
    SYNTAX     INTEGER {
        ok(0),
        inconsistent(1),
        online(2),
        offline(3)
    }
    MAX-ACCESS read-only
    STATUS     current
    DESCRIPTION
        "Status of the node."
    ::= { win32DFSNodeEntry 7 }

osdfsnStatus  OBJECT-TYPE
    SYNTAX     INTEGER {
        ok(1),
        error(2),
        degraded(3),
        unknown(4),
        predFail(5),
        starting(6),
        stopping(7),
        service(8)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is on-line,
        yet the managed element is neither 'OK' nor in one
        of the other states. This property is inherited
        from the CIM_ManagedSystemElement class."
    ::= { win32DFSNodeEntry 8 }

osdfsnTimeout  OBJECT-TYPE
    SYNTAX     Gauge32
    UNITS "Seconds"
    MAX-ACCESS read-only
    STATUS     current
    DESCRIPTION
        "Time in seconds that the client caches the
        referral of this link."
    ::= { win32DFSNodeEntry 9 }

win32DFSTargetTable OBJECT-TYPE
    SYNTAX     SEQUENCE OF Win32DFSTargetEntry
    MAX-ACCESS not-accessible
    STATUS     current
    DESCRIPTION
        "The Win32_DFSTarget WMI class represents a target
        of a DFS node. This class was added for Windows
        Server 2003 family."
    ::= { wmiShares 2 }

win32DFSTargetEntry OBJECT-TYPE
    SYNTAX     Win32DFSTargetEntry
    MAX-ACCESS not-accessible
    STATUS     current
    DESCRIPTION
        "None"
    INDEX      { osdfstIndex }
    ::= { win32DFSTargetTable 1 }

Win32DFSTargetEntry ::= SEQUENCE {
    osdfstIndex Integer32,
    osdfstCaption  WtcsDisplayString,
    osdfstDescription  WtcsDisplayString,
    osdfstInstallDate  DateAndTime,
    osdfstLinkName  WtcsDisplayString,
    osdfstName  WtcsDisplayString,
    osdfstServerName  WtcsDisplayString,
    osdfstShareName  WtcsDisplayString,
    osdfstState  INTEGER,
    osdfstStatus  INTEGER
}

osdfstIndex OBJECT-TYPE
    SYNTAX     Integer32 (1..2147483647)
    MAX-ACCESS read-only
    STATUS     current
    DESCRIPTION
        "The value of this object uniquely identifies the
        instance entry for this class."
    ::= { win32DFSTargetEntry 1 }

osdfstCaption  OBJECT-TYPE
    SYNTAX     WtcsDisplayString (SIZE (0..64))
    MAX-ACCESS read-only
    STATUS     current
    DESCRIPTION
        "Short description (one-line string) of the object.
        This property is inherited from
        CIM_ManagedSystemElement."
    ::= { win32DFSTargetEntry 2 }

osdfstDescription  OBJECT-TYPE
    SYNTAX     WtcsDisplayString
    MAX-ACCESS read-only
    STATUS     current
    DESCRIPTION
        "Comment that describes the link. This property is
        inherited from CIM_ManagedSystemElement."
    ::= { win32DFSTargetEntry 3 }

osdfstInstallDate  OBJECT-TYPE
    SYNTAX     DateAndTime
    MAX-ACCESS read-only
    STATUS     current
    DESCRIPTION
        "Date and time when object was installed. This
        property does not need a value to indicate that the
        object is installed. This property is inherited
        from CIM_ManagedSystemElement. "
    ::= { win32DFSTargetEntry 4 }

osdfstLinkName  OBJECT-TYPE
    SYNTAX     WtcsDisplayString
    MAX-ACCESS read-only
    STATUS     current
    DESCRIPTION
        "Entry path of the node to which this target
        belongs."
    ::= { win32DFSTargetEntry 5 }

osdfstName  OBJECT-TYPE
    SYNTAX     WtcsDisplayString
    MAX-ACCESS read-only
    STATUS     current
    DESCRIPTION
        "Label by which the object is known. When
        subclassed, the property can be overridden to be a
        key property. This property is inherited from
        CIM_ManagedSystemElement."
    ::= { win32DFSTargetEntry 6 }

osdfstServerName  OBJECT-TYPE
    SYNTAX     WtcsDisplayString
    MAX-ACCESS read-only
    STATUS     current
    DESCRIPTION
        "Name of the server that the node references"
    ::= { win32DFSTargetEntry 7 }

osdfstShareName  OBJECT-TYPE
    SYNTAX     WtcsDisplayString
    MAX-ACCESS read-only
    STATUS     current
    DESCRIPTION
        "String representing the name of the share that the
        node references."
    ::= { win32DFSTargetEntry 8 }

osdfstState  OBJECT-TYPE
    SYNTAX     INTEGER {
        offline(0),
        online(2),
        active(4)
    }
    MAX-ACCESS read-only
    STATUS     current
    DESCRIPTION
        "State of the target."
    ::= { win32DFSTargetEntry 9 }

osdfstStatus  OBJECT-TYPE
    SYNTAX     INTEGER {
        ok(1),
        error(2),
        degraded(3),
        unknown(4),
        predFail(5),
        starting(6),
        stopping(7),
        service(8)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is on-line,
        yet the managed element is neither 'OK' nor in one
        of the other states. This property is inherited
        from CIM_ManagedSystemElement."
    ::= { win32DFSTargetEntry 10 }

win32ServerConnectionTable OBJECT-TYPE
    SYNTAX     SEQUENCE OF Win32ServerConnectionEntry
    MAX-ACCESS not-accessible
    STATUS     current
    DESCRIPTION
        "The Win32_ServerConnection WMI class represents
        the connections made from a remote computer to a
        shared resource on the local computer. This class
        is new for Windows XP."
    ::= { wmiShares 3 }

win32ServerConnectionEntry OBJECT-TYPE
    SYNTAX     Win32ServerConnectionEntry
    MAX-ACCESS not-accessible
    STATUS     current
    DESCRIPTION
        "None"
    INDEX      { osscnIndex }
    ::= { win32ServerConnectionTable 1 }

Win32ServerConnectionEntry ::= SEQUENCE {
    osscnIndex Integer32,
    osscnActiveTime  Gauge32,
    osscnCaption  WtcsDisplayString,
    osscnComputerName  WtcsDisplayString,
    osscnConnectionID  Gauge32,
    osscnDescription  WtcsDisplayString,
    osscnInstallDate  DateAndTime,
    osscnName  WtcsDisplayString,
    osscnNumberOfFiles  Gauge32,
    osscnNumberOfUsers  Gauge32,
    osscnShareName  WtcsDisplayString,
    osscnStatus  INTEGER,
    osscnUserName  WtcsDisplayString
}

osscnIndex OBJECT-TYPE
    SYNTAX     Integer32 (1..2147483647)
    MAX-ACCESS read-only
    STATUS     current
    DESCRIPTION
        "The value of this object uniquely identifies the
        instance entry for this class."
    ::= { win32ServerConnectionEntry 1 }

osscnActiveTime  OBJECT-TYPE
    SYNTAX     Gauge32
    UNITS "Seconds"
    MAX-ACCESS read-only
    STATUS     current
    DESCRIPTION
        "Number of seconds since this connection was
        established."
    ::= { win32ServerConnectionEntry 2 }

osscnCaption  OBJECT-TYPE
    SYNTAX     WtcsDisplayString (SIZE (0..64))
    MAX-ACCESS read-only
    STATUS     current
    DESCRIPTION
        "Short description of the object a one-line string.
        This property is inherited from
        CIM_ManagedSystemElement."
    ::= { win32ServerConnectionEntry 3 }

osscnComputerName  OBJECT-TYPE
    SYNTAX     WtcsDisplayString
    MAX-ACCESS read-only
    STATUS     current
    DESCRIPTION
        "Name of the computer from which the connection is
        established."
    ::= { win32ServerConnectionEntry 4 }

osscnConnectionID  OBJECT-TYPE
    SYNTAX     Gauge32
    MAX-ACCESS read-only
    STATUS     current
    DESCRIPTION
        "Unique identifier for the connection."
    ::= { win32ServerConnectionEntry 5 }

osscnDescription  OBJECT-TYPE
    SYNTAX     WtcsDisplayString
    MAX-ACCESS read-only
    STATUS     current
    DESCRIPTION
        "Comment that describes the link. This property is
        inherited from CIM_ManagedSystemElement."
    ::= { win32ServerConnectionEntry 6 }

osscnInstallDate  OBJECT-TYPE
    SYNTAX     DateAndTime
    MAX-ACCESS read-only
    STATUS     current
    DESCRIPTION
        "Date/time when the object was installed. This
        property does not need a value to indicate that the
        object is installed. This property is inherited
        from CIM_ManagedSystemElement."
    ::= { win32ServerConnectionEntry 7 }

osscnName  OBJECT-TYPE
    SYNTAX     WtcsDisplayString
    MAX-ACCESS read-only
    STATUS     current
    DESCRIPTION
        "Label by which the object is known. When
        subclassed, the property can be overridden to be a
        key property. This property is inherited from
        CIM_ManagedSystemElement."
    ::= { win32ServerConnectionEntry 8 }

osscnNumberOfFiles  OBJECT-TYPE
    SYNTAX     Gauge32
    MAX-ACCESS read-only
    STATUS     current
    DESCRIPTION
        "Number of open files associated with this
        connection."
    ::= { win32ServerConnectionEntry 9 }

osscnNumberOfUsers  OBJECT-TYPE
    SYNTAX     Gauge32
    MAX-ACCESS read-only
    STATUS     current
    DESCRIPTION
        "Number of users associated with this connection."
    ::= { win32ServerConnectionEntry 10 }

osscnShareName  OBJECT-TYPE
    SYNTAX     WtcsDisplayString
    MAX-ACCESS read-only
    STATUS     current
    DESCRIPTION
        "Share resource to which the connection is
        established."
    ::= { win32ServerConnectionEntry 11 }

osscnStatus  OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly, but
        predicting a failure in the near future).
        Non-operational statuses include: 'Error',
        'Starting', 'Stopping', and 'Service'. The latter,
        'Service', could apply during mirror-resilvering of
        a disk, reload of a user permissions list, or other
        administrative work. Not all such work is on-line,
        yet the managed element is neither 'OK' nor in one
        of the other states. This property is inherited
        from CIM_ManagedSystemElement."
    ::= { win32ServerConnectionEntry 12 }

osscnUserName  OBJECT-TYPE
    SYNTAX     WtcsDisplayString
    MAX-ACCESS read-only
    STATUS     current
    DESCRIPTION
        "Name of the user that made a connection."
    ::= { win32ServerConnectionEntry 13 }

win32ServerSessionTable OBJECT-TYPE
    SYNTAX     SEQUENCE OF Win32ServerSessionEntry
    MAX-ACCESS not-accessible
    STATUS     current
    DESCRIPTION
        "The Win32_ServerSession WMI class represents the
        sessions that have been established with the local
        computer by users on a remote computer. This class
        was added for Windows XP."
    ::= { wmiShares 4 }

win32ServerSessionEntry OBJECT-TYPE
    SYNTAX     Win32ServerSessionEntry
    MAX-ACCESS not-accessible
    STATUS     current
    DESCRIPTION
        "None"
    INDEX      { osssIndex }
    ::= { win32ServerSessionTable 1 }

Win32ServerSessionEntry ::= SEQUENCE {
    osssIndex Integer32,
    osssActiveTime  Gauge32,
    osssCaption  WtcsDisplayString,
    osssClientType  WtcsDisplayString,
    osssComputerName  WtcsDisplayString,
    osssDescription  WtcsDisplayString,
    osssIdleTime  Gauge32,
    osssInstallDate  DateAndTime,
    osssName  WtcsDisplayString,
    osssResourcesOpened  Gauge32,
    osssSessionType  INTEGER,
    osssStatus  INTEGER,
    osssTransportName  WtcsDisplayString,
    osssUserName  WtcsDisplayString
}

osssIndex OBJECT-TYPE
    SYNTAX     Integer32 (1..2147483647)
    MAX-ACCESS read-only
    STATUS     current
    DESCRIPTION
        "The value of this object uniquely identifies the
        instance entry for this class."
    ::= { win32ServerSessionEntry 1 }

osssActiveTime  OBJECT-TYPE
    SYNTAX     Gauge32
    UNITS "Seconds"
    MAX-ACCESS read-only
    STATUS     current
    DESCRIPTION
        "Number of seconds since this session was
        established."
    ::= { win32ServerSessionEntry 2 }

osssCaption  OBJECT-TYPE
    SYNTAX     WtcsDisplayString (SIZE (0..64))
    MAX-ACCESS read-only
    STATUS     current
    DESCRIPTION
        "Short description (one-line string) of the object.
        This property is inherited from
        CIM_ManagedSystemElement."
    ::= { win32ServerSessionEntry 3 }

osssClientType  OBJECT-TYPE
    SYNTAX     WtcsDisplayString
    MAX-ACCESS read-only
    STATUS     current
    DESCRIPTION
        "Type of the connected client."
    ::= { win32ServerSessionEntry 4 }

osssComputerName  OBJECT-TYPE
    SYNTAX     WtcsDisplayString
    MAX-ACCESS read-only
    STATUS     current
    DESCRIPTION
        "Name of the computer from which the session is
        established."
    ::= { win32ServerSessionEntry 5 }

osssDescription  OBJECT-TYPE
    SYNTAX     WtcsDisplayString
    MAX-ACCESS read-only
    STATUS     current
    DESCRIPTION
        "Comment that describes the link. This property is
        inherited from CIM_ManagedSystemElement."
    ::= { win32ServerSessionEntry 6 }

osssIdleTime  OBJECT-TYPE
    SYNTAX     Gauge32
    UNITS "Seconds"
    MAX-ACCESS read-only
    STATUS     current
    DESCRIPTION
        "Number of seconds that the session has been idle."
    ::= { win32ServerSessionEntry 7 }

osssInstallDate  OBJECT-TYPE
    SYNTAX     DateAndTime
    MAX-ACCESS read-only
    STATUS     current
    DESCRIPTION
        "Date and time the object was installed. This
        property does not need a value to indicate that the
        object is installed. This property is inherited
        from CIM_ManagedSystemElement."
    ::= { win32ServerSessionEntry 8 }

osssName  OBJECT-TYPE
    SYNTAX     WtcsDisplayString
    MAX-ACCESS read-only
    STATUS     current
    DESCRIPTION
        "Label by which the object is known. When
        subclassed, the property can be overridden to be a
        key property. This property is inherited from
        CIM_ManagedSystemElement."
    ::= { win32ServerSessionEntry 9 }

osssResourcesOpened  OBJECT-TYPE
    SYNTAX     Gauge32
    MAX-ACCESS read-only
    STATUS     current
    DESCRIPTION
        "Number of files, devices, and pipes opened during
        this session."
    ::= { win32ServerSessionEntry 10 }

osssSessionType  OBJECT-TYPE
    SYNTAX     INTEGER {
        guest(0),
        noEncryption(1),
        other(2)
    }
    MAX-ACCESS read-only
    STATUS     current
    DESCRIPTION
        "Method of opening the session. This property is
        available only on Windows NT."
    ::= { win32ServerSessionEntry 11 }

osssStatus  OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is on-line,
        yet the managed element is neither 'OK' nor in one
        of the other states. This property is inherited
        from CIM_ManagedSystemElement."
    ::= { win32ServerSessionEntry 12 }

osssTransportName  OBJECT-TYPE
    SYNTAX     WtcsDisplayString
    MAX-ACCESS read-only
    STATUS     current
    DESCRIPTION
        "Name of the transport that the client is using to
        communicate with the server."
    ::= { win32ServerSessionEntry 13 }

osssUserName  OBJECT-TYPE
    SYNTAX     WtcsDisplayString
    MAX-ACCESS read-only
    STATUS     current
    DESCRIPTION
        "Name of the user that established the session."
    ::= { win32ServerSessionEntry 14 }

win32ShareTable OBJECT-TYPE
    SYNTAX     SEQUENCE OF Win32ShareEntry
    MAX-ACCESS not-accessible
    STATUS     current
    DESCRIPTION
        "The Win32_Share class represents a shared resource
        on a Windows system. This may be a disk drive,
        printer, inter-process communication, or other
        shareable device. For information on retrieving WMI
        classes see Retrieving a Class."
    ::= { wmiShares 5 }

win32ShareEntry OBJECT-TYPE
    SYNTAX     Win32ShareEntry
    MAX-ACCESS not-accessible
    STATUS     current
    DESCRIPTION
        "None"
    INDEX      { osshIndex }
    ::= { win32ShareTable 1 }

Win32ShareEntry ::= SEQUENCE {
    osshIndex Integer32,
    osshAccessMask  Gauge32,
    osshAllowMaximum  TruthValue,
    osshCaption  WtcsDisplayString,
    osshDescription  WtcsDisplayString,
    osshInstallDate  DateAndTime,
    osshMaximumAllowed  Gauge32,
    osshName  WtcsDisplayString,
    osshPath  WtcsDisplayString,
    osshStatus  INTEGER,
    osshType  Gauge32
}

osshIndex OBJECT-TYPE
    SYNTAX     Integer32 (1..2147483647)
    MAX-ACCESS read-only
    STATUS     current
    DESCRIPTION
        "The value of this object uniquely identifies the
        instance entry for this class."
    ::= { win32ShareEntry 1 }

osshAccessMask  OBJECT-TYPE
    SYNTAX     Gauge32
    MAX-ACCESS read-only
    STATUS     current
    DESCRIPTION
        "List of access rights to the given file or
        directory held by the user or group on whose behalf
        the instance is returned. This property is only
        supported under Windows NT and Windows 2000. On
        Windows 98 and on Windows NT/Windows 2000 FAT
        volumes, the FULL_ACCESS value is returned instead,
        indicating no security has been set on the object.
        Windows 2000, Windows XP:  This property is no
        longer used due to the expense of calling
        GetEffectiveRightsFromAcl. You should use the
        Win32_Share.GetAccessMask method instead. The value
        of the AccessMask property is set to NULL."
    ::= { win32ShareEntry 2 }

osshAllowMaximum  OBJECT-TYPE
    SYNTAX     TruthValue
    MAX-ACCESS read-only
    STATUS     current
    DESCRIPTION
        "Number of concurrent users for this resource has
        been limited. If TRUE, the value in the
        MaximumAllowed property is ignored."
    ::= { win32ShareEntry 3 }

osshCaption  OBJECT-TYPE
    SYNTAX     WtcsDisplayString
    MAX-ACCESS read-only
    STATUS     current
    DESCRIPTION
        "Short description (one-line string) of the
        object."
    ::= { win32ShareEntry 4 }

osshDescription  OBJECT-TYPE
    SYNTAX     WtcsDisplayString
    MAX-ACCESS read-only
    STATUS     current
    DESCRIPTION
        "Description of the object."
    ::= { win32ShareEntry 5 }

osshInstallDate  OBJECT-TYPE
    SYNTAX     DateAndTime
    MAX-ACCESS read-only
    STATUS     current
    DESCRIPTION
        "Object was installed. This property does not need
        a value to indicate that the object is installed."
    ::= { win32ShareEntry 6 }

osshMaximumAllowed  OBJECT-TYPE
    SYNTAX     Gauge32
    MAX-ACCESS read-only
    STATUS     current
    DESCRIPTION
        "Limit on the maximum number of users allowed to
        use this resource concurrently. The value is only
        valid if the AllowMaximum property is set to FALSE"
    ::= { win32ShareEntry 7 }

osshName  OBJECT-TYPE
    SYNTAX     WtcsDisplayString
    MAX-ACCESS read-only
    STATUS     current
    DESCRIPTION
        "Alias given to a path set up as a share on a
        Windows system.
        Example: 'public'"
    ::= { win32ShareEntry 8 }

osshPath  OBJECT-TYPE
    SYNTAX     WtcsDisplayString
    MAX-ACCESS read-only
    STATUS     current
    DESCRIPTION
        "Local path of the Windows share.
        Example: 'C:\Program Files'"
    ::= { win32ShareEntry 9 }

osshStatus  OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may be functioning properly but
        predicting a failure in the near future).
        Non-operational statuses include: 'Error',
        'Starting', 'Stopping', and 'Service'. The latter,
        'Service', could apply during mirror-resilvering of
        a disk, reload of a user permissions list, or other
        administrative work. Not all such work is on-line,
        yet the managed element is neither 'OK' nor in one
        of the other states."
    ::= { win32ShareEntry 10 }

osshType  OBJECT-TYPE
    SYNTAX     Gauge32
    MAX-ACCESS read-only
    STATUS     current
    DESCRIPTION
        "Type of resource being shared. Types include disk
        drives, print queues, interprocess communications
        (IPC), and general devices.
        
        Value Meaning
        0 Disk Drive
        1 Print Queue
        2 Device
        3 IPC
        2147483648 Disk Drive Admin
        2147483649 Print Queue Admin
        2147483650 Device Admin
        2147483651 IPC Admin"
    ::= { win32ShareEntry 11 }

wmiStorage OBJECT-IDENTITY
    STATUS     current
    DESCRIPTION
        "The Storage subcategory groups classes that
        represent storage information."
    ::= { wmiOperatingSystem 13 }

win32ShadowContextTable OBJECT-TYPE
    SYNTAX     SEQUENCE OF Win32ShadowContextEntry
    MAX-ACCESS not-accessible
    STATUS     current
    DESCRIPTION
        "The Win32_ShadowContext class specifies how a
        shadow copy is to be created, queried, or deleted,
        and the degree of writer involvement.
        
        Windows XP and earlier:  This class is not
        available."
    ::= { wmiStorage 1 }

win32ShadowContextEntry OBJECT-TYPE
    SYNTAX     Win32ShadowContextEntry
    MAX-ACCESS not-accessible
    STATUS     current
    DESCRIPTION
        "None"
    INDEX      { osscxIndex }
    ::= { win32ShadowContextTable 1 }

Win32ShadowContextEntry ::= SEQUENCE {
    osscxIndex Integer32,
    osscxClientAccessible  TruthValue,
    osscxDifferential  TruthValue,
    osscxExposedLocally  TruthValue,
    osscxExposedRemotely  TruthValue,
    osscxHardwareAssisted  TruthValue,
    osscxImported  TruthValue,
    osscxName  WtcsDisplayString,
    osscxNoAutoRelease  TruthValue,
    osscxNotSurfaced  TruthValue,
    osscxNoWriters  TruthValue,
    osscxPersistent  TruthValue,
    osscxPlex  TruthValue,
    osscxTransportable  TruthValue
}

osscxIndex OBJECT-TYPE
    SYNTAX     Integer32 (1..2147483647)
    MAX-ACCESS read-only
    STATUS     current
    DESCRIPTION
        "The value of this object uniquely identifies the
        instance entry for this class."
    ::= { win32ShadowContextEntry 1 }

osscxClientAccessible  OBJECT-TYPE
    SYNTAX     TruthValue
    MAX-ACCESS read-only
    STATUS     current
    DESCRIPTION
        "If true, the shadow copy is created by the Windows
        Previous Versions component."
    ::= { win32ShadowContextEntry 2 }

osscxDifferential  OBJECT-TYPE
    SYNTAX     TruthValue
    MAX-ACCESS read-only
    STATUS     current
    DESCRIPTION
        "If true, the shadow copy is created by a
        differential shadow copy provider. The provider can
        be implemented in hardware or software."
    ::= { win32ShadowContextEntry 3 }

osscxExposedLocally  OBJECT-TYPE
    SYNTAX     TruthValue
    MAX-ACCESS read-only
    STATUS     current
    DESCRIPTION
        "If true, the shadow copy is exposed on a remote
        computer with a network share. If both
        ExposedLocally and ExposedRemotely are false, the
        shadow copy is hidden."
    ::= { win32ShadowContextEntry 4 }

osscxExposedRemotely  OBJECT-TYPE
    SYNTAX     TruthValue
    MAX-ACCESS read-only
    STATUS     current
    DESCRIPTION
        "If true, the shadow copy is exposed on a remote
        computer with a network share. If both
        ExposedRemotely and ExposedLocally are false, the
        shadow copy is hidden."
    ::= { win32ShadowContextEntry 5 }

osscxHardwareAssisted  OBJECT-TYPE
    SYNTAX     TruthValue
    MAX-ACCESS read-only
    STATUS     current
    DESCRIPTION
        "If true, the shadow copy is created by a hardware
        shadow copy provider."
    ::= { win32ShadowContextEntry 6 }

osscxImported  OBJECT-TYPE
    SYNTAX     TruthValue
    MAX-ACCESS read-only
    STATUS     current
    DESCRIPTION
        "If true, the shadow copy is imported to a computer
        by using the Import method not created by using the
        Create method."
    ::= { win32ShadowContextEntry 7 }

osscxName  OBJECT-TYPE
    SYNTAX     WtcsDisplayString
    MAX-ACCESS read-only
    STATUS     current
    DESCRIPTION
        "Name of the context."
    ::= { win32ShadowContextEntry 8 }

osscxNoAutoRelease  OBJECT-TYPE
    SYNTAX     TruthValue
    MAX-ACCESS read-only
    STATUS     current
    DESCRIPTION
        "If true, the shadow copy is retained after the
        requestor process ends. If false, the shadow copy
        is automatically deleted when the shadow copy
        requestor process ends. "
    ::= { win32ShadowContextEntry 9 }

osscxNotSurfaced  OBJECT-TYPE
    SYNTAX     TruthValue
    MAX-ACCESS read-only
    STATUS     current
    DESCRIPTION
        "If true, the shadow copy is not currently in the
        device namespace of the local computer."
    ::= { win32ShadowContextEntry 10 }

osscxNoWriters  OBJECT-TYPE
    SYNTAX     TruthValue
    MAX-ACCESS read-only
    STATUS     current
    DESCRIPTION
        "If true, the shadow copy is created without
        involvement of shadow copy writer components."
    ::= { win32ShadowContextEntry 11 }

osscxPersistent  OBJECT-TYPE
    SYNTAX     TruthValue
    MAX-ACCESS read-only
    STATUS     current
    DESCRIPTION
        "If true, the shadow copy persists across reboots."
    ::= { win32ShadowContextEntry 12 }

osscxPlex  OBJECT-TYPE
    SYNTAX     TruthValue
    MAX-ACCESS read-only
    STATUS     current
    DESCRIPTION
        "If true, the shadow copy is created by a split
        mirror shadow copy provider."
    ::= { win32ShadowContextEntry 13 }

osscxTransportable  OBJECT-TYPE
    SYNTAX     TruthValue
    MAX-ACCESS read-only
    STATUS     current
    DESCRIPTION
        "If true, the shadow copy can be surfaced on
        another computer. If false, and the volumes are
        surfaced locally, it may not be possible to surface
        them later on a different computer."
    ::= { win32ShadowContextEntry 14 }

win32ShadowCopyTable OBJECT-TYPE
    SYNTAX     SEQUENCE OF Win32ShadowCopyEntry
    MAX-ACCESS not-accessible
    STATUS     current
    DESCRIPTION
        "The Win32_ShadowCopy class is a storage extent
        that represents a duplicate copy of the original
        volume at a previous time.
        
        Windows XP and earlier:  This class is not
        available."
    ::= { wmiStorage 2 }

win32ShadowCopyEntry OBJECT-TYPE
    SYNTAX     Win32ShadowCopyEntry
    MAX-ACCESS not-accessible
    STATUS     current
    DESCRIPTION
        "None"
    INDEX      { osscpIndex }
    ::= { win32ShadowCopyTable 1 }

Win32ShadowCopyEntry ::= SEQUENCE {
    osscpIndex Integer32,
    osscpClientAccessible  TruthValue,
    osscpCount  Gauge32,
    osscpDeviceObject  WtcsDisplayString,
    osscpDifferential  TruthValue,
    osscpExposedLocally  TruthValue,
    osscpExposedName  WtcsDisplayString,
    osscpExposedRemotely  TruthValue,
    osscpHardwareAssisted  TruthValue,
    osscpID  WtcsDisplayString,
    osscpImported  TruthValue,
    osscpNoAutoRelease  TruthValue,
    osscpNotSurfaced  TruthValue,
    osscpNoWriters  TruthValue,
    osscpOriginatingMachine  WtcsDisplayString,
    osscpPersistent  TruthValue,
    osscpPlex  TruthValue,
    osscpProviderID  WtcsDisplayString,
    osscpServiceMachine  WtcsDisplayString,
    osscpSetID  WtcsDisplayString,
    osscpState  INTEGER,
    osscpTransportable  TruthValue,
    osscpVolumeName  WtcsDisplayString
}

osscpIndex OBJECT-TYPE
    SYNTAX     Integer32 (1..2147483647)
    MAX-ACCESS read-only
    STATUS     current
    DESCRIPTION
        "The value of this object uniquely identifies the
        instance entry for this class."
    ::= { win32ShadowCopyEntry 1 }

osscpClientAccessible  OBJECT-TYPE
    SYNTAX     TruthValue
    MAX-ACCESS read-only
    STATUS     current
    DESCRIPTION
        "If true, the shadow copy is created by the Windows
        Previous Versions component."
    ::= { win32ShadowCopyEntry 2 }

osscpCount  OBJECT-TYPE
    SYNTAX     Gauge32
    MAX-ACCESS read-only
    STATUS     current
    DESCRIPTION
        "Number of shadow copies in a shadow copy set to
        which a shadow copy belongs."
    ::= { win32ShadowCopyEntry 3 }

osscpDeviceObject  OBJECT-TYPE
    SYNTAX     WtcsDisplayString
    MAX-ACCESS read-only
    STATUS     current
    DESCRIPTION
        "Windows object manager name for an underlying
        storage device that supports the original volume."
    ::= { win32ShadowCopyEntry 4 }

osscpDifferential  OBJECT-TYPE
    SYNTAX     TruthValue
    MAX-ACCESS read-only
    STATUS     current
    DESCRIPTION
        "If true, the shadow copy is created by a
        differential shadow copy provider. The provider can
        be implemented in hardware or software."
    ::= { win32ShadowCopyEntry 5 }

osscpExposedLocally  OBJECT-TYPE
    SYNTAX     TruthValue
    MAX-ACCESS read-only
    STATUS     current
    DESCRIPTION
        "If true, the shadow copy is exposed on the local
        computer with a drive letter or mount point. If
        ExposedLocally and ExposedRemotely are not set, the
        shadow copy is hidden."
    ::= { win32ShadowCopyEntry 6 }

osscpExposedName  OBJECT-TYPE
    SYNTAX     WtcsDisplayString
    MAX-ACCESS read-only
    STATUS     current
    DESCRIPTION
        "File system name of a shadow copy when it is
        exposed. The ExposedName property might contain a
        drive letter or mount point. The ExposedName
        property is NULL when a shadow copy is hidden or
        otherwise not exposed."
    ::= { win32ShadowCopyEntry 7 }

osscpExposedRemotely  OBJECT-TYPE
    SYNTAX     TruthValue
    MAX-ACCESS read-only
    STATUS     current
    DESCRIPTION
        "If true, the shadow copy is exposed on a remote
        computer with a network share. If ExposedRemotely
        and ExposedLocally are not set, the shadow copy is
        hidden."
    ::= { win32ShadowCopyEntry 8 }

osscpHardwareAssisted  OBJECT-TYPE
    SYNTAX     TruthValue
    MAX-ACCESS read-only
    STATUS     current
    DESCRIPTION
        "If true, the shadow copy is created by a hardware
        shadow copy provider."
    ::= { win32ShadowCopyEntry 9 }

osscpID  OBJECT-TYPE
    SYNTAX     WtcsDisplayString
    MAX-ACCESS read-only
    STATUS     current
    DESCRIPTION
        "Unique identifier for a shadow copy on the
        system."
    ::= { win32ShadowCopyEntry 10 }

osscpImported  OBJECT-TYPE
    SYNTAX     TruthValue
    MAX-ACCESS read-only
    STATUS     current
    DESCRIPTION
        "If true, the shadow copy is imported to a computer
        by using the Import method not created by using the
        Create method."
    ::= { win32ShadowCopyEntry 11 }

osscpNoAutoRelease  OBJECT-TYPE
    SYNTAX     TruthValue
    MAX-ACCESS read-only
    STATUS     current
    DESCRIPTION
        "If true, the shadow copy is retained after the
        requestor process ends. If false, the shadow copy
        is automatically deleted when the requestor process
        ends."
    ::= { win32ShadowCopyEntry 12 }

osscpNotSurfaced  OBJECT-TYPE
    SYNTAX     TruthValue
    MAX-ACCESS read-only
    STATUS     current
    DESCRIPTION
        "If true, the shadow copy is not currently in the
        device namespace of a local computer."
    ::= { win32ShadowCopyEntry 13 }

osscpNoWriters  OBJECT-TYPE
    SYNTAX     TruthValue
    MAX-ACCESS read-only
    STATUS     current
    DESCRIPTION
        "If true, the shadow copy is created with the
        involvement of the shadow copy writer components."
    ::= { win32ShadowCopyEntry 14 }

osscpOriginatingMachine  OBJECT-TYPE
    SYNTAX     WtcsDisplayString
    MAX-ACCESS read-only
    STATUS     current
    DESCRIPTION
        "Name of the computer that hosts the original
        volume."
    ::= { win32ShadowCopyEntry 15 }

osscpPersistent  OBJECT-TYPE
    SYNTAX     TruthValue
    MAX-ACCESS read-only
    STATUS     current
    DESCRIPTION
        "If true, the shadow copy is persistent across
        reboots."
    ::= { win32ShadowCopyEntry 16 }

osscpPlex  OBJECT-TYPE
    SYNTAX     TruthValue
    MAX-ACCESS read-only
    STATUS     current
    DESCRIPTION
        "If true, the shadow copy is created by a split
        mirror shadow copy provider. The provider can be
        implemented in hardware or software."
    ::= { win32ShadowCopyEntry 17 }

osscpProviderID  OBJECT-TYPE
    SYNTAX     WtcsDisplayString
    MAX-ACCESS read-only
    STATUS     current
    DESCRIPTION
        "Unique identifier for a shadow provider that
        creates a shadow."
    ::= { win32ShadowCopyEntry 18 }

osscpServiceMachine  OBJECT-TYPE
    SYNTAX     WtcsDisplayString
    MAX-ACCESS read-only
    STATUS     current
    DESCRIPTION
        "Name of the computer that services the shadow
        copy."
    ::= { win32ShadowCopyEntry 19 }

osscpSetID  OBJECT-TYPE
    SYNTAX     WtcsDisplayString
    MAX-ACCESS read-only
    STATUS     current
    DESCRIPTION
        "Unique identifier for a shadow copy set to which
        the shadow belongs."
    ::= { win32ShadowCopyEntry 20 }

osscpState  OBJECT-TYPE
    SYNTAX     INTEGER {
        unknown(0),
        preparing(1),
        processingPrepare(2),
        prepared(3),
        processingPrecommit(4),
        precommitted(5),
        processingCommit(6),
        committed(7),
        processingPostcommit(8),
        created(9),
        aborted(10),
        deleted(11),
        count(12)
    }
    MAX-ACCESS read-only
    STATUS     current
    DESCRIPTION
        "Current state of a shadow copy."
    ::= { win32ShadowCopyEntry 21 }

osscpTransportable  OBJECT-TYPE
    SYNTAX     TruthValue
    MAX-ACCESS read-only
    STATUS     current
    DESCRIPTION
        "If true, the shadow copy can be surfaced on
        another computer. If false, and the volumes are
        surfaced locally, it may not be possible to surface
        them later on a different computer."
    ::= { win32ShadowCopyEntry 22 }

osscpVolumeName  OBJECT-TYPE
    SYNTAX     WtcsDisplayString
    MAX-ACCESS read-only
    STATUS     current
    DESCRIPTION
        "Name of the original volume for which a shadow
        copy is made."
    ::= { win32ShadowCopyEntry 23 }

win32ShadowProviderTable OBJECT-TYPE
    SYNTAX     SEQUENCE OF Win32ShadowProviderEntry
    MAX-ACCESS not-accessible
    STATUS     current
    DESCRIPTION
        "Typically, the Win32_ShadowProvider class
        represents a component that is a combination of
        user-mode and kernel or firmware implementation,
        that creates and represents volume shadow copies.
        
        Windows XP and earlier:  This class is not
        available."
    ::= { wmiStorage 3 }

win32ShadowProviderEntry OBJECT-TYPE
    SYNTAX     Win32ShadowProviderEntry
    MAX-ACCESS not-accessible
    STATUS     current
    DESCRIPTION
        "None"
    INDEX      { osspIndex }
    ::= { win32ShadowProviderTable 1 }

Win32ShadowProviderEntry ::= SEQUENCE {
    osspIndex Integer32,
    osspCLSID  WtcsDisplayString,
    osspID  WtcsDisplayString,
    osspName  WtcsDisplayString,
    osspType  INTEGER,
    osspVersion  WtcsDisplayString,
    osspVersionID  WtcsDisplayString
}

osspIndex OBJECT-TYPE
    SYNTAX     Integer32 (1..2147483647)
    MAX-ACCESS read-only
    STATUS     current
    DESCRIPTION
        "The value of this object uniquely identifies the
        instance entry for this class."
    ::= { win32ShadowProviderEntry 1 }

osspCLSID  OBJECT-TYPE
    SYNTAX     WtcsDisplayString
    MAX-ACCESS read-only
    STATUS     current
    DESCRIPTION
        "Common Object Model (COM) class ID registered for
        a shadow provider."
    ::= { win32ShadowProviderEntry 2 }

osspID  OBJECT-TYPE
    SYNTAX     WtcsDisplayString
    MAX-ACCESS read-only
    STATUS     current
    DESCRIPTION
        "Uniquely identifies the shadow provider on a
        system."
    ::= { win32ShadowProviderEntry 3 }

osspName  OBJECT-TYPE
    SYNTAX     WtcsDisplayString
    MAX-ACCESS read-only
    STATUS     current
    DESCRIPTION
        "Descriptive name of a provider."
    ::= { win32ShadowProviderEntry 4 }

osspType  OBJECT-TYPE
    SYNTAX     INTEGER {
        unknown(0),
        system(1),
        software(2),
        hardware(3)
    }
    MAX-ACCESS read-only
    STATUS     current
    DESCRIPTION
        "Specifies the class to which a shadow provider
        belongs."
    ::= { win32ShadowProviderEntry 5 }

osspVersion  OBJECT-TYPE
    SYNTAX     WtcsDisplayString
    MAX-ACCESS read-only
    STATUS     current
    DESCRIPTION
        "Text representation of a shadow provider version."
    ::= { win32ShadowProviderEntry 6 }

osspVersionID  OBJECT-TYPE
    SYNTAX     WtcsDisplayString
    MAX-ACCESS read-only
    STATUS     current
    DESCRIPTION
        "Numeric representation of a shadow provider
        version."
    ::= { win32ShadowProviderEntry 7 }

wmiEventLog OBJECT-IDENTITY
    STATUS     current
    DESCRIPTION
        "The Windows NT Event Log subcategory groups
        classes that represent events, event log entries,
        event log configuration settings, and so on."
    ::= { wmiOperatingSystem 14 }

win32NTEventlogFileTable OBJECT-TYPE
    SYNTAX     SEQUENCE OF Win32NTEventlogFileEntry
    MAX-ACCESS not-accessible
    STATUS     current
    DESCRIPTION
        "The Win32_NTEventlogFile WMI class represents a
        logical file or directory of Windows NT events. The
        file is also known as the event log."
    ::= { wmiEventLog 1 }

win32NTEventlogFileEntry OBJECT-TYPE
    SYNTAX     Win32NTEventlogFileEntry
    MAX-ACCESS not-accessible
    STATUS     current
    DESCRIPTION
        "None"
    INDEX      { oselfIndex }
    ::= { win32NTEventlogFileTable 1 }

Win32NTEventlogFileEntry ::= SEQUENCE {
    oselfIndex Integer32,
    oselfAccessMask WtcsDisplayString,
    oselfArchive TruthValue,
    oselfCaption WtcsDisplayString,
    oselfCompressed TruthValue,
    oselfCompressionMethod WtcsDisplayString,
    oselfCreationClassName WtcsDisplayString,
    oselfCreationDate DateAndTime,
    oselfCSCreationClassName WtcsDisplayString,
    oselfCSName WtcsDisplayString,
    oselfDescription WtcsDisplayString,
    oselfDrive WtcsDisplayString,
    oselfEightDotThreeFileName WtcsDisplayString,
    oselfEncrypted TruthValue,
    oselfEncryptionMethod WtcsDisplayString,
    oselfExtension WtcsDisplayString,
    oselfFileName WtcsDisplayString,
    oselfFileSize Gauge32,
    oselfFileType WtcsDisplayString,
    oselfFSCreationClassName WtcsDisplayString,
    oselfFSName WtcsDisplayString,
    oselfHidden TruthValue,
    oselfInstallDate DateAndTime,
    oselfInUseCount Gauge32,
    oselfLastAccessed DateAndTime,
    oselfLastModified DateAndTime,
    oselfLogFileName WtcsDisplayString,
    oselfManufacturer WtcsDisplayString,
    oselfMaxFileSize Gauge32,
    oselfName WtcsDisplayString,
    oselfNumberOfRecords Gauge32,
    oselfOverwriteOutDated Gauge32,
    oselfOverWritePolicy WtcsDisplayString,
    oselfPath WtcsDisplayString,
    oselfReadable TruthValue,
    oselfSources WtcsDisplayString,
    oselfStatus INTEGER,
    oselfSystem TruthValue,
    oselfVersion WtcsDisplayString,
    oselfWriteable TruthValue
}

oselfIndex OBJECT-TYPE
    SYNTAX     Integer32 (1..2147483647)
    MAX-ACCESS read-only
    STATUS     current
    DESCRIPTION
        "The value of this object uniquely identifies the
        instance entry for this class."
    ::= { win32NTEventlogFileEntry 1 }

oselfAccessMask OBJECT-TYPE
    SYNTAX     WtcsDisplayString
    MAX-ACCESS read-only
    STATUS     current
    DESCRIPTION
        "List of access rights to the given file or
        directory of Windows NT events held by the user or
        group on whose behalf the instance is returned."
    ::= { win32NTEventlogFileEntry 2 }

oselfArchive OBJECT-TYPE
    SYNTAX     TruthValue
    MAX-ACCESS read-only
    STATUS     current
    DESCRIPTION
        "If True, a file of Windows NT events should be
        archived."
    ::= { win32NTEventlogFileEntry 3 }

oselfCaption OBJECT-TYPE
    SYNTAX     WtcsDisplayString
    MAX-ACCESS read-only
    STATUS     current
    DESCRIPTION
        "Short description (one-line string) of the
        object."
    ::= { win32NTEventlogFileEntry 4 }

oselfCompressed OBJECT-TYPE
    SYNTAX     TruthValue
    MAX-ACCESS read-only
    STATUS     current
    DESCRIPTION
        "If True, a file of Windows NT events is
        compressed."
    ::= { win32NTEventlogFileEntry 5 }

oselfCompressionMethod OBJECT-TYPE
    SYNTAX     WtcsDisplayString
    MAX-ACCESS read-only
    STATUS     current
    DESCRIPTION
        "Algorithm or tool used to compress the logical
        file of Windows NT events. If it is not possible
        (or not desired) to describe the compression scheme
        (perhaps because it is not known), use the
        following words:
        
        'Unknown' to represent that it is not known whether
        the logical file is compressed. 
        'Compressed' to represent that the file is
        compressed but either its compression scheme is not
        known or not disclosed. 
        'Not Compressed' to represent that the logical file
        is not compressed. 
        "
    ::= { win32NTEventlogFileEntry 6 }

oselfCreationClassName OBJECT-TYPE
    SYNTAX     WtcsDisplayString
    MAX-ACCESS read-only
    STATUS     current
    DESCRIPTION
        "Name of the first concrete class to appear in the
        inheritance chain used in the creation of an
        instance. When used with the other key properties
        of the class, the property allows all instances of
        this class and its subclasses to be uniquely
        identified."
    ::= { win32NTEventlogFileEntry 7 }

oselfCreationDate OBJECT-TYPE
    SYNTAX     DateAndTime
    MAX-ACCESS read-only
    STATUS     current
    DESCRIPTION
        "File of Windows NT events was created."
    ::= { win32NTEventlogFileEntry 8 }

oselfCSCreationClassName OBJECT-TYPE
    SYNTAX     WtcsDisplayString
    MAX-ACCESS read-only
    STATUS     current
    DESCRIPTION
        "Class of the computer system."
    ::= { win32NTEventlogFileEntry 9 }

oselfCSName OBJECT-TYPE
    SYNTAX     WtcsDisplayString
    MAX-ACCESS read-only
    STATUS     current
    DESCRIPTION
        "Name of the computer system."
    ::= { win32NTEventlogFileEntry 10 }

oselfDescription OBJECT-TYPE
    SYNTAX     WtcsDisplayString
    MAX-ACCESS read-only
    STATUS     current
    DESCRIPTION
        "Description of the object."
    ::= { win32NTEventlogFileEntry 11 }

oselfDrive OBJECT-TYPE
    SYNTAX     WtcsDisplayString
    MAX-ACCESS read-only
    STATUS     current
    DESCRIPTION
        "Drive letter (including colon) of the file of
        Windows NT events. Example: 'c:'"
    ::= { win32NTEventlogFileEntry 12 }

oselfEightDotThreeFileName OBJECT-TYPE
    SYNTAX     WtcsDisplayString
    MAX-ACCESS read-only
    STATUS     current
    DESCRIPTION
        "DOS-compatible file name for this file of Windows
        NT events. Example: 'c:\progra~1'"
    ::= { win32NTEventlogFileEntry 13 }

oselfEncrypted OBJECT-TYPE
    SYNTAX     TruthValue
    MAX-ACCESS read-only
    STATUS     current
    DESCRIPTION
        "File of Windows NT events is encrypted."
    ::= { win32NTEventlogFileEntry 14 }

oselfEncryptionMethod OBJECT-TYPE
    SYNTAX     WtcsDisplayString
    MAX-ACCESS read-only
    STATUS     current
    DESCRIPTION
        "Algorithm or tool used to encrypt the logical
        file. If it is not possible (or not desired) to
        describe the encryption scheme (perhaps for
        security reasons), use the following words:
        
        'Unknown' to represent that it is not known whether
        the logical file is encrypted. 
        'Encrypted' to represent that the file is encrypted
        but either its encryption scheme is not known or
        not disclosed. 
        'Not Encrypted' to represent that the logical file
        is not encrypted."
    ::= { win32NTEventlogFileEntry 15 }

oselfExtension OBJECT-TYPE
    SYNTAX     WtcsDisplayString
    MAX-ACCESS read-only
    STATUS     current
    DESCRIPTION
        "File extension (without the dot) of Windows NT
        events. Example: 'txt', 'mof', 'mdb'"
    ::= { win32NTEventlogFileEntry 16 }

oselfFileName OBJECT-TYPE
    SYNTAX     WtcsDisplayString
    MAX-ACCESS read-only
    STATUS     current
    DESCRIPTION
        "File name (without extension) of the file of
        Windows NT events. Example: 'autoexec'"
    ::= { win32NTEventlogFileEntry 17 }

oselfFileSize OBJECT-TYPE
    SYNTAX     Gauge32
    MAX-ACCESS read-only
    STATUS     current
    DESCRIPTION
        "Size of the file of Windows NT events (in bytes)."
    ::= { win32NTEventlogFileEntry 18 }

oselfFileType OBJECT-TYPE
    SYNTAX     WtcsDisplayString
    MAX-ACCESS read-only
    STATUS     current
    DESCRIPTION
        "File type (indicated by the Extension property)."
    ::= { win32NTEventlogFileEntry 19 }

oselfFSCreationClassName OBJECT-TYPE
    SYNTAX     WtcsDisplayString
    MAX-ACCESS read-only
    STATUS     current
    DESCRIPTION
        "Class of the file system."
    ::= { win32NTEventlogFileEntry 20 }

oselfFSName OBJECT-TYPE
    SYNTAX     WtcsDisplayString
    MAX-ACCESS read-only
    STATUS     current
    DESCRIPTION
        "Name of the file system."
    ::= { win32NTEventlogFileEntry 21 }

oselfHidden OBJECT-TYPE
    SYNTAX     TruthValue
    MAX-ACCESS read-only
    STATUS     current
    DESCRIPTION
        "If True, a file of Windows NT events is hidden."
    ::= { win32NTEventlogFileEntry 22 }

oselfInstallDate OBJECT-TYPE
    SYNTAX     DateAndTime
    MAX-ACCESS read-only
    STATUS     current
    DESCRIPTION
        "Object is installed. This property does not need a
        value to indicate that the object is installed."
    ::= { win32NTEventlogFileEntry 23 }

oselfInUseCount OBJECT-TYPE
    SYNTAX     Gauge32
    MAX-ACCESS read-only
    STATUS     current
    DESCRIPTION
        "Number of 'file opens' that are currently active
        against the file of Windows NT events."
    ::= { win32NTEventlogFileEntry 24 }

oselfLastAccessed OBJECT-TYPE
    SYNTAX     DateAndTime
    MAX-ACCESS read-only
    STATUS     current
    DESCRIPTION
        "File of Windows NT events was last accessed."
    ::= { win32NTEventlogFileEntry 25 }

oselfLastModified OBJECT-TYPE
    SYNTAX     DateAndTime
    MAX-ACCESS read-only
    STATUS     current
    DESCRIPTION
        "File of Windows NT events was last modified."
    ::= { win32NTEventlogFileEntry 26 }

oselfLogFileName OBJECT-TYPE
    SYNTAX     WtcsDisplayString
    MAX-ACCESS read-only
    STATUS     current
    DESCRIPTION
        "Name of the file of Windows NT events. Standard
        log file names include Application, System, and
        Security."
    ::= { win32NTEventlogFileEntry 27 }

oselfManufacturer OBJECT-TYPE
    SYNTAX     WtcsDisplayString
    MAX-ACCESS read-only
    STATUS     current
    DESCRIPTION
        "Manufacturer from version resource, if one is
        present."
    ::= { win32NTEventlogFileEntry 28 }

oselfMaxFileSize OBJECT-TYPE
    SYNTAX     Gauge32
    MAX-ACCESS read-only
    STATUS     current
    DESCRIPTION
        "Maximum size (in bytes) permitted for the file of
        Windows NT events. If the file exceeds its maximum
        size, its contents are moved to another file and
        the primary file is emptied. A value of zero
        indicates no size limit. WMI retrieves the Maxsize
        value from the Event Log Service registry values."
    ::= { win32NTEventlogFileEntry 29 }

oselfName OBJECT-TYPE
    SYNTAX     WtcsDisplayString
    MAX-ACCESS read-only
    STATUS     current
    DESCRIPTION
        "Inherited name that serves as a key of a logical
        file instance of Windows NT events within a file
        system. Full path names should be provided.
        Example: 'c:\winnt\system\win.ini'"
    ::= { win32NTEventlogFileEntry 30 }

oselfNumberOfRecords OBJECT-TYPE
    SYNTAX     Gauge32
    MAX-ACCESS read-only
    STATUS     current
    DESCRIPTION
        "Number of records in the file of Windows NT
        events. This value is determined by calling the
        Windows function GetNumberOfEventLogRecords."
    ::= { win32NTEventlogFileEntry 31 }

oselfOverwriteOutDated OBJECT-TYPE
    SYNTAX     Gauge32
    UNITS "Days"
    MAX-ACCESS read-only
    STATUS     current
    DESCRIPTION
        "Number of days after which an event can be
        overwritten.
        
        Value Meaning
        0: Any entry can be overwritten when necessary. 
        1..365: Events that have been in the log file for
        one year (365 days) or less can be overwritten. 
        4294967295: Nothing can be ever be overwritten. 
        "
    ::= { win32NTEventlogFileEntry 32 }

oselfOverWritePolicy OBJECT-TYPE
    SYNTAX     WtcsDisplayString
    MAX-ACCESS read-only
    STATUS     current
    DESCRIPTION
        "Current overwrite policy the Event Log service
        employs for this log file. Data can be never
        overwritten, or overwritten when necessary or when
        outdated. When data is outdated depends on the
        OverwriteOutDated value.
        
        Value Meaning 
        'WhenNeeded' The value of OverwriteOutDated equals
        0. 
        'OutDated' The value of OverwriteOutDated ranges
        from 1 to 365. 
        'Never' The value of OverwriteOutDated equals
        4294967295."
    ::= { win32NTEventlogFileEntry 33 }

oselfPath OBJECT-TYPE
    SYNTAX     WtcsDisplayString
    MAX-ACCESS read-only
    STATUS     current
    DESCRIPTION
        "Path of the file of Windows NT event. This
        includes leading and trailing backslashes. Example:
        '\windows\system\'"
    ::= { win32NTEventlogFileEntry 34 }

oselfReadable OBJECT-TYPE
    SYNTAX     TruthValue
    MAX-ACCESS read-only
    STATUS     current
    DESCRIPTION
        "If True, a file of Windows NT event can be read."
    ::= { win32NTEventlogFileEntry 35 }

oselfSources OBJECT-TYPE
    SYNTAX     WtcsDisplayString
    MAX-ACCESS read-only
    STATUS     current
    DESCRIPTION
        "List of applications that are registered to log
        into this log file."
    ::= { win32NTEventlogFileEntry 36 }

oselfStatus OBJECT-TYPE
    SYNTAX     INTEGER {
        ok(1),
        error(2),
        degraded(3),
        unknown(4),
        predFail(5),
        starting(6),
        stopping(7),
        service(8),
        stressed(9),
        nonRecover(10),
        noContact(11),
        lostComm(12)
    }
    MAX-ACCESS read-only
    STATUS     current
    DESCRIPTION
        "Current status of the object. Various operational
        and non-operational statuses can be defined.
        Operational statuses include: 'OK', 'Degraded', and
        'Pred Fail' (an element, such as a SMART-enabled
        hard drive, may function properly but predicts a
        failure in the near future). Non-operational
        statuses include: 'Error', 'Starting', 'Stopping',
        and 'Service'. The 'Service' status can apply
        during mirror-resilvering of a disk, reload of a
        user permissions list, or other administrative
        work. Not all such work is online, yet the managed
        element is neither 'OK' nor in one of the other
        states.
        
        Values are:
        
        'OK'
        'Error'
        'Degraded'
        'Unknown'
        'Pred Fail'
        'Starting'
        'Stopping'
        'Service'
        'Stressed'
        'NonRecover'
        'No Contact'
        'Lost Comm'"
    ::= { win32NTEventlogFileEntry 37 }

oselfSystem OBJECT-TYPE
    SYNTAX     TruthValue
    MAX-ACCESS read-only
    STATUS     current
    DESCRIPTION
        "If True, a file of Windows NT event is a system
        file."
    ::= { win32NTEventlogFileEntry 38 }

oselfVersion OBJECT-TYPE
    SYNTAX     WtcsDisplayString
    MAX-ACCESS read-only
    STATUS     current
    DESCRIPTION
        "Version string from version resource if one is
        present."
    ::= { win32NTEventlogFileEntry 39 }

oselfWriteable OBJECT-TYPE
    SYNTAX     TruthValue
    MAX-ACCESS read-only
    STATUS     current
    DESCRIPTION
        "If True, a file of Windows NT event can be
        written."
    ::= { win32NTEventlogFileEntry 40 }

win32NTLogEventTable OBJECT-TYPE
    SYNTAX     SEQUENCE OF Win32NTLogEventEntry
    MAX-ACCESS not-accessible
    STATUS     current
    DESCRIPTION
        "The Win32_NTLogEvent WMI class is used to
        translate instances from the Windows NT event log.
        An application must have SeSecurityPrivilege to
        receive events from the security event log,
        otherwise 'Access Denied' is returned to the
        application."
    ::= { wmiEventLog 2 }

win32NTLogEventEntry OBJECT-TYPE
    SYNTAX     Win32NTLogEventEntry
    MAX-ACCESS not-accessible
    STATUS     current
    DESCRIPTION
        "None"
    INDEX      { oselIndex }
    ::= { win32NTLogEventTable 1 }

Win32NTLogEventEntry ::= SEQUENCE {
    oselIndex Integer32,
    oselCategory Gauge32,
    oselCategoryString WtcsDisplayString,
    oselComputerName WtcsDisplayString,
    oselData WtcsDisplayString,
    oselEventCode Gauge32,
    oselEventIdentifier Gauge32,
    oselEventType INTEGER,
    oselInsertionStrings WtcsDisplayString,
    oselLogfile WtcsDisplayString,
    oselMessage WtcsDisplayString,
    oselRecordNumber Gauge32,
    oselSourceName WtcsDisplayString,
    oselTimeGenerated DateAndTime,
    oselTimeWritten DateAndTime,
    oselType WtcsDisplayString,
    oselUser WtcsDisplayString
}

oselIndex OBJECT-TYPE
    SYNTAX     Integer32 (1..2147483647)
    MAX-ACCESS read-only
    STATUS     current
    DESCRIPTION
        "The value of this object uniquely identifies the
        instance entry for this class."
    ::= { win32NTLogEventEntry 1 }

oselCategory OBJECT-TYPE
    SYNTAX     Gauge32
    MAX-ACCESS read-only
    STATUS     current
    DESCRIPTION
        "Subcategory for this event. This subcategory is
        source-specific."
    ::= { win32NTLogEventEntry 2 }

oselCategoryString OBJECT-TYPE
    SYNTAX     WtcsDisplayString
    MAX-ACCESS read-only
    STATUS     current
    DESCRIPTION
        "Translation of the subcategory. The translation is
        source-specific."
    ::= { win32NTLogEventEntry 3 }

oselComputerName OBJECT-TYPE
    SYNTAX     WtcsDisplayString
    MAX-ACCESS read-only
    STATUS     current
    DESCRIPTION
        "Name of the computer that generated this event."
    ::= { win32NTLogEventEntry 4 }

oselData OBJECT-TYPE
    SYNTAX     WtcsDisplayString
    MAX-ACCESS read-only
    STATUS     current
    DESCRIPTION
        "List of the binary data that accompanied the
        report of the Windows NT event."
    ::= { win32NTLogEventEntry 5 }

oselEventCode OBJECT-TYPE
    SYNTAX     Gauge32
    MAX-ACCESS read-only
    STATUS     current
    DESCRIPTION
        "Value of the lower 16-bits of the EventIdentifier
        property. It is present to match the value
        displayed in the Windows NT Event Viewer. Note that
        two events from the same source may have the same
        value for this property but may have different
        severity and EventIdentifier values."
    ::= { win32NTLogEventEntry 6 }

oselEventIdentifier OBJECT-TYPE
    SYNTAX     Gauge32
    MAX-ACCESS read-only
    STATUS     current
    DESCRIPTION
        "Identifier of the event. This is specific to the
        source that generated the event log entry and is
        used, together with SourceName, to uniquely
        identify a Windows NT event type."
    ::= { win32NTLogEventEntry 7 }

oselEventType OBJECT-TYPE
    SYNTAX     INTEGER {
        error(1),
        warning(2),
        information(3),
        securityAuditSuccess(4),
        securityAuditFailure(5)
    }
    MAX-ACCESS read-only
    STATUS     current
    DESCRIPTION
        "Type of event."
    ::= { win32NTLogEventEntry 8 }

oselInsertionStrings OBJECT-TYPE
    SYNTAX     WtcsDisplayString
    MAX-ACCESS read-only
    STATUS     current
    DESCRIPTION
        "List of the insertion strings that accompanied the
        report of the Windows NT event."
    ::= { win32NTLogEventEntry 9 }

oselLogfile OBJECT-TYPE
    SYNTAX     WtcsDisplayString
    MAX-ACCESS read-only
    STATUS     current
    DESCRIPTION
        "Name of Windows NT event log file. This is used
        together with RecordNumber to uniquely identify an
        instance of this class."
    ::= { win32NTLogEventEntry 10 }

oselMessage OBJECT-TYPE
    SYNTAX     WtcsDisplayString
    MAX-ACCESS read-only
    STATUS     current
    DESCRIPTION
        "Event message as it appears in the Windows NT
        event log. This is a standard message with zero or
        more insertion strings supplied by the source of
        the Windows NT event. The insertion strings are
        inserted into the standard message in a predefined
        format. If there are no insertion strings or there
        is a problem inserting the insertion strings, only
        the standard message will be present in this
        field."
    ::= { win32NTLogEventEntry 11 }

oselRecordNumber OBJECT-TYPE
    SYNTAX     Gauge32
    MAX-ACCESS read-only
    STATUS     current
    DESCRIPTION
        "Identifies the event within the Windows NT event
        log file. This is specific to the log file and is
        used together with the log file name to uniquely
        identify an instance of this class."
    ::= { win32NTLogEventEntry 12 }

oselSourceName OBJECT-TYPE
    SYNTAX     WtcsDisplayString
    MAX-ACCESS read-only
    STATUS     current
    DESCRIPTION
        "Name of the source (application, service, driver,
        subsystem) that generated the entry. It is used,
        together with EventIdentifier to uniquely identify
        an Windows NT event type."
    ::= { win32NTLogEventEntry 13 }

oselTimeGenerated OBJECT-TYPE
    SYNTAX     DateAndTime
    MAX-ACCESS read-only
    STATUS     current
    DESCRIPTION
        "Source generated the event."
    ::= { win32NTLogEventEntry 14 }

oselTimeWritten OBJECT-TYPE
    SYNTAX     DateAndTime
    MAX-ACCESS read-only
    STATUS     current
    DESCRIPTION
        "Event was written to the logfile."
    ::= { win32NTLogEventEntry 15 }

oselType OBJECT-TYPE
    SYNTAX     WtcsDisplayString
    MAX-ACCESS read-only
    STATUS     current
    DESCRIPTION
        "Type of event. This is an enumerated string. It is
        preferable to use the EventType property rather
        than the Type property.
        
        Value Meaning 
        1 Error 
        2 Warning 
        4 Information 
        8 Security audit success 
        16 Security audit failure"
    ::= { win32NTLogEventEntry 16 }

oselUser OBJECT-TYPE
    SYNTAX     WtcsDisplayString
    MAX-ACCESS read-only
    STATUS     current
    DESCRIPTION
        "User name of the logged-on user when the event
        occurred. If the user name cannot be determined,
        this will be NULL."
    ::= { win32NTLogEventEntry 17 }

siOperatingSystemVersion OBJECT-TYPE
    SYNTAX     OCTET STRING
    MAX-ACCESS read-only
    STATUS     current
    DESCRIPTION
        "Designates the version of this SNMP Informant
        agent."
    ::= { wmiOperatingSystem 999 }

END
