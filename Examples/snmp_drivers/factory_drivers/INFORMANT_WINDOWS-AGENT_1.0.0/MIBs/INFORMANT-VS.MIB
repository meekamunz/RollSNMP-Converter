INFORMANT-VS DEFINITIONS ::= BEGIN

IMPORTS
    MODULE-IDENTITY, OBJECT-IDENTITY, OBJECT-TYPE, Gauge32, Integer32, Counter64
        FROM SNMPv2-SMI
    DateAndTime, TruthValue
        FROM SNMPv2-TC
    informant,WtcsDisplayString
        FROM WTCS;

wmiVirtualServer MODULE-IDENTITY
    LAST-UPDATED "200912110102Z"
    ORGANIZATION "Informant Systems, Inc."
    CONTACT-INFO
            "Garth Williams
             11135-23A Ave
             Edmonton, AB  T6J4W5  Canada
             Tel: +1 780 434 4113
             E-mail: garth.williams@wtcs.org"
    DESCRIPTION
            "The MIB module for informant Hyper-V WMI
            entities."
    REVISION      "200912110102Z"
    DESCRIPTION
            "Added OID 999 which gives the version of this
             agent."
    REVISION      "200705102135Z"
    DESCRIPTION
            "The initial revision of this MIB module."
    ::= { informant 24 }

vsVirtualMachineTable OBJECT-TYPE
    SYNTAX     SEQUENCE OF VSVirtualMachineEntry
    MAX-ACCESS not-accessible
    STATUS     current
    DESCRIPTION
        "The VirtualMachine WMI class allows you to obtain information
        about CPU, disk, and network usage by each virtual machine, as well
        as the number of heartbeats received."
    ::= { wmiVirtualServer 1 }

vsVirtualMachineEntry OBJECT-TYPE
    SYNTAX     VSVirtualMachineEntry
    MAX-ACCESS not-accessible
    STATUS     current
    DESCRIPTION
        "None"
    INDEX      { vsvmIndex }
    ::= { vsVirtualMachineTable 1 }

VSVirtualMachineEntry ::= SEQUENCE {
    vsvmIndex Integer32,
    vsvmName WtcsDisplayString,
    vsvmCpuUtilization Gauge32,
    vsvmDiskBytesRead Counter64,
    vsvmDiskSpaceUsed Gauge32,
    vsvmDiskSpaceUsedK Gauge32,
    vsvmDiskSpaceUsedM Gauge32,
    vsvmDiskBytesWritten Counter64,
    vsvmHeartbeatCount Counter64,
    vsvmHeartbeatInterval Gauge32,
    vsvmHeartbeatPercentage Gauge32,
    vsvmHeartbeatRate Gauge32,
    vsvmNetworkBytesSent Counter64,
    vsvmNetworkBytesReceived Counter64,
    vsvmPhysicalMemoryAllocated Gauge32,
    vsvmPhysicalMemoryAllocatedK Gauge32,
    vsvmPhysicalMemoryAllocatedM Gauge32,
    vsvmUptime Gauge32
}

vsvmIndex OBJECT-TYPE
    SYNTAX     Integer32 (1..2147483647)
    MAX-ACCESS read-only
    STATUS     current
    DESCRIPTION
        "The value of this object uniquely identifies the instance entry
        for this class."
    ::= { vsVirtualMachineEntry 1 }

vsvmName OBJECT-TYPE
    SYNTAX     WtcsDisplayString
    MAX-ACCESS read-only
    STATUS     current
    DESCRIPTION
        "Name of the virtual machine."
    ::= { vsVirtualMachineEntry 2 }

vsvmCpuUtilization OBJECT-TYPE
    SYNTAX     Gauge32
    MAX-ACCESS read-only
    STATUS     current
    DESCRIPTION
        "Percentage of CPU resources allocated to this virtual machine that
        are currently in use. A zero indicates that the virtual machine may
        not be running. A 100 indicates that the virtual machine is
        consuming all currently allocated resources."
    ::= { vsVirtualMachineEntry 3 }

vsvmDiskBytesRead OBJECT-TYPE
    SYNTAX     Counter64
    UNITS "Bytes"
    MAX-ACCESS read-only
    STATUS     current
    DESCRIPTION
        "Number of bytes read by all of the virtual hard disks assigned to
        this virtual machine since the virtual machine was last turned on."
    ::= { vsVirtualMachineEntry 4 }

vsvmDiskSpaceUsed OBJECT-TYPE
    SYNTAX     Gauge32
    UNITS "Bytes"
    MAX-ACCESS read-only
    STATUS     current
    DESCRIPTION
        "Total disk space used by this virtual machine on all of the disks
        that are assigned to it."
    ::= { vsVirtualMachineEntry 5 }

vsvmDiskSpaceUsedK OBJECT-TYPE
    SYNTAX     Gauge32
    UNITS "KiloBytes"
    MAX-ACCESS read-only
    STATUS     current
    DESCRIPTION
        "Total disk space used in kilobytes by this virtual machine on all
        of the disks that are assigned to it."
    ::= { vsVirtualMachineEntry 6 }

vsvmDiskSpaceUsedM OBJECT-TYPE
    SYNTAX     Gauge32
    UNITS "MegaBytes"
    MAX-ACCESS read-only
    STATUS     current
    DESCRIPTION
        "Total disk space used in megabytes by this virtual machine on all
        of the disks that are assigned to it."
    ::= { vsVirtualMachineEntry 7 }

vsvmDiskBytesWritten OBJECT-TYPE
    SYNTAX     Counter64
    UNITS "Bytes"
    MAX-ACCESS read-only
    STATUS     current
    DESCRIPTION
        "Number of bytes written by all virtual hard disks assigned to this
        virtual machine."
    ::= { vsVirtualMachineEntry 8 }

vsvmHeartbeatCount OBJECT-TYPE
    SYNTAX     Counter64
    MAX-ACCESS read-only
    STATUS     current
    DESCRIPTION
        "Number of heartbeats received since the virtual machine was last
        turned on."
    ::= { vsVirtualMachineEntry 9 }

vsvmHeartbeatInterval OBJECT-TYPE
    SYNTAX     Gauge32
    MAX-ACCESS read-only
    STATUS     current
    DESCRIPTION
        "Duration of the heartbeat interval in seconds. This data is used
        by the HeartbeatPercentage counter."
    ::= { vsVirtualMachineEntry 10 }

vsvmHeartbeatPercentage OBJECT-TYPE
    SYNTAX     Gauge32
    MAX-ACCESS read-only
    STATUS     current
    DESCRIPTION
        "Percentage of total expected heartbeats that have been received in
        the last heartbeat interval. A HeartbeatPercentage of zero may
        indicate a problem with the guest operating system. A number
        greater than zero, but less than 100 may indicate that a heavy
        input/output (I/O) load is causing the heartbeat not to transmit."
    ::= { vsVirtualMachineEntry 11 }

vsvmHeartbeatRate OBJECT-TYPE
    SYNTAX     Gauge32
    MAX-ACCESS read-only
    STATUS     current
    DESCRIPTION
        "The number of heartbeats expected per heartbeat interval. This
        data is used by the HeartbeatPercentage counter."
    ::= { vsVirtualMachineEntry 12 }

vsvmNetworkBytesSent OBJECT-TYPE
    SYNTAX     Counter64
    UNITS "Bytes"
    MAX-ACCESS read-only
    STATUS     current
    DESCRIPTION
        "Total bytes sent by all virtual networks assigned to this virtual
        machine. This is a cumulative total."
    ::= { vsVirtualMachineEntry 13 }

vsvmNetworkBytesReceived OBJECT-TYPE
    SYNTAX     Counter64
    UNITS "Bytes"
    MAX-ACCESS read-only
    STATUS     current
    DESCRIPTION
        "Total bytes received by all virtual networks assigned to this
        virtual machine. This is a cumulative total."
    ::= { vsVirtualMachineEntry 14 }

vsvmPhysicalMemoryAllocated OBJECT-TYPE
    SYNTAX     Gauge32
    UNITS "Bytes"
    MAX-ACCESS read-only
    STATUS     current
    DESCRIPTION
        "The system memory allocated to this virtual machine in bytes. This
        figure includes 4 MB of video RAM (VRAM). It does not include the
        additional 32 MB of 'overhead' memory used by each virtual machine
        in addition to the memory that is allocated to it. If a virtual
        machine is functioning poorly, you can check this number to make
        sure that sufficient memory is allocated."
    ::= { vsVirtualMachineEntry 15 }

vsvmPhysicalMemoryAllocatedK OBJECT-TYPE
    SYNTAX     Gauge32
    UNITS "KiloBytes"
    MAX-ACCESS read-only
    STATUS     current
    DESCRIPTION
        "The system memory allocated to this virtual machine in kilobytes.
        This figure includes 4 MB of video RAM (VRAM). It does not include
        the additional 32 MB of 'overhead' memory used by each virtual
        machine in addition to the memory that is allocated to it. If a
        virtual machine is functioning poorly, you can check this number to
        make sure that sufficient memory is allocated."
    ::= { vsVirtualMachineEntry 16 }

vsvmPhysicalMemoryAllocatedM OBJECT-TYPE
    SYNTAX     Gauge32
    UNITS "MegaBytes"
    MAX-ACCESS read-only
    STATUS     current
    DESCRIPTION
        "The system memory allocated to this virtual machine in megabytes.
        This figure includes 4 MB of video RAM (VRAM). It does not include
        the additional 32 MB of 'overhead' memory used by each virtual
        machine in addition to the memory that is allocated to it. If a
        virtual machine is functioning poorly, you can check this number to
        make sure that sufficient memory is allocated."
    ::= { vsVirtualMachineEntry 17 }

vsvmUptime OBJECT-TYPE
    SYNTAX     Gauge32
    UNITS "Seconds"
    MAX-ACCESS read-only
    STATUS     current
    DESCRIPTION
        "Number of seconds that the virtual machine has been running since
        it was last turned on."
    ::= { vsVirtualMachineEntry 18 }

vsVirtualNetworkTable OBJECT-TYPE
    SYNTAX     SEQUENCE OF VSVirtualNetworkEntry
    MAX-ACCESS not-accessible
    STATUS     current
    DESCRIPTION
        "The VirtualNetwork WMI class allows you to monitor the usage of
        each virtual network."
    ::= { wmiVirtualServer 2 }

vsVirtualNetworkEntry OBJECT-TYPE
    SYNTAX     VSVirtualNetworkEntry
    MAX-ACCESS not-accessible
    STATUS     current
    DESCRIPTION
        "None"
    INDEX      { vsvnIndex }
    ::= { vsVirtualNetworkTable 1 }

VSVirtualNetworkEntry ::= SEQUENCE {
    vsvnIndex Integer32,
    vsvnName WtcsDisplayString,
    vsvnBytesDropped Counter64,
    vsvnBytesReceived Counter64,
    vsvnBytesSent Counter64,
    vsvnPacketsDropped Counter64,
    vsvnPacketsReceived Counter64,
    vsvnPacketsSent Counter64
}

vsvnIndex OBJECT-TYPE
    SYNTAX     Integer32 (1..2147483647)
    MAX-ACCESS read-only
    STATUS     current
    DESCRIPTION
        "The value of this object uniquely identifies the instance entry
        for this class."
    ::= { vsVirtualNetworkEntry 1 }

vsvnName OBJECT-TYPE
    SYNTAX     WtcsDisplayString
    MAX-ACCESS read-only
    STATUS     current
    DESCRIPTION
        "Name of the physical network adapter to which this virtual network
        is attached."
    ::= { vsVirtualNetworkEntry 2 }

vsvnBytesDropped OBJECT-TYPE
    SYNTAX     Counter64
    UNITS "Bytes"
    MAX-ACCESS read-only
    STATUS     current
    DESCRIPTION
        "Number of bytes dropped by this virtual network. Any number above
        zero indicates a virtual network failure."
    ::= { vsVirtualNetworkEntry 3 }

vsvnBytesReceived OBJECT-TYPE
    SYNTAX     Counter64
    UNITS "Bytes"
    MAX-ACCESS read-only
    STATUS     current
    DESCRIPTION
        "Total bytes received by this virtual network since the first
        virtual machine attached to it was turned on."
    ::= { vsVirtualNetworkEntry 4 }

vsvnBytesSent OBJECT-TYPE
    SYNTAX     Counter64
    UNITS "Bytes"
    MAX-ACCESS read-only
    STATUS     current
    DESCRIPTION
        "Total bytes sent by this virtual network since the first virtual
        machine attached to it was turned on."
    ::= { vsVirtualNetworkEntry 5 }

vsvnPacketsDropped OBJECT-TYPE
    SYNTAX     Counter64
    UNITS "Packets"
    MAX-ACCESS read-only
    STATUS     current
    DESCRIPTION
        "Number of packets of data dropped by this virtual network. Any
        number above zero indicates a virtual network failure."
    ::= { vsVirtualNetworkEntry 6 }

vsvnPacketsReceived OBJECT-TYPE
    SYNTAX     Counter64
    UNITS "Packets"
    MAX-ACCESS read-only
    STATUS     current
    DESCRIPTION
        "Total packets of data received by this virtual network since the
        first virtual machine attached to it was turned on."
    ::= { vsVirtualNetworkEntry 7 }

vsvnPacketsSent OBJECT-TYPE
    SYNTAX     Counter64
    UNITS "Packets"
    MAX-ACCESS read-only
    STATUS     current
    DESCRIPTION
        "Total packets of data sent by this virtual network since the first
        virtual machine attached to it was turned on."
    ::= { vsVirtualNetworkEntry 8 }

siVirtualServerVersion OBJECT-TYPE
    SYNTAX     OCTET STRING
    MAX-ACCESS read-only
    STATUS     current
    DESCRIPTION
        "Designates the version of this SNMP Informant agent."
    ::= { wmiVirtualServer 999 }

END
