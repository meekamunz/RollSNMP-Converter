INFORMANT-HYPERV DEFINITIONS ::= BEGIN

IMPORTS
    MODULE-IDENTITY, OBJECT-IDENTITY, OBJECT-TYPE, Gauge32, Integer32
        FROM SNMPv2-SMI
    DateAndTime, TruthValue
        FROM SNMPv2-TC
    informant,WtcsDisplayString
        FROM WTCS;

informantHyperV MODULE-IDENTITY
    LAST-UPDATED "200912110102Z"
    ORGANIZATION "Informant Systems, Inc."
    CONTACT-INFO
            "Garth Williams
             11135-23A Ave
             Edmonton, AB  T6J4W5  Canada
             Tel: +1 780 434 4113
             E-mail: garth.williams.org"
    DESCRIPTION
            "The MIB module for informant Hyper-V entities."
    REVISION      "200912110102Z"
    DESCRIPTION
            "Added OID 999 which gives the version of this
             agent."
    REVISION      "200804200634Z"
    DESCRIPTION
            "The initial revision of this MIB module."
    ::= { informant 25 }

msvmBIOS OBJECT-IDENTITY
    STATUS     current
    DESCRIPTION
        "The virtual BIOS is a software image that is loaded into RAM to
        configure some of the basic aspects of and boot a computer system.
        There is one BIOS element per computer system and that element
        cannot be replaced or removed. Thus, there is no resource pool for
        adding new BIOS elements to the virtual system. The BIOS element
        also does not have its own SettingData class to describe the
        settings for the BIOS. Settings for the BIOS, such as serial
        numbers, boot order, and num lock state, are found in the
        Msvm_VirtualSystemSettingData class."
    ::= { informantHyperV 1 }

msvmBIOSElementTable OBJECT-TYPE
    SYNTAX     SEQUENCE OF MsvmBIOSElement
    MAX-ACCESS not-accessible
    STATUS     current
    DESCRIPTION
        "Represents the low-level software that is loaded into RAM to
        configure and start the system. The BIOS is not a logical device,
        hence the virtual BIOS should not be thought of as a virtual
        computer system device. As it is not a device, it does not have a
        corresponding resource pool. The BIOS object is associated with the
        virtual computer system through the Msvm_SystemBIOS association."
    ::= { msvmBIOS 1 }

msvmBIOSElementEntry OBJECT-TYPE
    SYNTAX     MsvmBIOSElement
    MAX-ACCESS not-accessible
    STATUS     current
    DESCRIPTION
        "None"
    INDEX      { msvmbeIndex }
    ::= { msvmBIOSElementTable 1 }

MsvmBIOSElement ::= SEQUENCE {
    msvmbeIndex Integer32,
    msvmbeBIOSGUID WtcsDisplayString,
    msvmbeBIOSNumLock TruthValue,
    msvmbeBIOSSerialNumber WtcsDisplayString,
    msvmbeBaseBoardSerialNumber WtcsDisplayString,
    msvmbeBootOrder Integer32,
    msvmbeBuildNumber WtcsDisplayString,
    msvmbeCaption WtcsDisplayString,
    msvmbeChassisAssetTag WtcsDisplayString,
    msvmbeChassisSerialNumber WtcsDisplayString,
    msvmbeCodeSet WtcsDisplayString,
    msvmbeCurrentLanguage WtcsDisplayString,
    msvmbeDescription WtcsDisplayString,
    msvmbeElementName WtcsDisplayString,
    msvmbeEmbedFirmwareMajorRelease Integer32,
    msvmbeEmbedFirmwareMinorRelease Integer32,
    msvmbeHealthState INTEGER,
    msvmbeIdentificationCode WtcsDisplayString,
    msvmbeInstallDate DateAndTime,
    msvmbeLanguageEdition WtcsDisplayString,
    msvmbeListOfLanguages WtcsDisplayString,
    msvmbeLoadUtilityInformation WtcsDisplayString,
    msvmbeLoadedEndingAddress Gauge32,
    msvmbeLoadedStartingAddress Gauge32,
    msvmbeManufacturer WtcsDisplayString,
    msvmbeName WtcsDisplayString,
    msvmbeOperationStatus Integer32,
    msvmbeOperationalStatus INTEGER,
    msvmbeOtherTargetOS WtcsDisplayString,
    msvmbePrimaryBIOS TruthValue,
    msvmbeReleaseDate DateAndTime,
    msvmbeSerialNumber WtcsDisplayString,
    msvmbeSoftwareElementID WtcsDisplayString,
    msvmbeSoftwareElementState INTEGER,
    msvmbeStatus WtcsDisplayString,
    msvmbeStatusDescriptions WtcsDisplayString,
    msvmbeSystemBIOSMajorRelease Integer32,
    msvmbeSystemBIOSMinorRelease Integer32,
    msvmbeTargetOperatingSystem INTEGER,
    msvmbeVersion WtcsDisplayString
}

msvmbeIndex OBJECT-TYPE
    SYNTAX     Integer32 (1..2147483647)
    MAX-ACCESS read-only
    STATUS     current
    DESCRIPTION
        "The value of this object uniquely identifies the instance entry
        for this class."
    ::= { msvmBIOSElementEntry 1 }

msvmbeBIOSGUID OBJECT-TYPE
    SYNTAX     WtcsDisplayString
    MAX-ACCESS read-only
    STATUS     current
    DESCRIPTION
        "The unique identifier for the BIOS."
    ::= { msvmBIOSElementEntry 2 }

msvmbeBIOSNumLock OBJECT-TYPE
    SYNTAX     TruthValue
    MAX-ACCESS read-only
    STATUS     current
    DESCRIPTION
        "The enabled state of the Num Lock in the BIOS."
    ::= { msvmBIOSElementEntry 3 }

msvmbeBIOSSerialNumber OBJECT-TYPE
    SYNTAX     WtcsDisplayString
    MAX-ACCESS read-only
    STATUS     current
    DESCRIPTION
        "The serial number for the BIOS."
    ::= { msvmBIOSElementEntry 4 }

msvmbeBaseBoardSerialNumber OBJECT-TYPE
    SYNTAX     WtcsDisplayString
    MAX-ACCESS read-only
    STATUS     current
    DESCRIPTION
        "The serial number for the base board on the virtual system."
    ::= { msvmBIOSElementEntry 5 }

msvmbeBootOrder OBJECT-TYPE
    SYNTAX     Integer32
    MAX-ACCESS read-only
    STATUS     current
    DESCRIPTION
        "The order in which devices will be searched for a boot sector at
        startup."
    ::= { msvmBIOSElementEntry 6 }

msvmbeBuildNumber OBJECT-TYPE
    SYNTAX     WtcsDisplayString (SIZE (0..64))
    MAX-ACCESS read-only
    STATUS     current
    DESCRIPTION
        "The internal identifier for this compilation of SoftwareElement."
    ::= { msvmBIOSElementEntry 7 }

msvmbeCaption OBJECT-TYPE
    SYNTAX     WtcsDisplayString (SIZE (0..64))
    MAX-ACCESS read-only
    STATUS     current
    DESCRIPTION
        "The Caption property is a short textual description (one- line
        string) of the object."
    ::= { msvmBIOSElementEntry 8 }

msvmbeChassisAssetTag OBJECT-TYPE
    SYNTAX     WtcsDisplayString
    MAX-ACCESS read-only
    STATUS     current
    DESCRIPTION
        "Automatically populated by the BIOS when the virtual machine is
        created."
    ::= { msvmBIOSElementEntry 9 }

msvmbeChassisSerialNumber OBJECT-TYPE
    SYNTAX     WtcsDisplayString
    MAX-ACCESS read-only
    STATUS     current
    DESCRIPTION
        "Automatically populated by the BIOS when the virtual machine is
        created."
    ::= { msvmBIOSElementEntry 10 }

msvmbeCodeSet OBJECT-TYPE
    SYNTAX     WtcsDisplayString (SIZE (0..64))
    MAX-ACCESS read-only
    STATUS     current
    DESCRIPTION
        "The code set used by this SoftwareElement. It defines the bit
        patterns that a system uses to identify characters. ISO defines
        various code sets such as UTF-8 and ISO8859-1."
    ::= { msvmBIOSElementEntry 11 }

msvmbeCurrentLanguage OBJECT-TYPE
    SYNTAX     WtcsDisplayString
    MAX-ACCESS read-only
    STATUS     current
    DESCRIPTION
        "The currently selected language for the BIOS. This information can
        be obtained from SMBIOS, using the Current Language attribute of
        the Type 13 structure, to index into the string list following the
        structure. The property is formatted using the ISO 639 Language
        Name, and may be followed by the ISO 3166 Territory Name and the
        encoding method."
    ::= { msvmBIOSElementEntry 12 }

msvmbeDescription OBJECT-TYPE
    SYNTAX     WtcsDisplayString
    MAX-ACCESS read-only
    STATUS     current
    DESCRIPTION
        "The Description property provides a textual description of the
        object."
    ::= { msvmBIOSElementEntry 13 }

msvmbeElementName OBJECT-TYPE
    SYNTAX     WtcsDisplayString
    MAX-ACCESS read-only
    STATUS     current
    DESCRIPTION
        "A user-friendly name for the object. This property allows each
        instance to define a user-friendly name in addition to its key
        properties, identity data, and description information. 
        Note that the Name property of ManagedSystemElement is also defined
        as a user-friendly name. But, it is often subclassed to be a Key.
        It is not reasonable that the same property can convey both
        identity and a user-friendly name, without inconsistencies. Where
        Name exists and is not a Key (such as for instances of
        LogicalDevice), the same information can be present in both the
        Name and ElementName properties."
    ::= { msvmBIOSElementEntry 14 }

msvmbeEmbedFirmwareMajorRelease OBJECT-TYPE
    SYNTAX     Integer32
    MAX-ACCESS read-only
    STATUS     current
    DESCRIPTION
        "Indicates the major release of the embedded controller firmware,
        e.g. the value will be 0Ah for revision 10.22 and 02h for revision
        2.1. The value 0xFF denotes the embedded controller firmware is not
        field-upgradeable."
    ::= { msvmBIOSElementEntry 15 }

msvmbeEmbedFirmwareMinorRelease OBJECT-TYPE
    SYNTAX     Integer32
    MAX-ACCESS read-only
    STATUS     current
    DESCRIPTION
        "Indicates the minor release of the embedded controller firmware,
        e.g. the value will be 16h for revision 10.22 and 01h for revision
        2.1. The value 0xFF denotes the embedded controller firmware is not
        field-upgradeable."
    ::= { msvmBIOSElementEntry 16 }

msvmbeHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmBIOSElementEntry 17 }

msvmbeIdentificationCode OBJECT-TYPE
    SYNTAX     WtcsDisplayString (SIZE (0..64))
    MAX-ACCESS read-only
    STATUS     current
    DESCRIPTION
        "The manufacturer's identifier for this
        SoftwareElement. Often this will be a stock keeping
        unit (SKU) or a part number."
    ::= { msvmBIOSElementEntry 18 }

msvmbeInstallDate OBJECT-TYPE
    SYNTAX     DateAndTime
    MAX-ACCESS read-only
    STATUS     current
    DESCRIPTION
        "A datetime value that indicates when the object
        was installed. Lack of a value does not indicate
        that the object is not installed."
    ::= { msvmBIOSElementEntry 19 }

msvmbeLanguageEdition OBJECT-TYPE
    SYNTAX     WtcsDisplayString (SIZE (0..32))
    MAX-ACCESS read-only
    STATUS     current
    DESCRIPTION
        "The value of this property identifies the language
        edition of this SoftwareElement. The language codes
        defined in ISO 639 should be used. Where the
        element represents a multi-lingual or international
        version, the string 'Multilingual' should be used."
    ::= { msvmBIOSElementEntry 20 }

msvmbeListOfLanguages OBJECT-TYPE
    SYNTAX     WtcsDisplayString
    MAX-ACCESS read-only
    STATUS     current
    DESCRIPTION
        "A list of installable languages for the BIOS. This
        information can be obtained from SMBIOS, from the
        string list that follows the Type 13 structure. An
        ISO 639 Language Name should be used to specify the
        BIOS' installable languages. The ISO 3166 Territory
        Name and the encoding method may also be specified,
        following the Language Name."
    ::= { msvmBIOSElementEntry 21 }

msvmbeLoadUtilityInformation OBJECT-TYPE
    SYNTAX     WtcsDisplayString (SIZE (0..64))
    MAX-ACCESS read-only
    STATUS     current
    DESCRIPTION
        "A free form string describing the BIOS flash/load
        utility that is required to update the BIOSElement.
        Version and other information may be indicated in
        this property."
    ::= { msvmBIOSElementEntry 22 }

msvmbeLoadedEndingAddress OBJECT-TYPE
    SYNTAX     Gauge32
    MAX-ACCESS read-only
    STATUS     current
    DESCRIPTION
        "The ending address of the memory which this BIOS
        occupies."
    ::= { msvmBIOSElementEntry 23 }

msvmbeLoadedStartingAddress OBJECT-TYPE
    SYNTAX     Gauge32
    MAX-ACCESS read-only
    STATUS     current
    DESCRIPTION
        "The starting address of the memory which this BIOS
        occupies."
    ::= { msvmBIOSElementEntry 24 }

msvmbeManufacturer OBJECT-TYPE
    SYNTAX     WtcsDisplayString (SIZE (0..256))
    MAX-ACCESS read-only
    STATUS     current
    DESCRIPTION
        "Manufacturer of this SoftwareElement."
    ::= { msvmBIOSElementEntry 25 }

msvmbeName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmBIOSElementEntry 26 }

msvmbeOperationStatus OBJECT-TYPE
    SYNTAX     Integer32
    MAX-ACCESS read-only
    STATUS     current
    DESCRIPTION
        "Indicates the current status of the element. This
        property is inherited from CIM_ManagedSystemElement
        and it is always set to 2 ('OK')."
    ::= { msvmBIOSElementEntry 27 }

msvmbeOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmBIOSElementEntry 28 }

msvmbeOtherTargetOS OBJECT-TYPE
    SYNTAX     WtcsDisplayString (SIZE (0..64))
    MAX-ACCESS read-only
    STATUS     current
    DESCRIPTION
        "The OtherTargetOS property records the
        manufacturer and operating system type for a
        SoftwareElement when the TargetOperatingSystem
        property has a value of 1 ('Other'). For all other
        values of TargetOperatingSystem, the OtherTargetOS
        property is NULL."
    ::= { msvmBIOSElementEntry 29 }

msvmbePrimaryBIOS OBJECT-TYPE
    SYNTAX     TruthValue
    MAX-ACCESS read-only
    STATUS     current
    DESCRIPTION
        "If true, this is the primary BIOS of the
        ComputerSystem."
    ::= { msvmBIOSElementEntry 30 }

msvmbeReleaseDate OBJECT-TYPE
    SYNTAX     DateAndTime
    MAX-ACCESS read-only
    STATUS     current
    DESCRIPTION
        "Date that this BIOS was released."
    ::= { msvmBIOSElementEntry 31 }

msvmbeSerialNumber OBJECT-TYPE
    SYNTAX     WtcsDisplayString (SIZE (0..64))
    MAX-ACCESS read-only
    STATUS     current
    DESCRIPTION
        "The assigned serial number of this
        SoftwareElement."
    ::= { msvmBIOSElementEntry 32 }

msvmbeSoftwareElementID OBJECT-TYPE
    SYNTAX     WtcsDisplayString (SIZE (0..256))
    MAX-ACCESS read-only
    STATUS     current
    DESCRIPTION
        "This is an identifier for the SoftwareElement and
        is designed to be used in conjunction with other
        keys to create a unique representation of the
        element."
    ::= { msvmBIOSElementEntry 33 }

msvmbeSoftwareElementState OBJECT-TYPE
    SYNTAX     INTEGER {
        deployable(0),
        installable(1),
        executable(2),
        running(3)
    }
    MAX-ACCESS read-only
    STATUS     current
    DESCRIPTION
        "The SoftwareElementState is defined in this model
        to identify various states of a SoftwareElement's
        life cycle. 
        - A SoftwareElement in the deployable state
        describes the details necessary to successfully
        distribute it and the details (Checks and Actions)
        required to move it to the installable state (i.e,
        the next state). 
        - A SoftwareElement in the installable state
        describes the details necessary to successfully
        install it and the details (Checks and Actions)
        required to create an element in the executable
        state (i.e., the next state). 
        - A SoftwareElement in the executable state
        describes the details necessary to successfully
        start it and the details (Checks and Actions)
        required to move it to the running state (i.e., the
        next state). 
        - A SoftwareElement in the running state describes
        the details necessary to manage the started
        element."
    ::= { msvmBIOSElementEntry 34 }

msvmbeStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmBIOSElementEntry 35 }

msvmbeStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmBIOSElementEntry 36 }

msvmbeSystemBIOSMajorRelease OBJECT-TYPE
    SYNTAX     Integer32
    MAX-ACCESS read-only
    STATUS     current
    DESCRIPTION
        "Indicates the major release of the system BIOS,
        e.g. the value will be 0Ah for revision 10.22 and
        02h for revision 2.1. The value 0xFF denotes the
        system does not support the use of this field."
    ::= { msvmBIOSElementEntry 37 }

msvmbeSystemBIOSMinorRelease OBJECT-TYPE
    SYNTAX     Integer32
    MAX-ACCESS read-only
    STATUS     current
    DESCRIPTION
        "Indicates the minor release of the system BIOS,
        e.g. the value will be 16h for revision 10.22 and
        01h for revision 2.1. The value 0xFF denotes the
        system does not support the use of this field."
    ::= { msvmBIOSElementEntry 38 }

msvmbeTargetOperatingSystem OBJECT-TYPE
    SYNTAX     INTEGER {
        unknown(0),
        other(1),
        macos(2),
        attunix(3),
        dgux(4),
        decnt(5),
        tru64UNIX(6),
        openVMS(7),
        hpux(8),
        aix(9),
        mvs(10),
        os400(11),
        os2(12),
        javaVM(13),
        msdos(14),
        win3x(15),
        win95(16),
        win98(17),
        winnt(18),
        wince(19),
        ncr3000(20),
        netWare(21),
        osf(22),
        dcOS(23),
        reliantUNIX(24),
        scoUnixWare(25),
        scoOpenServer(26),
        sequent(27),
        irix(28),
        solaris(29),
        sunOS(30),
        u6000(31),
        aseries(32),
        hpNonStopOS(33),
        hpNonStopOSS(34),
        bs2000(35),
        linux(36),
        lynx(37),
        xenix(38),
        vm(39),
        interactiveUNIX(40),
        bsdunix(41),
        freeBSD(42),
        netBSD(43),
        gnuHurd(44),
        os9(45),
        machKernel(46),
        inferno(47),
        qnx(48),
        epoc(49),
        ixWorks(50),
        vxWorks(51),
        miNT(52),
        beOS(53),
        hpMPE(54),
        nextStep(55),
        palmPilot(56),
        rhapsody(57),
        windows2000(58),
        dedicated(59),
        os390(60),
        vse(61),
        tpf(62),
        windowsRMe(63),
        calderaOpenUNIX(64),
        openBSD(65),
        notApplicable(66),
        windowsXP(67),
        zOS(68),
        microsoftWindowsServer2003(69),
        microsoftWindowsServer200364Bit(70)
    }
    MAX-ACCESS read-only
    STATUS     current
    DESCRIPTION
        "The TargetOperatingSystem property specifies the
        element's operating system environment. The value
        of this property does not ensure that it is binary
        executable. Two other pieces of information are
        needed. First, the version of the OS needs to be
        specified using the class, CIM_OSVersion Check. The
        second piece of information is the architecture
        that the OS runs on. This information is verified
        using CIM_ArchitectureCheck. The combination of
        these constructs clearly identifies the level of OS
        required for a particular SoftwareElement."
    ::= { msvmBIOSElementEntry 39 }

msvmbeVersion OBJECT-TYPE
    SYNTAX     WtcsDisplayString (SIZE (0..64))
    MAX-ACCESS read-only
    STATUS     current
    DESCRIPTION
        "Software Version should be in the form
        <Major>.<Minor>.<Revision> or
        <Major>.<Minor><letter><revision>."
    ::= { msvmBIOSElementEntry 40 }

msvmSystemBIOSTable OBJECT-TYPE
    SYNTAX     SEQUENCE OF MsvmSystemBIOS
    MAX-ACCESS not-accessible
    STATUS     current
    DESCRIPTION
        "This class is used to associate a virtual system
        with its BIOS."
    ::= { msvmBIOS 2 }

msvmSystemBIOSEntry OBJECT-TYPE
    SYNTAX     MsvmSystemBIOS
    MAX-ACCESS not-accessible
    STATUS     current
    DESCRIPTION
        "None"
    INDEX      { msvmsbIndex }
    ::= { msvmSystemBIOSTable 1 }

MsvmSystemBIOS ::= SEQUENCE {
    msvmsbIndex Integer32,
    msvmsbGroupComponent WtcsDisplayString,
    msvmsbPartComponent WtcsDisplayString
}

msvmsbIndex OBJECT-TYPE
    SYNTAX     Integer32 (1..2147483647)
    MAX-ACCESS read-only
    STATUS     current
    DESCRIPTION
        "The value of this object uniquely identifies the
        instance entry for this class."
    ::= { msvmSystemBIOSEntry 1 }

msvmsbGroupComponent OBJECT-TYPE
    SYNTAX     WtcsDisplayString
    MAX-ACCESS read-only
    STATUS     current
    DESCRIPTION
        "The parent element in the association."
    ::= { msvmSystemBIOSEntry 2 }

msvmsbPartComponent OBJECT-TYPE
    SYNTAX     WtcsDisplayString
    MAX-ACCESS read-only
    STATUS     current
    DESCRIPTION
        "The child element in the association."
    ::= { msvmSystemBIOSEntry 3 }

msvmInput OBJECT-IDENTITY
    STATUS     current
    DESCRIPTION
        "The user input devices are represented by these
        classes. A virtual system always has one instance
        of each class associated with it. These devices may
        not be added or removed from the virtual system.
        Therefore, there are no resource pool instances for
        keyboard or mouse devices."
    ::= { informantHyperV 2 }

msvmKeyboardTable OBJECT-TYPE
    SYNTAX     SEQUENCE OF MsvmKeyboard
    MAX-ACCESS not-accessible
    STATUS     current
    DESCRIPTION
        "Represents a keyboard device. Keyboards are
        logical devices that are always present in a
        virtual system, and thus are not allocated through
        a resource pool. One Msvm_Keyboard instance is
        always present in a virtual computer system."
    ::= { msvmInput 1 }

msvmKeyboardEntry OBJECT-TYPE
    SYNTAX     MsvmKeyboard
    MAX-ACCESS not-accessible
    STATUS     current
    DESCRIPTION
        "None"
    INDEX      { msvmkbIndex }
    ::= { msvmKeyboardTable 1 }

MsvmKeyboard ::= SEQUENCE {
    msvmkbIndex Integer32,
    msvmkbAdditionalAvailability INTEGER,
    msvmkbAvailability INTEGER,
    msvmkbCaption WtcsDisplayString,
    msvmkbCreationClassName WtcsDisplayString,
    msvmkbDescription WtcsDisplayString,
    msvmkbDeviceID WtcsDisplayString,
    msvmkbElementName WtcsDisplayString,
    msvmkbEnabledDefault INTEGER,
    msvmkbEnabledState INTEGER,
    msvmkbErrorCleared TruthValue,
    msvmkbErrorDescription WtcsDisplayString,
    msvmkbHealthState INTEGER,
    msvmkbIdentifyingDescriptions WtcsDisplayString,
    msvmkbInstallDate DateAndTime,
    msvmkbIsLocked TruthValue,
    msvmkbLastErrorCode Gauge32,
    msvmkbLayout WtcsDisplayString,
    msvmkbLocationIndicator INTEGER,
    msvmkbMaxQuiesceTime Gauge32,
    msvmkbName WtcsDisplayString,
    msvmkbNumberOfFunctionKeys Integer32,
    msvmkbOperationalStatus INTEGER,
    msvmkbOtherEnabledState WtcsDisplayString,
    msvmkbOtherIdentifyingInfo WtcsDisplayString,
    msvmkbPassword Integer32,
    msvmkbPowerManagementCapability INTEGER,
    msvmkbPowerManagementSupported TruthValue,
    msvmkbPowerOnHours Gauge32,
    msvmkbRequestedState INTEGER,
    msvmkbStatus WtcsDisplayString,
    msvmkbStatusDescriptions WtcsDisplayString,
    msvmkbStatusInfo INTEGER,
    msvmkbSystemCreationClassName WtcsDisplayString,
    msvmkbSystemName WtcsDisplayString,
    msvmkbTimeOfLastStateChange DateAndTime,
    msvmkbTotalPowerOnHours Gauge32
}

msvmkbIndex OBJECT-TYPE
    SYNTAX     Integer32 (1..2147483647)
    MAX-ACCESS read-only
    STATUS     current
    DESCRIPTION
        "The value of this object uniquely identifies the
        instance entry for this class."
    ::= { msvmKeyboardEntry 1 }

msvmkbAdditionalAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Additional availability and status of the Device
        in addition to that specified in the Availability
        property. The Availability property denotes the
        primary status and availability of the Device. In
        some cases, this property will not be sufficient to
        denote the complete status of the Device. In those
        cases, the AdditionalAvailability property can be
        used to provide further information. For example,
        the primary Availability of a device might be 'Off
        line' (value=8) or in a low-power state
        (AdditionalAvailability value=14), or the Device
        could be running Diagnostics
        (AdditionalAvailability value=5, 'In Test')."
    ::= { msvmKeyboardEntry 2 }

msvmkbAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Note: The use of this property has been
        deprecated. 
        Deprecated description: The primary availability
        and status of the Device. (Additional status
        information can be specified using the Additional
        Availability array property.) For example, the
        Availability property indicates that the Device is
        running and has full power (value=3), or is in a
        warning (4), test (5), degraded (10) or power save
        state (values 13-15 and 17). The Power Save states
        are defined as follows: Value 13 ('Power Save -
        Unknown') indicates that the Device is known to be
        in a power save mode, but its exact status in this
        mode is unknown; value 14 ('Power Save - Low Power
        Mode') indicates that the Device is in a power save
        state but still functioning, and might exhibit
        degraded performance; value 15 ('Power Save -
        Standby') indicates that the Device is not
        functioning but could be brought to full power
        'quickly'; and value 17 ('Power Save - Warning')
        indicates that the Device is in a warning state,
        but is also in a power save mode."
    ::= { msvmKeyboardEntry 3 }

msvmkbCaption OBJECT-TYPE
    SYNTAX     WtcsDisplayString (SIZE (0..64))
    MAX-ACCESS read-only
    STATUS     current
    DESCRIPTION
        "The Caption property is a short textual
        description (one- line string) of the object."
    ::= { msvmKeyboardEntry 4 }

msvmkbCreationClassName OBJECT-TYPE
    SYNTAX     WtcsDisplayString (SIZE (0..256))
    MAX-ACCESS read-only
    STATUS     current
    DESCRIPTION
        "CreationClassName indicates the name of the class
        or the subclass used in the creation of an
        instance. When used with the other key properties
        of this class, this property allows all instances
        of this class and its subclasses to be uniquely
        identified."
    ::= { msvmKeyboardEntry 5 }

msvmkbDescription OBJECT-TYPE
    SYNTAX     WtcsDisplayString
    MAX-ACCESS read-only
    STATUS     current
    DESCRIPTION
        "The Description property provides a textual
        description of the object."
    ::= { msvmKeyboardEntry 6 }

msvmkbDeviceID OBJECT-TYPE
    SYNTAX     WtcsDisplayString (SIZE (0..64))
    MAX-ACCESS read-only
    STATUS     current
    DESCRIPTION
        "An address or other identifying information used
        to uniquely name the LogicalDevice."
    ::= { msvmKeyboardEntry 7 }

msvmkbElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmKeyboardEntry 8 }

msvmkbEnabledDefault OBJECT-TYPE
    SYNTAX     INTEGER {
        enabled(2),
        disabled(3),
        notApplicable(5),
        enabledbutOffline(6),
        noDefault(7)
    }
    MAX-ACCESS read-only
    STATUS     current
    DESCRIPTION
        "An enumerated value indicating an administrator's
        default or startup configuration for the Enabled
        State of an element. By default, the element is
        'Enabled' (value=2)."
    ::= { msvmKeyboardEntry 9 }

msvmkbEnabledState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "EnabledState is an integer enumeration that
        indicates the enabled and disabled states of an
        element. It can also indicate the transitions
        between these requested states. For example,
        shutting down (value=4) and starting (value=10) are
        transient states between enabled and disabled. The
        following text briefly summarizes the various
        enabled and disabled states: 
        Enabled (2) indicates that the element is or could
        be executing commands, will process any queued
        commands, and queues new requests. 
        Disabled (3) indicates that the element will not
        execute commands and will drop any new requests. 
        Shutting Down (4) indicates that the element is in
        the process of going to a Disabled state. 
        Not Applicable (5) indicates the element does not
        support being enabled or disabled. 
        Enabled but Offline (6) indicates that the element
        might be completing commands, and will drop any new
        requests. 
        Test (7) indicates that the element is in a test
        state. 
        Deferred (8) indicates that the element might be
        completing commands, but will queue any new
        requests. 
        Quiesce (9) indicates that the element is enabled
        but in a restricted mode. The behavior of the
        element is similar to the Enabled state, but it
        processes only a restricted set of commands. All
        other requests are queued. 
        Starting (10) indicates that the element is in the
        process of going to an Enabled state. New requests
        are queued."
    ::= { msvmKeyboardEntry 10 }

msvmkbErrorCleared OBJECT-TYPE
    SYNTAX     TruthValue
    MAX-ACCESS read-only
    STATUS     current
    DESCRIPTION
        "Note: The use of this method is deprecated. 
        Deprecated description: ErrorCleared is a Boolean
        property that indicates that the error reported in
        LastErrorCode is now cleared."
    ::= { msvmKeyboardEntry 11 }

msvmkbErrorDescription OBJECT-TYPE
    SYNTAX     WtcsDisplayString
    MAX-ACCESS read-only
    STATUS     current
    DESCRIPTION
        "Note: The use of this method is deprecated. 
        Deprecated description: ErrorDescription is a
        free-form string that supplies more information
        about the error recorded in LastErrorCode and
        information on any corrective actions that can be
        taken."
    ::= { msvmKeyboardEntry 12 }

msvmkbHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmKeyboardEntry 13 }

msvmkbIdentifyingDescriptions OBJECT-TYPE
    SYNTAX     WtcsDisplayString
    MAX-ACCESS read-only
    STATUS     current
    DESCRIPTION
        "An array of free-form strings providing
        explanations and details behind the entries in the
        OtherIdentifyingInfo array. Note that each entry of
        this array is related to the entry in
        OtherIdentifyingInfo that is located at the same
        index."
    ::= { msvmKeyboardEntry 14 }

msvmkbInstallDate OBJECT-TYPE
    SYNTAX     DateAndTime
    MAX-ACCESS read-only
    STATUS     current
    DESCRIPTION
        "A datetime value that indicates when the object
        was installed. Lack of a value does not indicate
        that the object is not installed."
    ::= { msvmKeyboardEntry 15 }

msvmkbIsLocked OBJECT-TYPE
    SYNTAX     TruthValue
    MAX-ACCESS read-only
    STATUS     current
    DESCRIPTION
        "An indication of whether the Device is locked,
        preventing user input or output."
    ::= { msvmKeyboardEntry 16 }

msvmkbLastErrorCode OBJECT-TYPE
    SYNTAX     Gauge32
    MAX-ACCESS read-only
    STATUS     current
    DESCRIPTION
        "Note: The use of this method is deprecated. 
        Deprecated description: LastErrorCode captures the
        last error code reported by the LogicalDevice."
    ::= { msvmKeyboardEntry 17 }

msvmkbLayout OBJECT-TYPE
    SYNTAX     WtcsDisplayString
    MAX-ACCESS read-only
    STATUS     current
    DESCRIPTION
        "A free-form string indicating the format and
        layout of the Keyboard."
    ::= { msvmKeyboardEntry 18 }

msvmkbLocationIndicator OBJECT-TYPE
    SYNTAX     INTEGER {
        unknown(0),
        on(2),
        off(3),
        notSupported(4)
    }
    MAX-ACCESS read-only
    STATUS     current
    DESCRIPTION
        "An integer that reflects the state of an indicator
        (e.g., LED) that is part of a device. Reading the
        value gives the current state. Writing the value
        with 'On'/'Off' turns the indicator on/off, other
        values may not be written."
    ::= { msvmKeyboardEntry 19 }

msvmkbMaxQuiesceTime OBJECT-TYPE
    SYNTAX     Gauge32
    UNITS "MilliSeconds"
    MAX-ACCESS read-only
    STATUS     current
    DESCRIPTION
        "Note: The use of this property has been
        deprecated. When evaluating the use of Quiesce, it
        was determined that this single property is not
        adequate for describing when a device will
        automatically exit a quiescent state. In fact, the
        most likely scenario for a device to exit a
        quiescent state was determined to be based on the
        number of outstanding requests queued rather than
        on a maximum time. This decision will be
        re-evaluated and repositioned later. 
        Deprecated description: Maximum time, in
        milliseconds, that a Device can run in a 'Quiesced'
        state. The state is defined in its Availability and
        AdditionalAvailability properties, where 'Quiesced'
        is conveyed by the value 21. What occurs at the end
        of the time limit is device-specific. The Device
        can unquiesce, can be offline, or can take other
        actions. A value of 0 indicates that a Device can
        remain quiesced indefinitely."
    ::= { msvmKeyboardEntry 20 }

msvmkbName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmKeyboardEntry 21 }

msvmkbNumberOfFunctionKeys OBJECT-TYPE
    SYNTAX     Integer32
    MAX-ACCESS read-only
    STATUS     current
    DESCRIPTION
        "Number of function keys on the Keyboard."
    ::= { msvmKeyboardEntry 22 }

msvmkbOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmKeyboardEntry 23 }

msvmkbOtherEnabledState OBJECT-TYPE
    SYNTAX     WtcsDisplayString
    MAX-ACCESS read-only
    STATUS     current
    DESCRIPTION
        "A string that describes the enabled or disabled
        state of the element when the EnabledState property
        is set to 1 ('Other'). This property must be set to
        null when EnabledState is any value other than 1."
    ::= { msvmKeyboardEntry 24 }

msvmkbOtherIdentifyingInfo OBJECT-TYPE
    SYNTAX     WtcsDisplayString (SIZE (0..256))
    MAX-ACCESS read-only
    STATUS     current
    DESCRIPTION
        "OtherIdentifyingInfo captures data, in addition to
        DeviceID information, that could be used to
        identify a LogicalDevice. For example, you could
        use this property to hold the operating system's
        user-friendly name for the Device."
    ::= { msvmKeyboardEntry 25 }

msvmkbPassword OBJECT-TYPE
    SYNTAX     Integer32
    MAX-ACCESS read-only
    STATUS     current
    DESCRIPTION
        "An integer indicating whether a hardware-level
        password is enabled at the keyboard, preventing
        local input."
    ::= { msvmKeyboardEntry 26 }

msvmkbPowerManagementCapability OBJECT-TYPE
    SYNTAX     INTEGER {
        unknown(0),
        notSupported(1),
        disabled(2),
        enabled(3),
        powerSavingModesEnteredAutomatic(4),
        powerStateSettable(5),
        powerCyclingSupported(6),
        timedPowerOnSupported(7)
    }
    MAX-ACCESS read-only
    STATUS     current
    DESCRIPTION
        "Note: The use of this property has been
        deprecated. Instead, use the PowerCapabilites
        property in an associated
        PowerManagementCapabilities class. Deprecated
        description: An enumerated array describing the
        power management capabilities of the Device."
    ::= { msvmKeyboardEntry 27 }

msvmkbPowerManagementSupported OBJECT-TYPE
    SYNTAX     TruthValue
    MAX-ACCESS read-only
    STATUS     current
    DESCRIPTION
        "Note: The use of this property has been
        deprecated. Instead, the existence of an associated
        PowerManagementCapabilities class (associated using
        the ElementCapabilities relationship) indicates
        that power management is supported. Deprecated
        description: Boolean that indicates that the Device
        can use power management."
    ::= { msvmKeyboardEntry 28 }

msvmkbPowerOnHours OBJECT-TYPE
    SYNTAX     Gauge32
    UNITS "Hours"
    MAX-ACCESS read-only
    STATUS     current
    DESCRIPTION
        "Note: The use of this method is deprecated. 
        Deprecated description: The number of consecutive
        hours that this Device has been powered on since
        its last power cycle."
    ::= { msvmKeyboardEntry 29 }

msvmkbRequestedState OBJECT-TYPE
    SYNTAX     INTEGER {
        enabled(2),
        disabled(3),
        shutDown(4),
        noChange(5),
        offline(6),
        test(7),
        deferred(8),
        quiesce(9),
        reboot(10),
        reset(11),
        notApplicable(12)
    }
    MAX-ACCESS read-only
    STATUS     current
    DESCRIPTION
        "RequestedState is an integer enumeration that
        indicates the last requested or desired state for
        the element. The actual state of the element is
        represented by EnabledState. This property is
        provided to compare the last requested and current
        enabled or disabled states. Note that when
        EnabledState is set to 5 ('Not Applicable'), then
        this property has no meaning. By default, the
        RequestedState of the element is 5 ('No Change').
        Refer to the EnabledState property description for
        explanations of the values in the RequestedState
        enumeration. 
        
        It should be noted that there are two new values in
        RequestedState that build on the statuses of
        EnabledState. These are 'Reboot' (10) and 'Reset'
        (11). Reboot refers to doing a 'Shut Down' and then
        moving to an 'Enabled' state. Reset indicates that
        the element is first 'Disabled' and then 'Enabled'.
        The distinction between requesting 'Shut Down' and
        'Disabled' should also be noted. Shut Down requests
        an orderly transition to the Disabled state, and
        might involve removing power, to completely erase
        any existing state. The Disabled state requests an
        immediate disabling of the element, such that it
        will not execute or accept any commands or
        processing requests. 
        
        This property is set as the result of a method
        invocation (such as Start or StopService on
        CIM_Service), or can be overridden and defined as
        WRITEable in a subclass. The method approach is
        considered superior to a WRITEable property,
        because it allows an explicit invocation of the
        operation and the return of a result code. 
        
        A particular instance of EnabledLogicalElement
        might not support RequestedStateChange. If this
        occurs, the value 12 ('Not Applicable') is used."
    ::= { msvmKeyboardEntry 30 }

msvmkbStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmKeyboardEntry 31 }

msvmkbStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmKeyboardEntry 32 }

msvmkbStatusInfo OBJECT-TYPE
    SYNTAX     INTEGER {
        other(1),
        unknown(2),
        enabled(3),
        disabled(4),
        notApplicable(5)
    }
    MAX-ACCESS read-only
    STATUS     current
    DESCRIPTION
        "Note: The use of this method is deprecated in lieu
        of a more clearly named property (EnabledState)
        that is inherited from ManagedSystemElement and
        that has additional enumerated values. 
        Deprecated description: The StatusInfo property
        indicates whether the Logical Device is in an
        enabled state (value=3), disabled state (value=4),
        some other state (value=1), or an unknown state
        (value=2). If this property does not apply to the
        LogicalDevice, the value 5 ('Not Applicable')
        should be used. If a Device is
        ('Enabled')(value=3), it has been powered up and is
        configured and operational. The Device might or
        might not be functionally active, depending on
        whether its Availability (or
        AdditionalAvailability) indicates that it is
        ('Running/Full Power')(value=3) or ('Off line')
        (value=8). In an enabled but offline mode, a Device
        might be performing out-of-band requests, such as
        running Diagnostics. If StatusInfo is ('Disabled')
        (value=4), a Device can only be 'enabled' or
        powered off. In a personal computer environment,
        ('Disabled') means that the driver of the device is
        not available in the stack. In other environments,
        a Device can be disabled by removing its
        configuration file. A disabled device is physically
        present in a System and consuming resources, but it
        cannot be communicated with until a driver is
        loaded, a configuration file is loaded, or some
        other 'enabling' activity has occurred."
    ::= { msvmKeyboardEntry 33 }

msvmkbSystemCreationClassName OBJECT-TYPE
    SYNTAX     WtcsDisplayString (SIZE (0..256))
    MAX-ACCESS read-only
    STATUS     current
    DESCRIPTION
        "The CreationClassName of the scoping system."
    ::= { msvmKeyboardEntry 34 }

msvmkbSystemName OBJECT-TYPE
    SYNTAX     WtcsDisplayString (SIZE (0..256))
    MAX-ACCESS read-only
    STATUS     current
    DESCRIPTION
        "The System Name of the scoping system."
    ::= { msvmKeyboardEntry 35 }

msvmkbTimeOfLastStateChange OBJECT-TYPE
    SYNTAX     DateAndTime
    MAX-ACCESS read-only
    STATUS     current
    DESCRIPTION
        "The date or time when the EnabledState of the
        element last changed. If the state of the element
        has not changed and this property is populated,
        then it must be set to a 0 interval value. If a
        state change was requested, but rejected or not yet
        processed, the property must not be updated."
    ::= { msvmKeyboardEntry 36 }

msvmkbTotalPowerOnHours OBJECT-TYPE
    SYNTAX     Gauge32
    UNITS "Hours"
    MAX-ACCESS read-only
    STATUS     current
    DESCRIPTION
        "Note: The use of this method is deprecated. 
        Deprecated description: The total number of hours
        that this Device has been powered on."
    ::= { msvmKeyboardEntry 37 }

msvmPs2MouseTable OBJECT-TYPE
    SYNTAX     SEQUENCE OF MsvmPs2Mouse
    MAX-ACCESS not-accessible
    STATUS     current
    DESCRIPTION
        "Represents a PS2 mouse device. Instances of this
        class are logical devices that are always present
        in a virtual system, and thus are not allocated
        through a resource pool. One instance is always
        present in a virtual computer system."
    ::= { msvmInput 2 }

msvmPs2MouseEntry OBJECT-TYPE
    SYNTAX     MsvmPs2Mouse
    MAX-ACCESS not-accessible
    STATUS     current
    DESCRIPTION
        "None"
    INDEX      { msvmps2Index }
    ::= { msvmPs2MouseTable 1 }

MsvmPs2Mouse ::= SEQUENCE {
    msvmps2Index Integer32,
    msvmps2AbsoluteCoordinates TruthValue,
    msvmps2AdditionalAvailability INTEGER,
    msvmps2Availability INTEGER,
    msvmps2Caption WtcsDisplayString,
    msvmps2CreationClassName WtcsDisplayString,
    msvmps2Description WtcsDisplayString,
    msvmps2DeviceID WtcsDisplayString,
    msvmps2ElementName WtcsDisplayString,
    msvmps2EnabledDefault INTEGER,
    msvmps2EnabledState INTEGER,
    msvmps2ErrorCleared TruthValue,
    msvmps2ErrorDescription WtcsDisplayString,
    msvmps2Handedness INTEGER,
    msvmps2HealthState INTEGER,
    msvmps2IdentifyingDescriptions WtcsDisplayString,
    msvmps2InstallDate DateAndTime,
    msvmps2IsLocked TruthValue,
    msvmps2LastErrorCode Gauge32,
    msvmps2LocationIndicator INTEGER,
    msvmps2MaxQuiesceTime Gauge32,
    msvmps2Name WtcsDisplayString,
    msvmps2NumberOfButtons Integer32,
    msvmps2OperationalStatus INTEGER,
    msvmps2OtherEnabledState WtcsDisplayString,
    msvmps2OtherIdentifyingInfo WtcsDisplayString,
    msvmps2PointingType INTEGER,
    msvmps2PowerManagementCapability INTEGER,
    msvmps2PowerManagementSupported TruthValue,
    msvmps2PowerOnHours Gauge32,
    msvmps2RequestedState INTEGER,
    msvmps2Resolution Gauge32,
    msvmps2Status WtcsDisplayString,
    msvmps2StatusDescriptions WtcsDisplayString,
    msvmps2StatusInfo INTEGER,
    msvmps2SystemCreationClassName WtcsDisplayString,
    msvmps2SystemName WtcsDisplayString,
    msvmps2TimeOfLastStateChange DateAndTime,
    msvmps2TotalPowerOnHours Gauge32
}

msvmps2Index OBJECT-TYPE
    SYNTAX     Integer32 (1..2147483647)
    MAX-ACCESS read-only
    STATUS     current
    DESCRIPTION
        "The value of this object uniquely identifies the
        instance entry for this class."
    ::= { msvmPs2MouseEntry 1 }

msvmps2AbsoluteCoordinates OBJECT-TYPE
    SYNTAX     TruthValue
    MAX-ACCESS read-only
    STATUS     current
    DESCRIPTION
        "Indicates whether the device operates on absolute
        coordinates. If not set, the device's coordinates
        are relative."
    ::= { msvmPs2MouseEntry 2 }

msvmps2AdditionalAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Additional availability and status of the Device
        in addition to that specified in the Availability
        property. The Availability property denotes the
        primary status and availability of the Device. In
        some cases, this property will not be sufficient to
        denote the complete status of the Device. In those
        cases, the AdditionalAvailability property can be
        used to provide further information. For example,
        the primary Availability of a device might be 'Off
        line' (value=8) or in a low-power state
        (AdditionalAvailability value=14), or the Device
        could be running Diagnostics
        (AdditionalAvailability value=5, 'In Test')."
    ::= { msvmPs2MouseEntry 3 }

msvmps2Availability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Note: The use of this property has been
        deprecated. 
        Deprecated description: The primary availability
        and status of the Device. (Additional status
        information can be specified using the Additional
        Availability array property.) For example, the
        Availability property indicates that the Device is
        running and has full power (value=3), or is in a
        warning (4), test (5), degraded (10) or power save
        state (values 13-15 and 17). The Power Save states
        are defined as follows: Value 13 ('Power Save -
        Unknown') indicates that the Device is known to be
        in a power save mode, but its exact status in this
        mode is unknown; value 14 ('Power Save - Low Power
        Mode') indicates that the Device is in a power save
        state but still functioning, and might exhibit
        degraded performance; value 15 ('Power Save -
        Standby') indicates that the Device is not
        functioning but could be brought to full power
        'quickly'; and value 17 ('Power Save - Warning')
        indicates that the Device is in a warning state,
        but is also in a power save mode."
    ::= { msvmPs2MouseEntry 4 }

msvmps2Caption OBJECT-TYPE
    SYNTAX     WtcsDisplayString (SIZE (0..64))
    MAX-ACCESS read-only
    STATUS     current
    DESCRIPTION
        "The Caption property is a short textual
        description (one- line string) of the object."
    ::= { msvmPs2MouseEntry 5 }

msvmps2CreationClassName OBJECT-TYPE
    SYNTAX     WtcsDisplayString (SIZE (0..256))
    MAX-ACCESS read-only
    STATUS     current
    DESCRIPTION
        "CreationClassName indicates the name of the class
        or the subclass used in the creation of an
        instance. When used with the other key properties
        of this class, this property allows all instances
        of this class and its subclasses to be uniquely
        identified."
    ::= { msvmPs2MouseEntry 6 }

msvmps2Description OBJECT-TYPE
    SYNTAX     WtcsDisplayString
    MAX-ACCESS read-only
    STATUS     current
    DESCRIPTION
        "The Description property provides a textual
        description of the object."
    ::= { msvmPs2MouseEntry 7 }

msvmps2DeviceID OBJECT-TYPE
    SYNTAX     WtcsDisplayString (SIZE (0..64))
    MAX-ACCESS read-only
    STATUS     current
    DESCRIPTION
        "An address or other identifying information used
        to uniquely name the LogicalDevice."
    ::= { msvmPs2MouseEntry 8 }

msvmps2ElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmPs2MouseEntry 9 }

msvmps2EnabledDefault OBJECT-TYPE
    SYNTAX     INTEGER {
        enabled(2),
        disabled(3),
        notApplicable(5),
        enabledbutOffline(6),
        noDefault(7)
    }
    MAX-ACCESS read-only
    STATUS     current
    DESCRIPTION
        "An enumerated value indicating an administrator's
        default or startup configuration for the Enabled
        State of an element. By default, the element is
        'Enabled' (value=2)."
    ::= { msvmPs2MouseEntry 10 }

msvmps2EnabledState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "EnabledState is an integer enumeration that
        indicates the enabled and disabled states of an
        element. It can also indicate the transitions
        between these requested states. For example,
        shutting down (value=4) and starting (value=10) are
        transient states between enabled and disabled. The
        following text briefly summarizes the various
        enabled and disabled states: 
        Enabled (2) indicates that the element is or could
        be executing commands, will process any queued
        commands, and queues new requests. 
        Disabled (3) indicates that the element will not
        execute commands and will drop any new requests. 
        Shutting Down (4) indicates that the element is in
        the process of going to a Disabled state. 
        Not Applicable (5) indicates the element does not
        support being enabled or disabled. 
        Enabled but Offline (6) indicates that the element
        might be completing commands, and will drop any new
        requests. 
        Test (7) indicates that the element is in a test
        state. 
        Deferred (8) indicates that the element might be
        completing commands, but will queue any new
        requests. 
        Quiesce (9) indicates that the element is enabled
        but in a restricted mode. The behavior of the
        element is similar to the Enabled state, but it
        processes only a restricted set of commands. All
        other requests are queued. 
        Starting (10) indicates that the element is in the
        process of going to an Enabled state. New requests
        are queued."
    ::= { msvmPs2MouseEntry 11 }

msvmps2ErrorCleared OBJECT-TYPE
    SYNTAX     TruthValue
    MAX-ACCESS read-only
    STATUS     current
    DESCRIPTION
        "Note: The use of this method is deprecated. 
        Deprecated description: ErrorCleared is a Boolean
        property that indicates that the error reported in
        LastErrorCode is now cleared."
    ::= { msvmPs2MouseEntry 12 }

msvmps2ErrorDescription OBJECT-TYPE
    SYNTAX     WtcsDisplayString
    MAX-ACCESS read-only
    STATUS     current
    DESCRIPTION
        "Note: The use of this method is deprecated. 
        Deprecated description: ErrorDescription is a
        free-form string that supplies more information
        about the error recorded in LastErrorCode and
        information on any corrective actions that can be
        taken."
    ::= { msvmPs2MouseEntry 13 }

msvmps2Handedness OBJECT-TYPE
    SYNTAX     INTEGER {
        unknown(0),
        notApplicable(1),
        rightHandedOperation(2),
        leftHandedOperation(3)
    }
    MAX-ACCESS read-only
    STATUS     current
    DESCRIPTION
        "Integer indicating whether the PointingDevice is
        configured for right (value=2) or left handed
        operation (value=3). Also, the values, 'Unknown'
        (0) and 'Not Applicable' (1), can be defined."
    ::= { msvmPs2MouseEntry 14 }

msvmps2HealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmPs2MouseEntry 15 }

msvmps2IdentifyingDescriptions OBJECT-TYPE
    SYNTAX     WtcsDisplayString
    MAX-ACCESS read-only
    STATUS     current
    DESCRIPTION
        "An array of free-form strings providing
        explanations and details behind the entries in the
        OtherIdentifyingInfo array. Note that each entry of
        this array is related to the entry in
        OtherIdentifyingInfo that is located at the same
        index."
    ::= { msvmPs2MouseEntry 16 }

msvmps2InstallDate OBJECT-TYPE
    SYNTAX     DateAndTime
    MAX-ACCESS read-only
    STATUS     current
    DESCRIPTION
        "A datetime value that indicates when the object
        was installed. Lack of a value does not indicate
        that the object is not installed."
    ::= { msvmPs2MouseEntry 17 }

msvmps2IsLocked OBJECT-TYPE
    SYNTAX     TruthValue
    MAX-ACCESS read-only
    STATUS     current
    DESCRIPTION
        "An indication of whether the Device is locked,
        preventing user input or output."
    ::= { msvmPs2MouseEntry 18 }

msvmps2LastErrorCode OBJECT-TYPE
    SYNTAX     Gauge32
    MAX-ACCESS read-only
    STATUS     current
    DESCRIPTION
        "Note: The use of this method is deprecated. 
        Deprecated description: LastErrorCode captures the
        last error code reported by the LogicalDevice."
    ::= { msvmPs2MouseEntry 19 }

msvmps2LocationIndicator OBJECT-TYPE
    SYNTAX     INTEGER {
        unknown(0),
        on(2),
        off(3),
        notSupported(4)
    }
    MAX-ACCESS read-only
    STATUS     current
    DESCRIPTION
        "An integer that reflects the state of an indicator
        (e.g., LED) that is part of a device. Reading the
        value gives the current state. Writing the value
        with 'On'/'Off' turns the indicator on/off, other
        values may not be written."
    ::= { msvmPs2MouseEntry 20 }

msvmps2MaxQuiesceTime OBJECT-TYPE
    SYNTAX     Gauge32
    UNITS "MilliSeconds"
    MAX-ACCESS read-only
    STATUS     current
    DESCRIPTION
        "Note: The use of this property has been
        deprecated. When evaluating the use of Quiesce, it
        was determined that this single property is not
        adequate for describing when a device will
        automatically exit a quiescent state. In fact, the
        most likely scenario for a device to exit a
        quiescent state was determined to be based on the
        number of outstanding requests queued rather than
        on a maximum time. This decision will be
        re-evaluated and repositioned later. 
        Deprecated description: Maximum time, in
        milliseconds, that a Device can run in a 'Quiesced'
        state. The state is defined in its Availability and
        AdditionalAvailability properties, where 'Quiesced'
        is conveyed by the value 21. What occurs at the end
        of the time limit is device-specific. The Device
        can unquiesce, can be offline, or can take other
        actions. A value of 0 indicates that a Device can
        remain quiesced indefinitely."
    ::= { msvmPs2MouseEntry 21 }

msvmps2Name OBJECT-TYPE
    SYNTAX     WtcsDisplayString (SIZE (0..1024))
    MAX-ACCESS read-only
    STATUS     current
    DESCRIPTION
        "The Name property defines the label by which the
        object is known. When subclassed, the Name property
        can be overridden to be a Key property."
    ::= { msvmPs2MouseEntry 22 }

msvmps2NumberOfButtons OBJECT-TYPE
    SYNTAX     Integer32
    MAX-ACCESS read-only
    STATUS     current
    DESCRIPTION
        "Number of buttons. If the PointingDevice has no
        buttons, enter 0."
    ::= { msvmPs2MouseEntry 23 }

msvmps2OperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmPs2MouseEntry 24 }

msvmps2OtherEnabledState OBJECT-TYPE
    SYNTAX     WtcsDisplayString
    MAX-ACCESS read-only
    STATUS     current
    DESCRIPTION
        "A string that describes the enabled or disabled
        state of the element when the EnabledState property
        is set to 1 ('Other'). This property must be set to
        null when EnabledState is any value other than 1."
    ::= { msvmPs2MouseEntry 25 }

msvmps2OtherIdentifyingInfo OBJECT-TYPE
    SYNTAX     WtcsDisplayString (SIZE (0..256))
    MAX-ACCESS read-only
    STATUS     current
    DESCRIPTION
        "OtherIdentifyingInfo captures data, in addition to
        DeviceID information, that could be used to
        identify a LogicalDevice. For example, you could
        use this property to hold the operating system's
        user-friendly name for the Device."
    ::= { msvmPs2MouseEntry 26 }

msvmps2PointingType OBJECT-TYPE
    SYNTAX     INTEGER {
        other(1),
        unknown(2),
        mouse(3),
        trackBall(4),
        trackPoint(5),
        glidePoint(6),
        touchPad(7),
        touchScreen(8),
        mouseOpticalSensor(9)
    }
    MAX-ACCESS read-only
    STATUS     current
    DESCRIPTION
        "The type of the pointing device."
    ::= { msvmPs2MouseEntry 27 }

msvmps2PowerManagementCapability OBJECT-TYPE
    SYNTAX     INTEGER {
        unknown(0),
        notSupported(1),
        disabled(2),
        enabled(3),
        powerSavingModesEnteredAutomatic(4),
        powerStateSettable(5),
        powerCyclingSupported(6),
        timedPowerOnSupported(7)
    }
    MAX-ACCESS read-only
    STATUS     current
    DESCRIPTION
        "Note: The use of this property has been
        deprecated. Instead, use the PowerCapabilites
        property in an associated
        PowerManagementCapabilities class. Deprecated
        description: An enumerated array describing the
        power management capabilities of the Device."
    ::= { msvmPs2MouseEntry 28 }

msvmps2PowerManagementSupported OBJECT-TYPE
    SYNTAX     TruthValue
    MAX-ACCESS read-only
    STATUS     current
    DESCRIPTION
        "Note: The use of this property has been
        deprecated. Instead, the existence of an associated
        PowerManagementCapabilities class (associated using
        the ElementCapabilities relationship) indicates
        that power management is supported. Deprecated
        description: Boolean that indicates that the Device
        can use power management."
    ::= { msvmPs2MouseEntry 29 }

msvmps2PowerOnHours OBJECT-TYPE
    SYNTAX     Gauge32
    UNITS "Hours"
    MAX-ACCESS read-only
    STATUS     current
    DESCRIPTION
        "Note: The use of this method is deprecated. 
        Deprecated description: The number of consecutive
        hours that this Device has been powered on since
        its last power cycle."
    ::= { msvmPs2MouseEntry 30 }

msvmps2RequestedState OBJECT-TYPE
    SYNTAX     INTEGER {
        enabled(2),
        disabled(3),
        shutDown(4),
        noChange(5),
        offline(6),
        test(7),
        deferred(8),
        quiesce(9),
        reboot(10),
        reset(11),
        notApplicable(12)
    }
    MAX-ACCESS read-only
    STATUS     current
    DESCRIPTION
        "RequestedState is an integer enumeration that
        indicates the last requested or desired state for
        the element. The actual state of the element is
        represented by EnabledState. This property is
        provided to compare the last requested and current
        enabled or disabled states. Note that when
        EnabledState is set to 5 ('Not Applicable'), then
        this property has no meaning. By default, the
        RequestedState of the element is 5 ('No Change').
        Refer to the EnabledState property description for
        explanations of the values in the RequestedState
        enumeration. 
        
        It should be noted that there are two new values in
        RequestedState that build on the statuses of
        EnabledState. These are 'Reboot' (10) and 'Reset'
        (11). Reboot refers to doing a 'Shut Down' and then
        moving to an 'Enabled' state. Reset indicates that
        the element is first 'Disabled' and then 'Enabled'.
        The distinction between requesting 'Shut Down' and
        'Disabled' should also be noted. Shut Down requests
        an orderly transition to the Disabled state, and
        might involve removing power, to completely erase
        any existing state. The Disabled state requests an
        immediate disabling of the element, such that it
        will not execute or accept any commands or
        processing requests. 
        
        This property is set as the result of a method
        invocation (such as Start or StopService on
        CIM_Service), or can be overridden and defined as
        WRITEable in a subclass. The method approach is
        considered superior to a WRITEable property,
        because it allows an explicit invocation of the
        operation and the return of a result code. 
        
        A particular instance of EnabledLogicalElement
        might not support RequestedStateChange. If this
        occurs, the value 12 ('Not Applicable') is used."
    ::= { msvmPs2MouseEntry 31 }

msvmps2Resolution OBJECT-TYPE
    SYNTAX     Gauge32
    UNITS "Counts per Inch"
    MAX-ACCESS read-only
    STATUS     current
    DESCRIPTION
        "Tracking resolution of the PointingDevice in
        Counts per Inch."
    ::= { msvmPs2MouseEntry 32 }

msvmps2Status OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmPs2MouseEntry 33 }

msvmps2StatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmPs2MouseEntry 34 }

msvmps2StatusInfo OBJECT-TYPE
    SYNTAX     INTEGER {
        other(1),
        unknown(2),
        enabled(3),
        disabled(4),
        notApplicable(5)
    }
    MAX-ACCESS read-only
    STATUS     current
    DESCRIPTION
        "Note: The use of this method is deprecated in lieu
        of a more clearly named property (EnabledState)
        that is inherited from ManagedSystemElement and
        that has additional enumerated values. 
        Deprecated description: The StatusInfo property
        indicates whether the Logical Device is in an
        enabled state (value=3), disabled state (value=4),
        some other state (value=1), or an unknown state
        (value=2). If this property does not apply to the
        LogicalDevice, the value 5 ('Not Applicable')
        should be used. If a Device is
        ('Enabled')(value=3), it has been powered up and is
        configured and operational. The Device might or
        might not be functionally active, depending on
        whether its Availability (or
        AdditionalAvailability) indicates that it is
        ('Running/Full Power')(value=3) or ('Off line')
        (value=8). In an enabled but offline mode, a Device
        might be performing out-of-band requests, such as
        running Diagnostics. If StatusInfo is ('Disabled')
        (value=4), a Device can only be 'enabled' or
        powered off. In a personal computer environment,
        ('Disabled') means that the driver of the device is
        not available in the stack. In other environments,
        a Device can be disabled by removing its
        configuration file. A disabled device is physically
        present in a System and consuming resources, but it
        cannot be communicated with until a driver is
        loaded, a configuration file is loaded, or some
        other 'enabling' activity has occurred."
    ::= { msvmPs2MouseEntry 35 }

msvmps2SystemCreationClassName OBJECT-TYPE
    SYNTAX     WtcsDisplayString (SIZE (0..256))
    MAX-ACCESS read-only
    STATUS     current
    DESCRIPTION
        "The CreationClassName of the scoping system."
    ::= { msvmPs2MouseEntry 36 }

msvmps2SystemName OBJECT-TYPE
    SYNTAX     WtcsDisplayString (SIZE (0..256))
    MAX-ACCESS read-only
    STATUS     current
    DESCRIPTION
        "The System Name of the scoping system."
    ::= { msvmPs2MouseEntry 37 }

msvmps2TimeOfLastStateChange OBJECT-TYPE
    SYNTAX     DateAndTime
    MAX-ACCESS read-only
    STATUS     current
    DESCRIPTION
        "The date or time when the EnabledState of the
        element last changed. If the state of the element
        has not changed and this property is populated,
        then it must be set to a 0 interval value. If a
        state change was requested, but rejected or not yet
        processed, the property must not be updated."
    ::= { msvmPs2MouseEntry 38 }

msvmps2TotalPowerOnHours OBJECT-TYPE
    SYNTAX     Gauge32
    UNITS "Hours"
    MAX-ACCESS read-only
    STATUS     current
    DESCRIPTION
        "Note: The use of this method is deprecated. 
        Deprecated description: The total number of hours
        that this Device has been powered on."
    ::= { msvmPs2MouseEntry 39 }

msvmSyntheticMouseTable OBJECT-TYPE
    SYNTAX     SEQUENCE OF MsvmSyntheticMouse
    MAX-ACCESS not-accessible
    STATUS     current
    DESCRIPTION
        "Represents a synthetic mouse device."
    ::= { msvmInput 3 }

msvmSyntheticMouseEntry OBJECT-TYPE
    SYNTAX     MsvmSyntheticMouse
    MAX-ACCESS not-accessible
    STATUS     current
    DESCRIPTION
        "None"
    INDEX      { msvmsmIndex }
    ::= { msvmSyntheticMouseTable 1 }

MsvmSyntheticMouse ::= SEQUENCE {
    msvmsmIndex Integer32,
    msvmsmAbsoluteCoordinates TruthValue,
    msvmsmAdditionalAvailability INTEGER,
    msvmsmAvailability INTEGER,
    msvmsmCaption WtcsDisplayString,
    msvmsmCreationClassName WtcsDisplayString,
    msvmsmDescription WtcsDisplayString,
    msvmsmDeviceID WtcsDisplayString,
    msvmsmElementName WtcsDisplayString,
    msvmsmEnabledDefault INTEGER,
    msvmsmEnabledState INTEGER,
    msvmsmErrorCleared TruthValue,
    msvmsmErrorDescription WtcsDisplayString,
    msvmsmHandedness INTEGER,
    msvmsmHealthState INTEGER,
    msvmsmHorizontalPosition Integer32,
    msvmsmIdentifyingDescriptions WtcsDisplayString,
    msvmsmInstallDate DateAndTime,
    msvmsmIsLocked TruthValue,
    msvmsmLastErrorCode Gauge32,
    msvmsmLocationIndicator INTEGER,
    msvmsmMaxQuiesceTime Gauge32,
    msvmsmName WtcsDisplayString,
    msvmsmNumberOfButtons Integer32,
    msvmsmOperationalStatus INTEGER,
    msvmsmOtherEnabledState WtcsDisplayString,
    msvmsmOtherIdentifyingInfo WtcsDisplayString,
    msvmsmPointingType INTEGER,
    msvmsmPowerManagementCapability INTEGER,
    msvmsmPowerManagementSupported TruthValue,
    msvmsmPowerOnHours Gauge32,
    msvmsmRequestedState INTEGER,
    msvmsmResolution Gauge32,
    msvmsmScrollPosition Integer32,
    msvmsmStatus WtcsDisplayString,
    msvmsmStatusDescriptions WtcsDisplayString,
    msvmsmStatusInfo INTEGER,
    msvmsmSystemCreationClassName WtcsDisplayString,
    msvmsmSystemName WtcsDisplayString,
    msvmsmTimeOfLastStateChange DateAndTime,
    msvmsmTotalPowerOnHours Gauge32,
    msvmsmVerticalPosition Integer32
}

msvmsmIndex OBJECT-TYPE
    SYNTAX     Integer32 (1..2147483647)
    MAX-ACCESS read-only
    STATUS     current
    DESCRIPTION
        "The value of this object uniquely identifies the
        instance entry for this class."
    ::= { msvmSyntheticMouseEntry 1 }

msvmsmAbsoluteCoordinates OBJECT-TYPE
    SYNTAX     TruthValue
    MAX-ACCESS read-only
    STATUS     current
    DESCRIPTION
        "If the device uses absolute, rather than relative,
        coordinates"
    ::= { msvmSyntheticMouseEntry 2 }

msvmsmAdditionalAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Additional availability and status of the Device
        in addition to that specified in the Availability
        property. The Availability property denotes the
        primary status and availability of the Device. In
        some cases, this property will not be sufficient to
        denote the complete status of the Device. In those
        cases, the AdditionalAvailability property can be
        used to provide further information. For example,
        the primary Availability of a device might be 'Off
        line' (value=8) or in a low-power state
        (AdditionalAvailability value=14), or the Device
        could be running Diagnostics
        (AdditionalAvailability value=5, 'In Test')."
    ::= { msvmSyntheticMouseEntry 3 }

msvmsmAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Note: The use of this property has been
        deprecated. 
        Deprecated description: The primary availability
        and status of the Device. (Additional status
        information can be specified using the Additional
        Availability array property.) For example, the
        Availability property indicates that the Device is
        running and has full power (value=3), or is in a
        warning (4), test (5), degraded (10) or power save
        state (values 13-15 and 17). The Power Save states
        are defined as follows: Value 13 ('Power Save -
        Unknown') indicates that the Device is known to be
        in a power save mode, but its exact status in this
        mode is unknown; value 14 ('Power Save - Low Power
        Mode') indicates that the Device is in a power save
        state but still functioning, and might exhibit
        degraded performance; value 15 ('Power Save -
        Standby') indicates that the Device is not
        functioning but could be brought to full power
        'quickly'; and value 17 ('Power Save - Warning')
        indicates that the Device is in a warning state,
        but is also in a power save mode."
    ::= { msvmSyntheticMouseEntry 4 }

msvmsmCaption OBJECT-TYPE
    SYNTAX     WtcsDisplayString (SIZE (0..64))
    MAX-ACCESS read-only
    STATUS     current
    DESCRIPTION
        "The Caption property is a short textual
        description (one- line string) of the object."
    ::= { msvmSyntheticMouseEntry 5 }

msvmsmCreationClassName OBJECT-TYPE
    SYNTAX     WtcsDisplayString (SIZE (0..256))
    MAX-ACCESS read-only
    STATUS     current
    DESCRIPTION
        "CreationClassName indicates the name of the class
        or the subclass used in the creation of an
        instance. When used with the other key properties
        of this class, this property allows all instances
        of this class and its subclasses to be uniquely
        identified."
    ::= { msvmSyntheticMouseEntry 6 }

msvmsmDescription OBJECT-TYPE
    SYNTAX     WtcsDisplayString
    MAX-ACCESS read-only
    STATUS     current
    DESCRIPTION
        "The Description property provides a textual
        description of the object."
    ::= { msvmSyntheticMouseEntry 7 }

msvmsmDeviceID OBJECT-TYPE
    SYNTAX     WtcsDisplayString (SIZE (0..64))
    MAX-ACCESS read-only
    STATUS     current
    DESCRIPTION
        "An address or other identifying information used
        to uniquely name the LogicalDevice."
    ::= { msvmSyntheticMouseEntry 8 }

msvmsmElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmSyntheticMouseEntry 9 }

msvmsmEnabledDefault OBJECT-TYPE
    SYNTAX     INTEGER {
        enabled(2),
        disabled(3),
        notApplicable(5),
        enabledbutOffline(6),
        noDefault(7)
    }
    MAX-ACCESS read-only
    STATUS     current
    DESCRIPTION
        "An enumerated value indicating an administrator's
        default or startup configuration for the Enabled
        State of an element. By default, the element is
        'Enabled' (value=2)."
    ::= { msvmSyntheticMouseEntry 10 }

msvmsmEnabledState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "EnabledState is an integer enumeration that
        indicates the enabled and disabled states of an
        element. It can also indicate the transitions
        between these requested states. For example,
        shutting down (value=4) and starting (value=10) are
        transient states between enabled and disabled. The
        following text briefly summarizes the various
        enabled and disabled states: 
        Enabled (2) indicates that the element is or could
        be executing commands, will process any queued
        commands, and queues new requests. 
        Disabled (3) indicates that the element will not
        execute commands and will drop any new requests. 
        Shutting Down (4) indicates that the element is in
        the process of going to a Disabled state. 
        Not Applicable (5) indicates the element does not
        support being enabled or disabled. 
        Enabled but Offline (6) indicates that the element
        might be completing commands, and will drop any new
        requests. 
        Test (7) indicates that the element is in a test
        state. 
        Deferred (8) indicates that the element might be
        completing commands, but will queue any new
        requests. 
        Quiesce (9) indicates that the element is enabled
        but in a restricted mode. The behavior of the
        element is similar to the Enabled state, but it
        processes only a restricted set of commands. All
        other requests are queued. 
        Starting (10) indicates that the element is in the
        process of going to an Enabled state. New requests
        are queued."
    ::= { msvmSyntheticMouseEntry 11 }

msvmsmErrorCleared OBJECT-TYPE
    SYNTAX     TruthValue
    MAX-ACCESS read-only
    STATUS     current
    DESCRIPTION
        "Note: The use of this method is deprecated. 
        Deprecated description: ErrorCleared is a Boolean
        property that indicates that the error reported in
        LastErrorCode is now cleared."
    ::= { msvmSyntheticMouseEntry 12 }

msvmsmErrorDescription OBJECT-TYPE
    SYNTAX     WtcsDisplayString
    MAX-ACCESS read-only
    STATUS     current
    DESCRIPTION
        "Note: The use of this method is deprecated. 
        Deprecated description: ErrorDescription is a
        free-form string that supplies more information
        about the error recorded in LastErrorCode and
        information on any corrective actions that can be
        taken."
    ::= { msvmSyntheticMouseEntry 13 }

msvmsmHandedness OBJECT-TYPE
    SYNTAX     INTEGER {
        unknown(0),
        notApplicable(1),
        rightHandedOperation(2),
        leftHandedOperation(3)
    }
    MAX-ACCESS read-only
    STATUS     current
    DESCRIPTION
        "Integer indicating whether the PointingDevice is
        configured for right (value=2) or left handed
        operation (value=3). Also, the values, 'Unknown'
        (0) and 'Not Applicable' (1), can be defined."
    ::= { msvmSyntheticMouseEntry 14 }

msvmsmHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmSyntheticMouseEntry 15 }

msvmsmHorizontalPosition OBJECT-TYPE
    SYNTAX     Integer32
    MAX-ACCESS read-only
    STATUS     current
    DESCRIPTION
        "Indicates the absolute x-coordinate of the
        pointing device."
    ::= { msvmSyntheticMouseEntry 16 }

msvmsmIdentifyingDescriptions OBJECT-TYPE
    SYNTAX     WtcsDisplayString
    MAX-ACCESS read-only
    STATUS     current
    DESCRIPTION
        "An array of free-form strings providing
        explanations and details behind the entries in the
        OtherIdentifyingInfo array. Note that each entry of
        this array is related to the entry in
        OtherIdentifyingInfo that is located at the same
        index."
    ::= { msvmSyntheticMouseEntry 17 }

msvmsmInstallDate OBJECT-TYPE
    SYNTAX     DateAndTime
    MAX-ACCESS read-only
    STATUS     current
    DESCRIPTION
        "A datetime value that indicates when the object
        was installed. Lack of a value does not indicate
        that the object is not installed."
    ::= { msvmSyntheticMouseEntry 18 }

msvmsmIsLocked OBJECT-TYPE
    SYNTAX     TruthValue
    MAX-ACCESS read-only
    STATUS     current
    DESCRIPTION
        "An indication of whether the Device is locked,
        preventing user input or output."
    ::= { msvmSyntheticMouseEntry 19 }

msvmsmLastErrorCode OBJECT-TYPE
    SYNTAX     Gauge32
    MAX-ACCESS read-only
    STATUS     current
    DESCRIPTION
        "Note: The use of this method is deprecated. 
        Deprecated description: LastErrorCode captures the
        last error code reported by the LogicalDevice."
    ::= { msvmSyntheticMouseEntry 20 }

msvmsmLocationIndicator OBJECT-TYPE
    SYNTAX     INTEGER {
        unknown(0),
        on(2),
        off(3),
        notSupported(4)
    }
    MAX-ACCESS read-only
    STATUS     current
    DESCRIPTION
        "An integer that reflects the state of an indicator
        (e.g., LED) that is part of a device. Reading the
        value gives the current state. Writing the value
        with 'On'/'Off' turns the indicator on/off, other
        values may not be written."
    ::= { msvmSyntheticMouseEntry 21 }

msvmsmMaxQuiesceTime OBJECT-TYPE
    SYNTAX     Gauge32
    UNITS "MilliSeconds"
    MAX-ACCESS read-only
    STATUS     current
    DESCRIPTION
        "Note: The use of this property has been
        deprecated. When evaluating the use of Quiesce, it
        was determined that this single property is not
        adequate for describing when a device will
        automatically exit a quiescent state. In fact, the
        most likely scenario for a device to exit a
        quiescent state was determined to be based on the
        number of outstanding requests queued rather than
        on a maximum time. This decision will be
        re-evaluated and repositioned later. 
        Deprecated description: Maximum time, in
        milliseconds, that a Device can run in a 'Quiesced'
        state. The state is defined in its Availability and
        AdditionalAvailability properties, where 'Quiesced'
        is conveyed by the value 21. What occurs at the end
        of the time limit is device-specific. The Device
        can unquiesce, can be offline, or can take other
        actions. A value of 0 indicates that a Device can
        remain quiesced indefinitely."
    ::= { msvmSyntheticMouseEntry 22 }

msvmsmName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmSyntheticMouseEntry 23 }

msvmsmNumberOfButtons OBJECT-TYPE
    SYNTAX     Integer32
    MAX-ACCESS read-only
    STATUS     current
    DESCRIPTION
        "Number of buttons. If the PointingDevice has no
        buttons, enter 0."
    ::= { msvmSyntheticMouseEntry 24 }

msvmsmOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmSyntheticMouseEntry 25 }

msvmsmOtherEnabledState OBJECT-TYPE
    SYNTAX     WtcsDisplayString
    MAX-ACCESS read-only
    STATUS     current
    DESCRIPTION
        "A string that describes the enabled or disabled
        state of the element when the EnabledState property
        is set to 1 ('Other'). This property must be set to
        null when EnabledState is any value other than 1."
    ::= { msvmSyntheticMouseEntry 26 }

msvmsmOtherIdentifyingInfo OBJECT-TYPE
    SYNTAX     WtcsDisplayString (SIZE (0..256))
    MAX-ACCESS read-only
    STATUS     current
    DESCRIPTION
        "OtherIdentifyingInfo captures data, in addition to
        DeviceID information, that could be used to
        identify a LogicalDevice. For example, you could
        use this property to hold the operating system's
        user-friendly name for the Device."
    ::= { msvmSyntheticMouseEntry 27 }

msvmsmPointingType OBJECT-TYPE
    SYNTAX     INTEGER {
        other(1),
        unknown(2),
        mouse(3),
        trackBall(4),
        trackPoint(5),
        glidePoint(6),
        touchPad(7),
        touchScreen(8),
        mouseOpticalSensor(9)
    }
    MAX-ACCESS read-only
    STATUS     current
    DESCRIPTION
        "The type of the pointing device."
    ::= { msvmSyntheticMouseEntry 28 }

msvmsmPowerManagementCapability OBJECT-TYPE
    SYNTAX     INTEGER {
        unknown(0),
        notSupported(1),
        disabled(2),
        enabled(3),
        powerSavingModesEnteredAutomatic(4),
        powerStateSettable(5),
        powerCyclingSupported(6),
        timedPowerOnSupported(7)
    }
    MAX-ACCESS read-only
    STATUS     current
    DESCRIPTION
        "Note: The use of this property has been
        deprecated. Instead, use the PowerCapabilites
        property in an associated
        PowerManagementCapabilities class. Deprecated
        description: An enumerated array describing the
        power management capabilities of the Device."
    ::= { msvmSyntheticMouseEntry 29 }

msvmsmPowerManagementSupported OBJECT-TYPE
    SYNTAX     TruthValue
    MAX-ACCESS read-only
    STATUS     current
    DESCRIPTION
        "Note: The use of this property has been
        deprecated. Instead, the existence of an associated
        PowerManagementCapabilities class (associated using
        the ElementCapabilities relationship) indicates
        that power management is supported. Deprecated
        description: Boolean that indicates that the Device
        can use power management."
    ::= { msvmSyntheticMouseEntry 30 }

msvmsmPowerOnHours OBJECT-TYPE
    SYNTAX     Gauge32
    UNITS "Hours"
    MAX-ACCESS read-only
    STATUS     current
    DESCRIPTION
        "Note: The use of this method is deprecated. 
        Deprecated description: The number of consecutive
        hours that this Device has been powered on since
        its last power cycle."
    ::= { msvmSyntheticMouseEntry 31 }

msvmsmRequestedState OBJECT-TYPE
    SYNTAX     INTEGER {
        enabled(2),
        disabled(3),
        shutDown(4),
        noChange(5),
        offline(6),
        test(7),
        deferred(8),
        quiesce(9),
        reboot(10),
        reset(11),
        notApplicable(12)
    }
    MAX-ACCESS read-only
    STATUS     current
    DESCRIPTION
        "RequestedState is an integer enumeration that
        indicates the last requested or desired state for
        the element. The actual state of the element is
        represented by EnabledState. This property is
        provided to compare the last requested and current
        enabled or disabled states. Note that when
        EnabledState is set to 5 ('Not Applicable'), then
        this property has no meaning. By default, the
        RequestedState of the element is 5 ('No Change').
        Refer to the EnabledState property description for
        explanations of the values in the RequestedState
        enumeration. 
        
        It should be noted that there are two new values in
        RequestedState that build on the statuses of
        EnabledState. These are 'Reboot' (10) and 'Reset'
        (11). Reboot refers to doing a 'Shut Down' and then
        moving to an 'Enabled' state. Reset indicates that
        the element is first 'Disabled' and then 'Enabled'.
        The distinction between requesting 'Shut Down' and
        'Disabled' should also be noted. Shut Down requests
        an orderly transition to the Disabled state, and
        might involve removing power, to completely erase
        any existing state. The Disabled state requests an
        immediate disabling of the element, such that it
        will not execute or accept any commands or
        processing requests. 
        
        This property is set as the result of a method
        invocation (such as Start or StopService on
        CIM_Service), or can be overridden and defined as
        WRITEable in a subclass. The method approach is
        considered superior to a WRITEable property,
        because it allows an explicit invocation of the
        operation and the return of a result code. 
        
        A particular instance of EnabledLogicalElement
        might not support RequestedStateChange. If this
        occurs, the value 12 ('Not Applicable') is used."
    ::= { msvmSyntheticMouseEntry 32 }

msvmsmResolution OBJECT-TYPE
    SYNTAX     Gauge32
    UNITS "Counts per Inch"
    MAX-ACCESS read-only
    STATUS     current
    DESCRIPTION
        "Tracking resolution of the PointingDevice in
        Counts per Inch."
    ::= { msvmSyntheticMouseEntry 33 }

msvmsmScrollPosition OBJECT-TYPE
    SYNTAX     Integer32
    UNITS "Mickeys"
    MAX-ACCESS read-only
    STATUS     current
    DESCRIPTION
        "Indicates the z-coordinate position of the mouse
        device."
    ::= { msvmSyntheticMouseEntry 34 }

msvmsmStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmSyntheticMouseEntry 35 }

msvmsmStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmSyntheticMouseEntry 36 }

msvmsmStatusInfo OBJECT-TYPE
    SYNTAX     INTEGER {
        other(1),
        unknown(2),
        enabled(3),
        disabled(4),
        notApplicable(5)
    }
    MAX-ACCESS read-only
    STATUS     current
    DESCRIPTION
        "Note: The use of this method is deprecated in lieu
        of a more clearly named property (EnabledState)
        that is inherited from ManagedSystemElement and
        that has additional enumerated values. 
        Deprecated description: The StatusInfo property
        indicates whether the Logical Device is in an
        enabled state (value=3), disabled state (value=4),
        some other state (value=1), or an unknown state
        (value=2). If this property does not apply to the
        LogicalDevice, the value 5 ('Not Applicable')
        should be used. If a Device is
        ('Enabled')(value=3), it has been powered up and is
        configured and operational. The Device might or
        might not be functionally active, depending on
        whether its Availability (or
        AdditionalAvailability) indicates that it is
        ('Running/Full Power')(value=3) or ('Off line')
        (value=8). In an enabled but offline mode, a Device
        might be performing out-of-band requests, such as
        running Diagnostics. If StatusInfo is ('Disabled')
        (value=4), a Device can only be 'enabled' or
        powered off. In a personal computer environment,
        ('Disabled') means that the driver of the device is
        not available in the stack. In other environments,
        a Device can be disabled by removing its
        configuration file. A disabled device is physically
        present in a System and consuming resources, but it
        cannot be communicated with until a driver is
        loaded, a configuration file is loaded, or some
        other 'enabling' activity has occurred."
    ::= { msvmSyntheticMouseEntry 37 }

msvmsmSystemCreationClassName OBJECT-TYPE
    SYNTAX     WtcsDisplayString (SIZE (0..256))
    MAX-ACCESS read-only
    STATUS     current
    DESCRIPTION
        "The CreationClassName of the scoping system."
    ::= { msvmSyntheticMouseEntry 38 }

msvmsmSystemName OBJECT-TYPE
    SYNTAX     WtcsDisplayString (SIZE (0..256))
    MAX-ACCESS read-only
    STATUS     current
    DESCRIPTION
        "The System Name of the scoping system."
    ::= { msvmSyntheticMouseEntry 39 }

msvmsmTimeOfLastStateChange OBJECT-TYPE
    SYNTAX     DateAndTime
    MAX-ACCESS read-only
    STATUS     current
    DESCRIPTION
        "The date or time when the EnabledState of the
        element last changed. If the state of the element
        has not changed and this property is populated,
        then it must be set to a 0 interval value. If a
        state change was requested, but rejected or not yet
        processed, the property must not be updated."
    ::= { msvmSyntheticMouseEntry 40 }

msvmsmTotalPowerOnHours OBJECT-TYPE
    SYNTAX     Gauge32
    UNITS "Hours"
    MAX-ACCESS read-only
    STATUS     current
    DESCRIPTION
        "Note: The use of this method is deprecated. 
        Deprecated description: The total number of hours
        that this Device has been powered on."
    ::= { msvmSyntheticMouseEntry 41 }

msvmsmVerticalPosition OBJECT-TYPE
    SYNTAX     Integer32
    MAX-ACCESS read-only
    STATUS     current
    DESCRIPTION
        "Indicates the absolute y-coordinate of the
        pointing device."
    ::= { msvmSyntheticMouseEntry 42 }

msvmIntegrationComponents OBJECT-IDENTITY
    STATUS     current
    DESCRIPTION
        "Integration components are software components
        that run on top of the guest operating system
        inside of a child partition and as part of the
        virtualization stack in the parent partition to
        provide some level of integration with the parent
        partition. They are used to address problems that
        arise from the high level of isolation provided by
        virtual machines."
    ::= { informantHyperV 3 }

msvmHeartbeatComponentTable OBJECT-TYPE
    SYNTAX     SEQUENCE OF MsvmHeartbeatComponent
    MAX-ACCESS not-accessible
    STATUS     current
    DESCRIPTION
        "Represents the state of the heartbeat component,
        which is responsible for monitoring the state of a
        virtual machine by reporting a heartbeat at regular
        intervals."
    ::= { msvmIntegrationComponents 1 }

msvmHeartbeatComponentEntry OBJECT-TYPE
    SYNTAX     MsvmHeartbeatComponent
    MAX-ACCESS not-accessible
    STATUS     current
    DESCRIPTION
        "None"
    INDEX      { msvmhcIndex }
    ::= { msvmHeartbeatComponentTable 1 }

MsvmHeartbeatComponent ::= SEQUENCE {
    msvmhcIndex Integer32,
    msvmhcAdditionalAvailability INTEGER,
    msvmhcAvailability INTEGER,
    msvmhcCaption WtcsDisplayString,
    msvmhcCreationClassName WtcsDisplayString,
    msvmhcDescription WtcsDisplayString,
    msvmhcDeviceID WtcsDisplayString,
    msvmhcElementName WtcsDisplayString,
    msvmhcEnabledDefault INTEGER,
    msvmhcEnabledState INTEGER,
    msvmhcErrorCleared TruthValue,
    msvmhcErrorDescription WtcsDisplayString,
    msvmhcHealthState INTEGER,
    msvmhcIdentifyingDescriptions WtcsDisplayString,
    msvmhcInstallDate DateAndTime,
    msvmhcLastErrorCode Gauge32,
    msvmhcLocationIndicator INTEGER,
    msvmhcMaxQuiesceTime Gauge32,
    msvmhcName WtcsDisplayString,
    msvmhcOperationalStatus INTEGER,
    msvmhcOtherEnabledState WtcsDisplayString,
    msvmhcOtherIdentifyingInfo WtcsDisplayString,
    msvmhcPowerManagementCapability INTEGER,
    msvmhcPowerManagementSupported TruthValue,
    msvmhcPowerOnHours Gauge32,
    msvmhcRequestedState INTEGER,
    msvmhcStatus WtcsDisplayString,
    msvmhcStatusDescriptions WtcsDisplayString,
    msvmhcStatusInfo INTEGER,
    msvmhcSystemCreationClassName WtcsDisplayString,
    msvmhcSystemName WtcsDisplayString,
    msvmhcTimeOfLastStateChange DateAndTime,
    msvmhcTotalPowerOnHours Gauge32
}

msvmhcIndex OBJECT-TYPE
    SYNTAX     Integer32 (1..2147483647)
    MAX-ACCESS read-only
    STATUS     current
    DESCRIPTION
        "The value of this object uniquely identifies the
        instance entry for this class."
    ::= { msvmHeartbeatComponentEntry 1 }

msvmhcAdditionalAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Additional availability and status of the Device
        in addition to that specified in the Availability
        property. The Availability property denotes the
        primary status and availability of the Device. In
        some cases, this property will not be sufficient to
        denote the complete status of the Device. In those
        cases, the AdditionalAvailability property can be
        used to provide further information. For example,
        the primary Availability of a device might be 'Off
        line' (value=8) or in a low-power state
        (AdditionalAvailability value=14), or the Device
        could be running Diagnostics
        (AdditionalAvailability value=5, 'In Test')."
    ::= { msvmHeartbeatComponentEntry 2 }

msvmhcAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Note: The use of this property has been
        deprecated. 
        Deprecated description: The primary availability
        and status of the Device. (Additional status
        information can be specified using the Additional
        Availability array property.) For example, the
        Availability property indicates that the Device is
        running and has full power (value=3), or is in a
        warning (4), test (5), degraded (10) or power save
        state (values 13-15 and 17). The Power Save states
        are defined as follows: Value 13 ('Power Save -
        Unknown') indicates that the Device is known to be
        in a power save mode, but its exact status in this
        mode is unknown; value 14 ('Power Save - Low Power
        Mode') indicates that the Device is in a power save
        state but still functioning, and might exhibit
        degraded performance; value 15 ('Power Save -
        Standby') indicates that the Device is not
        functioning but could be brought to full power
        'quickly'; and value 17 ('Power Save - Warning')
        indicates that the Device is in a warning state,
        but is also in a power save mode."
    ::= { msvmHeartbeatComponentEntry 3 }

msvmhcCaption OBJECT-TYPE
    SYNTAX     WtcsDisplayString (SIZE (0..64))
    MAX-ACCESS read-only
    STATUS     current
    DESCRIPTION
        "The Caption property is a short textual
        description (one- line string) of the object."
    ::= { msvmHeartbeatComponentEntry 4 }

msvmhcCreationClassName OBJECT-TYPE
    SYNTAX     WtcsDisplayString (SIZE (0..256))
    MAX-ACCESS read-only
    STATUS     current
    DESCRIPTION
        "CreationClassName indicates the name of the class
        or the subclass used in the creation of an
        instance. When used with the other key properties
        of this class, this property allows all instances
        of this class and its subclasses to be uniquely
        identified."
    ::= { msvmHeartbeatComponentEntry 5 }

msvmhcDescription OBJECT-TYPE
    SYNTAX     WtcsDisplayString
    MAX-ACCESS read-only
    STATUS     current
    DESCRIPTION
        "The Description property provides a textual
        description of the object."
    ::= { msvmHeartbeatComponentEntry 6 }

msvmhcDeviceID OBJECT-TYPE
    SYNTAX     WtcsDisplayString (SIZE (0..64))
    MAX-ACCESS read-only
    STATUS     current
    DESCRIPTION
        "An address or other identifying information used
        to uniquely name the LogicalDevice."
    ::= { msvmHeartbeatComponentEntry 7 }

msvmhcElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmHeartbeatComponentEntry 8 }

msvmhcEnabledDefault OBJECT-TYPE
    SYNTAX     INTEGER {
        enabled(2),
        disabled(3),
        notApplicable(5),
        enabledbutOffline(6),
        noDefault(7)
    }
    MAX-ACCESS read-only
    STATUS     current
    DESCRIPTION
        "An enumerated value indicating an administrator's
        default or startup configuration for the Enabled
        State of an element. By default, the element is
        'Enabled' (value=2)."
    ::= { msvmHeartbeatComponentEntry 9 }

msvmhcEnabledState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "EnabledState is an integer enumeration that
        indicates the enabled and disabled states of an
        element. It can also indicate the transitions
        between these requested states. For example,
        shutting down (value=4) and starting (value=10) are
        transient states between enabled and disabled. The
        following text briefly summarizes the various
        enabled and disabled states: 
        Enabled (2) indicates that the element is or could
        be executing commands, will process any queued
        commands, and queues new requests. 
        Disabled (3) indicates that the element will not
        execute commands and will drop any new requests. 
        Shutting Down (4) indicates that the element is in
        the process of going to a Disabled state. 
        Not Applicable (5) indicates the element does not
        support being enabled or disabled. 
        Enabled but Offline (6) indicates that the element
        might be completing commands, and will drop any new
        requests. 
        Test (7) indicates that the element is in a test
        state. 
        Deferred (8) indicates that the element might be
        completing commands, but will queue any new
        requests. 
        Quiesce (9) indicates that the element is enabled
        but in a restricted mode. The behavior of the
        element is similar to the Enabled state, but it
        processes only a restricted set of commands. All
        other requests are queued. 
        Starting (10) indicates that the element is in the
        process of going to an Enabled state. New requests
        are queued."
    ::= { msvmHeartbeatComponentEntry 10 }

msvmhcErrorCleared OBJECT-TYPE
    SYNTAX     TruthValue
    MAX-ACCESS read-only
    STATUS     current
    DESCRIPTION
        "Note: The use of this method is deprecated. 
        Deprecated description: ErrorCleared is a Boolean
        property that indicates that the error reported in
        LastErrorCode is now cleared."
    ::= { msvmHeartbeatComponentEntry 11 }

msvmhcErrorDescription OBJECT-TYPE
    SYNTAX     WtcsDisplayString
    MAX-ACCESS read-only
    STATUS     current
    DESCRIPTION
        "Note: The use of this method is deprecated. 
        Deprecated description: ErrorDescription is a
        free-form string that supplies more information
        about the error recorded in LastErrorCode and
        information on any corrective actions that can be
        taken."
    ::= { msvmHeartbeatComponentEntry 12 }

msvmhcHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmHeartbeatComponentEntry 13 }

msvmhcIdentifyingDescriptions OBJECT-TYPE
    SYNTAX     WtcsDisplayString
    MAX-ACCESS read-only
    STATUS     current
    DESCRIPTION
        "An array of free-form strings providing
        explanations and details behind the entries in the
        OtherIdentifyingInfo array. Note that each entry of
        this array is related to the entry in
        OtherIdentifyingInfo that is located at the same
        index."
    ::= { msvmHeartbeatComponentEntry 14 }

msvmhcInstallDate OBJECT-TYPE
    SYNTAX     DateAndTime
    MAX-ACCESS read-only
    STATUS     current
    DESCRIPTION
        "A datetime value that indicates when the object
        was installed. Lack of a value does not indicate
        that the object is not installed."
    ::= { msvmHeartbeatComponentEntry 15 }

msvmhcLastErrorCode OBJECT-TYPE
    SYNTAX     Gauge32
    MAX-ACCESS read-only
    STATUS     current
    DESCRIPTION
        "Note: The use of this method is deprecated. 
        Deprecated description: LastErrorCode captures the
        last error code reported by the LogicalDevice."
    ::= { msvmHeartbeatComponentEntry 16 }

msvmhcLocationIndicator OBJECT-TYPE
    SYNTAX     INTEGER {
        unknown(0),
        on(2),
        off(3),
        notSupported(4)
    }
    MAX-ACCESS read-only
    STATUS     current
    DESCRIPTION
        "An integer that reflects the state of an indicator
        (e.g., LED) that is part of a device. Reading the
        value gives the current state. Writing the value
        with 'On'/'Off' turns the indicator on/off, other
        values may not be written."
    ::= { msvmHeartbeatComponentEntry 17 }

msvmhcMaxQuiesceTime OBJECT-TYPE
    SYNTAX     Gauge32
    UNITS "MilliSeconds"
    MAX-ACCESS read-only
    STATUS     current
    DESCRIPTION
        "Note: The use of this property has been
        deprecated. When evaluating the use of Quiesce, it
        was determined that this single property is not
        adequate for describing when a device will
        automatically exit a quiescent state. In fact, the
        most likely scenario for a device to exit a
        quiescent state was determined to be based on the
        number of outstanding requests queued rather than
        on a maximum time. This decision will be
        re-evaluated and repositioned later. 
        Deprecated description: Maximum time, in
        milliseconds, that a Device can run in a 'Quiesced'
        state. The state is defined in its Availability and
        AdditionalAvailability properties, where 'Quiesced'
        is conveyed by the value 21. What occurs at the end
        of the time limit is device-specific. The Device
        can unquiesce, can be offline, or can take other
        actions. A value of 0 indicates that a Device can
        remain quiesced indefinitely."
    ::= { msvmHeartbeatComponentEntry 18 }

msvmhcName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmHeartbeatComponentEntry 19 }

msvmhcOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmHeartbeatComponentEntry 20 }

msvmhcOtherEnabledState OBJECT-TYPE
    SYNTAX     WtcsDisplayString
    MAX-ACCESS read-only
    STATUS     current
    DESCRIPTION
        "A string that describes the enabled or disabled
        state of the element when the EnabledState property
        is set to 1 ('Other'). This property must be set to
        null when EnabledState is any value other than 1."
    ::= { msvmHeartbeatComponentEntry 21 }

msvmhcOtherIdentifyingInfo OBJECT-TYPE
    SYNTAX     WtcsDisplayString (SIZE (0..256))
    MAX-ACCESS read-only
    STATUS     current
    DESCRIPTION
        "OtherIdentifyingInfo captures data, in addition to
        DeviceID information, that could be used to
        identify a LogicalDevice. For example, you could
        use this property to hold the operating system's
        user-friendly name for the Device."
    ::= { msvmHeartbeatComponentEntry 22 }

msvmhcPowerManagementCapability OBJECT-TYPE
    SYNTAX     INTEGER {
        unknown(0),
        notSupported(1),
        disabled(2),
        enabled(3),
        powerSavingModesEnteredAutomatic(4),
        powerStateSettable(5),
        powerCyclingSupported(6),
        timedPowerOnSupported(7)
    }
    MAX-ACCESS read-only
    STATUS     current
    DESCRIPTION
        "Note: The use of this property has been
        deprecated. Instead, use the PowerCapabilites
        property in an associated
        PowerManagementCapabilities class. Deprecated
        description: An enumerated array describing the
        power management capabilities of the Device."
    ::= { msvmHeartbeatComponentEntry 23 }

msvmhcPowerManagementSupported OBJECT-TYPE
    SYNTAX     TruthValue
    MAX-ACCESS read-only
    STATUS     current
    DESCRIPTION
        "Note: The use of this property has been
        deprecated. Instead, the existence of an associated
        PowerManagementCapabilities class (associated using
        the ElementCapabilities relationship) indicates
        that power management is supported. Deprecated
        description: Boolean that indicates that the Device
        can use power management."
    ::= { msvmHeartbeatComponentEntry 24 }

msvmhcPowerOnHours OBJECT-TYPE
    SYNTAX     Gauge32
    UNITS "Hours"
    MAX-ACCESS read-only
    STATUS     current
    DESCRIPTION
        "Note: The use of this method is deprecated. 
        Deprecated description: The number of consecutive
        hours that this Device has been powered on since
        its last power cycle."
    ::= { msvmHeartbeatComponentEntry 25 }

msvmhcRequestedState OBJECT-TYPE
    SYNTAX     INTEGER {
        enabled(2),
        disabled(3),
        shutDown(4),
        noChange(5),
        offline(6),
        test(7),
        deferred(8),
        quiesce(9),
        reboot(10),
        reset(11),
        notApplicable(12)
    }
    MAX-ACCESS read-only
    STATUS     current
    DESCRIPTION
        "RequestedState is an integer enumeration that
        indicates the last requested or desired state for
        the element. The actual state of the element is
        represented by EnabledState. This property is
        provided to compare the last requested and current
        enabled or disabled states. Note that when
        EnabledState is set to 5 ('Not Applicable'), then
        this property has no meaning. By default, the
        RequestedState of the element is 5 ('No Change').
        Refer to the EnabledState property description for
        explanations of the values in the RequestedState
        enumeration. 
        
        It should be noted that there are two new values in
        RequestedState that build on the statuses of
        EnabledState. These are 'Reboot' (10) and 'Reset'
        (11). Reboot refers to doing a 'Shut Down' and then
        moving to an 'Enabled' state. Reset indicates that
        the element is first 'Disabled' and then 'Enabled'.
        The distinction between requesting 'Shut Down' and
        'Disabled' should also be noted. Shut Down requests
        an orderly transition to the Disabled state, and
        might involve removing power, to completely erase
        any existing state. The Disabled state requests an
        immediate disabling of the element, such that it
        will not execute or accept any commands or
        processing requests. 
        
        This property is set as the result of a method
        invocation (such as Start or StopService on
        CIM_Service), or can be overridden and defined as
        WRITEable in a subclass. The method approach is
        considered superior to a WRITEable property,
        because it allows an explicit invocation of the
        operation and the return of a result code. 
        
        A particular instance of EnabledLogicalElement
        might not support RequestedStateChange. If this
        occurs, the value 12 ('Not Applicable') is used."
    ::= { msvmHeartbeatComponentEntry 26 }

msvmhcStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmHeartbeatComponentEntry 27 }

msvmhcStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmHeartbeatComponentEntry 28 }

msvmhcStatusInfo OBJECT-TYPE
    SYNTAX     INTEGER {
        other(1),
        unknown(2),
        enabled(3),
        disabled(4),
        notApplicable(5)
    }
    MAX-ACCESS read-only
    STATUS     current
    DESCRIPTION
        "Note: The use of this method is deprecated in lieu
        of a more clearly named property (EnabledState)
        that is inherited from ManagedSystemElement and
        that has additional enumerated values. 
        Deprecated description: The StatusInfo property
        indicates whether the Logical Device is in an
        enabled state (value=3), disabled state (value=4),
        some other state (value=1), or an unknown state
        (value=2). If this property does not apply to the
        LogicalDevice, the value 5 ('Not Applicable')
        should be used. If a Device is
        ('Enabled')(value=3), it has been powered up and is
        configured and operational. The Device might or
        might not be functionally active, depending on
        whether its Availability (or
        AdditionalAvailability) indicates that it is
        ('Running/Full Power')(value=3) or ('Off line')
        (value=8). In an enabled but offline mode, a Device
        might be performing out-of-band requests, such as
        running Diagnostics. If StatusInfo is ('Disabled')
        (value=4), a Device can only be 'enabled' or
        powered off. In a personal computer environment,
        ('Disabled') means that the driver of the device is
        not available in the stack. In other environments,
        a Device can be disabled by removing its
        configuration file. A disabled device is physically
        present in a System and consuming resources, but it
        cannot be communicated with until a driver is
        loaded, a configuration file is loaded, or some
        other 'enabling' activity has occurred."
    ::= { msvmHeartbeatComponentEntry 29 }

msvmhcSystemCreationClassName OBJECT-TYPE
    SYNTAX     WtcsDisplayString (SIZE (0..256))
    MAX-ACCESS read-only
    STATUS     current
    DESCRIPTION
        "The CreationClassName of the scoping system."
    ::= { msvmHeartbeatComponentEntry 30 }

msvmhcSystemName OBJECT-TYPE
    SYNTAX     WtcsDisplayString (SIZE (0..256))
    MAX-ACCESS read-only
    STATUS     current
    DESCRIPTION
        "The System Name of the scoping system."
    ::= { msvmHeartbeatComponentEntry 31 }

msvmhcTimeOfLastStateChange OBJECT-TYPE
    SYNTAX     DateAndTime
    MAX-ACCESS read-only
    STATUS     current
    DESCRIPTION
        "The date or time when the EnabledState of the
        element last changed. If the state of the element
        has not changed and this property is populated,
        then it must be set to a 0 interval value. If a
        state change was requested, but rejected or not yet
        processed, the property must not be updated."
    ::= { msvmHeartbeatComponentEntry 32 }

msvmhcTotalPowerOnHours OBJECT-TYPE
    SYNTAX     Gauge32
    UNITS "Hours"
    MAX-ACCESS read-only
    STATUS     current
    DESCRIPTION
        "Note: The use of this method is deprecated. 
        Deprecated description: The total number of hours
        that this Device has been powered on."
    ::= { msvmHeartbeatComponentEntry 33 }

msvmHeartbeatCmpSettingDataTable OBJECT-TYPE
    SYNTAX     SEQUENCE OF MsvmHeartbeatCmpSettingData
    MAX-ACCESS not-accessible
    STATUS     current
    DESCRIPTION
        "Represents the configured state of the heartbeat
        component."
    ::= { msvmIntegrationComponents 2 }

msvmHeartbeatCmpSettingDataEntry OBJECT-TYPE
    SYNTAX     MsvmHeartbeatCmpSettingData
    MAX-ACCESS not-accessible
    STATUS     current
    DESCRIPTION
        "None"
    INDEX      { msvmhcsdIndex }
    ::= { msvmHeartbeatCmpSettingDataTable 1 }

MsvmHeartbeatCmpSettingData ::= SEQUENCE {
    msvmhcsdIndex Integer32,
    msvmhcsdAddress WtcsDisplayString,
    msvmhcsdAllocationUnits WtcsDisplayString,
    msvmhcsdAutomaticAllocation TruthValue,
    msvmhcsdAutomaticDeallocation TruthValue,
    msvmhcsdCaption WtcsDisplayString,
    msvmhcsdConnection WtcsDisplayString,
    msvmhcsdConsumerVisibility INTEGER,
    msvmhcsdDescription WtcsDisplayString,
    msvmhcsdElementName WtcsDisplayString,
    msvmhcsdEnabledState Integer32,
    msvmhcsdErrorThreshold Gauge32,
    msvmhcsdHostResource WtcsDisplayString,
    msvmhcsdInstanceID WtcsDisplayString,
    msvmhcsdInterval Gauge32,
    msvmhcsdLatency Gauge32,
    msvmhcsdLimit Gauge32,
    msvmhcsdMappingBehavior INTEGER,
    msvmhcsdOtherResourceType WtcsDisplayString,
    msvmhcsdParent WtcsDisplayString,
    msvmhcsdPoolID WtcsDisplayString,
    msvmhcsdReservation Gauge32,
    msvmhcsdResourceSubType WtcsDisplayString,
    msvmhcsdResourceType INTEGER,
    msvmhcsdVirtualQuantity Gauge32,
    msvmhcsdWeight Gauge32
}

msvmhcsdIndex OBJECT-TYPE
    SYNTAX     Integer32 (1..2147483647)
    MAX-ACCESS read-only
    STATUS     current
    DESCRIPTION
        "The value of this object uniquely identifies the
        instance entry for this class."
    ::= { msvmHeartbeatCmpSettingDataEntry 1 }

msvmhcsdAddress OBJECT-TYPE
    SYNTAX     WtcsDisplayString
    MAX-ACCESS read-only
    STATUS     current
    DESCRIPTION
        "The address of the resource.For example, the MAC
        address of a Ethernet port."
    ::= { msvmHeartbeatCmpSettingDataEntry 2 }

msvmhcsdAllocationUnits OBJECT-TYPE
    SYNTAX     WtcsDisplayString
    MAX-ACCESS read-only
    STATUS     current
    DESCRIPTION
        "This property specifies the units of allocation
        used by the Reservation and Limit properties.  For
        example, when ResourceType=Processor,
        AllocationUnits may be set to MHZ. When
        ResourceType=Memory, AllocationUnits may be set to
        MB"
    ::= { msvmHeartbeatCmpSettingDataEntry 3 }

msvmhcsdAutomaticAllocation OBJECT-TYPE
    SYNTAX     TruthValue
    MAX-ACCESS read-only
    STATUS     current
    DESCRIPTION
        "This property specifies if the resource will be
        automatically allocated.  For example when set to
        true, when the consuming virtual computer system is
        powered on, this resource would be allocated.  A
        value of false indicates the resource must be
        explicitly allocated.  For example, the setting may
        represent removable media (cdrom, floppy, etc.)
        where at power on time, the media isnot present. 
        An explicit operation is required to allocate the
        resource."
    ::= { msvmHeartbeatCmpSettingDataEntry 4 }

msvmhcsdAutomaticDeallocation OBJECT-TYPE
    SYNTAX     TruthValue
    MAX-ACCESS read-only
    STATUS     current
    DESCRIPTION
        "This property specifies if the resource will be
        automatically de-allocated.  For example, when set
        to true, when the consuming virtual computer system
        is powered off, this resource would be
        de-allocated.  When set to false, the resource will
        remain allocated and must be explicitly
        de-allocated."
    ::= { msvmHeartbeatCmpSettingDataEntry 5 }

msvmhcsdCaption OBJECT-TYPE
    SYNTAX     WtcsDisplayString (SIZE (0..64))
    MAX-ACCESS read-only
    STATUS     current
    DESCRIPTION
        "The Caption property is a short textual
        description (one- line string) of the object."
    ::= { msvmHeartbeatCmpSettingDataEntry 6 }

msvmhcsdConnection OBJECT-TYPE
    SYNTAX     WtcsDisplayString
    MAX-ACCESS read-only
    STATUS     current
    DESCRIPTION
        "The thing to which this resource is connected. 
        For example, a named network or switch port."
    ::= { msvmHeartbeatCmpSettingDataEntry 7 }

msvmhcsdConsumerVisibility OBJECT-TYPE
    SYNTAX     INTEGER {
        unknown(0),
        passedThrough(2),
        virtualized(3),
        notrepresented(4)
    }
    MAX-ACCESS read-only
    STATUS     current
    DESCRIPTION
        "Describes the consumers visibility to the
        allocated  resource.
        A value of 'Passed-Through' indicates the
        underlying or host resource is utilized and passed
        through to the consumer, possibly using
        partitioning. At least one item shall be present in
        the DeviceID property.  
        A value of 'Virtualized' indicates the resource is
        virtualized and may not map directly to an
        underlying/host resource. Some implementations may
        support specific assignment for virtualized
        resources, in which case the host resource(s) are
        exposed using the DeviceID property. 
        A value of 'Not represented' indicates a
        representation of the resource does not exist
        within the context of the resource consumer."
    ::= { msvmHeartbeatCmpSettingDataEntry 8 }

msvmhcsdDescription OBJECT-TYPE
    SYNTAX     WtcsDisplayString
    MAX-ACCESS read-only
    STATUS     current
    DESCRIPTION
        "The Description property provides a textual
        description of the object."
    ::= { msvmHeartbeatCmpSettingDataEntry 9 }

msvmhcsdElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmHeartbeatCmpSettingDataEntry 10 }

msvmhcsdEnabledState OBJECT-TYPE
    SYNTAX     Integer32
    MAX-ACCESS read-only
    STATUS     current
    DESCRIPTION
        "An integer enumeration that indicates the enabled
        and disabled states of an element. This property is
        inherited from CIM_EnabledLogicalElement and is
        either set to 2 ('Enabled') or 3 ('Disabled')."
    ::= { msvmHeartbeatCmpSettingDataEntry 11 }

msvmhcsdErrorThreshold OBJECT-TYPE
    SYNTAX     Gauge32
    MAX-ACCESS read-only
    STATUS     current
    DESCRIPTION
        "An enumerated value indicating an administrator's
        startup configuration for the Enabled State of an
        element. This property is inherited from
        CIM_ResourceAllocationSettingData and is always set
        to 2 ('Enabled')."
    ::= { msvmHeartbeatCmpSettingDataEntry 12 }

msvmhcsdHostResource OBJECT-TYPE
    SYNTAX     WtcsDisplayString
    MAX-ACCESS read-only
    STATUS     current
    DESCRIPTION
        "This property exposes specific assignment to host
        or underlying resources.        The embedded
        instances shall contain only key properties and be
        treated as Object Paths. If the virtual resource
        may be scheduled on a number of underlying
        resources, this property shall be left NULL. In
        that case, the DeviceAllocatedFromPool or
        ResourceAllocationFromPool associations may be used
        to determine the pool of host resources this
        virtual resource may be scheduled on. If specific
        assignment is utilized, all underlying resources
        used by this virtual resource shall be listed in
        this array.  Typically the array will contain one
        item, however for aggregate allocations, such as
        multiple processors, multiple host resources may be
        specified."
    ::= { msvmHeartbeatCmpSettingDataEntry 13 }

msvmhcsdInstanceID OBJECT-TYPE
    SYNTAX     WtcsDisplayString
    MAX-ACCESS read-only
    STATUS     current
    DESCRIPTION
        "Within the scope of the instantiating Namespace,
        InstanceID opaquely and uniquely identifies an
        instance of this class. To ensure uniqueness within
        the NameSpace, the value of InstanceID should be
        constructed using the following 'preferred'
        algorithm: 
        <OrgID>:<LocalID> 
        Where <OrgID> and <LocalID> are separated by a
        colon (:), and where <OrgID> must include a
        copyrighted, trademarked, or otherwise unique name
        that is owned by the business entity that is
        creating or defining the InstanceID or that is a
        registered ID assigned to the business entity by a
        recognized global authority. (This requirement is
        similar to the <Schema Name>_<Class Name> structure
        of Schema class names.) In addition, to ensure
        uniqueness, <OrgID> must not contain a colon (:).
        When using this algorithm, the first colon to
        appear in InstanceID must appear between <OrgID>
        and <LocalID>. 
        <LocalID> is chosen by the business entity and
        should not be reused to identify different
        underlying (real-world) elements. If the above
        'preferred' algorithm is not used, the defining
        entity must assure that the resulting InstanceID is
        not reused across any InstanceIDs produced by this
        or other providers for the NameSpace of this
        instance. 
        For DMTF-defined instances, the 'preferred'
        algorithm must be used with the <OrgID> set to
        CIM."
    ::= { msvmHeartbeatCmpSettingDataEntry 14 }

msvmhcsdInterval OBJECT-TYPE
    SYNTAX     Gauge32
    MAX-ACCESS read-only
    STATUS     current
    DESCRIPTION
        "Specifies the interval between ping attempts, in
        milliseconds. This property is inherited from
        CIM_ResourceAllocationSettingData and is always set
        to 2000."
    ::= { msvmHeartbeatCmpSettingDataEntry 15 }

msvmhcsdLatency OBJECT-TYPE
    SYNTAX     Gauge32
    MAX-ACCESS read-only
    STATUS     current
    DESCRIPTION
        "Specifies the maximum expected latency between a
        request ping and a response, in milliseconds,
        before a given request is considered dropped. This
        property is inherited from
        CIM_ResourceAllocationSettingData and is always set
        to 1000."
    ::= { msvmHeartbeatCmpSettingDataEntry 16 }

msvmhcsdLimit OBJECT-TYPE
    SYNTAX     Gauge32
    MAX-ACCESS read-only
    STATUS     current
    DESCRIPTION
        "This property specifies the upper bound, or
        maximum amount of resource that will be granted for
        this allocation. For example, a system which
        supports memory paging may support setting the
        Limit of a Memory allocation below that of the
        VirtualQuantity, thus forcing paging to occur for
        this allocation."
    ::= { msvmHeartbeatCmpSettingDataEntry 17 }

msvmhcsdMappingBehavior OBJECT-TYPE
    SYNTAX     INTEGER {
        unknown(0),
        notSupported(1),
        dedicated(2),
        softAffinity(3),
        hardAffinity(4)
    }
    MAX-ACCESS read-only
    STATUS     current
    DESCRIPTION
        "Specifies how this resource maps to underlying
        resourcesIf the HostResource array contains any
        entries, this property reflects how the resource
        maps to those specific resources."
    ::= { msvmHeartbeatCmpSettingDataEntry 18 }

msvmhcsdOtherResourceType OBJECT-TYPE
    SYNTAX     WtcsDisplayString
    MAX-ACCESS read-only
    STATUS     current
    DESCRIPTION
        "A string that describes the resource type when a
        well defined value is not available and
        ResourceType has the value 'Other'."
    ::= { msvmHeartbeatCmpSettingDataEntry 19 }

msvmhcsdParent OBJECT-TYPE
    SYNTAX     WtcsDisplayString
    MAX-ACCESS read-only
    STATUS     current
    DESCRIPTION
        "The Parent of the resource.  For example, a
        controller for the current allocation"
    ::= { msvmHeartbeatCmpSettingDataEntry 20 }

msvmhcsdPoolID OBJECT-TYPE
    SYNTAX     WtcsDisplayString
    MAX-ACCESS read-only
    STATUS     current
    DESCRIPTION
        "This property specifies which ResourcePool the
        resource is currently allocated from, or which
        ResourcePool the resource will be allocated from
        when the allocation occurs."
    ::= { msvmHeartbeatCmpSettingDataEntry 21 }

msvmhcsdReservation OBJECT-TYPE
    SYNTAX     Gauge32
    MAX-ACCESS read-only
    STATUS     current
    DESCRIPTION
        "This property specifies the amount of resource
        guaranteed to be available for this allocation.  On
        system which support over-commitment of resources,
        this value is typically used for admission control
        to prevent an an allocation from being accepted
        thus preventing starvation."
    ::= { msvmHeartbeatCmpSettingDataEntry 22 }

msvmhcsdResourceSubType OBJECT-TYPE
    SYNTAX     WtcsDisplayString
    MAX-ACCESS read-only
    STATUS     current
    DESCRIPTION
        "A string describing an implementation specific
        sub-type for this resource.  For example, this may
        be used to distinguish different models of the same
        resource type."
    ::= { msvmHeartbeatCmpSettingDataEntry 23 }

msvmhcsdResourceType OBJECT-TYPE
    SYNTAX     INTEGER {
        other(1),
        computerSystem(2),
        processor(3),
        memory(4),
        ideController(5),
        parallelSCSIHBA(6),
        fcHBA(7),
        iSCSIHBA(8),
        ibHCA(9),
        ethernetAdapter(10),
        iOSlot(11),
        iODevice(12),
        floppyDrive(13),
        cdDrive(14),
        dvddrive(15),
        serialport(16),
        parallelport(17),
        usbController(18),
        graphicscontroller(19),
        storageExtent(20),
        disk(21),
        tape(22),
        otherstoragedevice(23),
        firewireController(24),
        partitionableUnit(25),
        basePartitionableUnit(26),
        powerSupply(27),
        coolingDevice(28),
        dmtfreserved(29)
    }
    MAX-ACCESS read-only
    STATUS     current
    DESCRIPTION
        "The type of resource this allocation setting
        represents."
    ::= { msvmHeartbeatCmpSettingDataEntry 24 }

msvmhcsdVirtualQuantity OBJECT-TYPE
    SYNTAX     Gauge32
    MAX-ACCESS read-only
    STATUS     current
    DESCRIPTION
        "This property specifies the quantity of resources
        presented to the consumer.  For example, when
        ResourceType=Processor,  this property would
        reflect the number of discrete Processors presented
        to the virtual computer system.  When
        ResourceType=Memory, this property could reflect
        the number of MB reported to the virtual computer
        system."
    ::= { msvmHeartbeatCmpSettingDataEntry 25 }

msvmhcsdWeight OBJECT-TYPE
    SYNTAX     Gauge32
    MAX-ACCESS read-only
    STATUS     current
    DESCRIPTION
        "This property specifies a relative priority for
        this allocation in relation to other allocations
        from the same ResourcePool.  This property has no
        unit of measure, and is only relevant when compared
        to other allocations vying for the same host
        resources."
    ::= { msvmHeartbeatCmpSettingDataEntry 26 }

msvmKvpExchangeComponentTable OBJECT-TYPE
    SYNTAX     SEQUENCE OF MsvmKvpExchangeComponent
    MAX-ACCESS not-accessible
    STATUS     current
    DESCRIPTION
        "Represents the state of the key/value pair
        exchange component, which provides a mechanism to
        exchange data between the virtual machine and the
        operating system running on the parent partition."
    ::= { msvmIntegrationComponents 3 }

msvmKvpExchangeComponentEntry OBJECT-TYPE
    SYNTAX     MsvmKvpExchangeComponent
    MAX-ACCESS not-accessible
    STATUS     current
    DESCRIPTION
        "None"
    INDEX      { msvmkvpIndex }
    ::= { msvmKvpExchangeComponentTable 1 }

MsvmKvpExchangeComponent ::= SEQUENCE {
    msvmkvpIndex Integer32,
    msvmkvpAdditionalAvailability INTEGER,
    msvmkvpAvailability INTEGER,
    msvmkvpCaption WtcsDisplayString,
    msvmkvpCreationClassName WtcsDisplayString,
    msvmkvpDescription WtcsDisplayString,
    msvmkvpDeviceID WtcsDisplayString,
    msvmkvpElementName WtcsDisplayString,
    msvmkvpEnabledDefault INTEGER,
    msvmkvpEnabledState INTEGER,
    msvmkvpErrorCleared TruthValue,
    msvmkvpErrorDescription WtcsDisplayString,
    msvmkvpGuestExchangeItems WtcsDisplayString,
    msvmkvpGuestIntrinsicExchangeItm WtcsDisplayString,
    msvmkvpHealthState INTEGER,
    msvmkvpIdentifyingDescriptions WtcsDisplayString,
    msvmkvpInstallDate DateAndTime,
    msvmkvpLastErrorCode Gauge32,
    msvmkvpLocationIndicator INTEGER,
    msvmkvpMaxQuiesceTime Gauge32,
    msvmkvpName WtcsDisplayString,
    msvmkvpOperationalStatus INTEGER,
    msvmkvpOtherEnabledState WtcsDisplayString,
    msvmkvpOtherIdentifyingInfo WtcsDisplayString,
    msvmkvpPowerManagementCapability INTEGER,
    msvmkvpPowerManagementSupported TruthValue,
    msvmkvpPowerOnHours Gauge32,
    msvmkvpRequestedState INTEGER,
    msvmkvpStatus WtcsDisplayString,
    msvmkvpStatusDescriptions WtcsDisplayString,
    msvmkvpStatusInfo INTEGER,
    msvmkvpSystemCreationClassName WtcsDisplayString,
    msvmkvpSystemName WtcsDisplayString,
    msvmkvpTimeOfLastStateChange DateAndTime,
    msvmkvpTotalPowerOnHours Gauge32
}

msvmkvpIndex OBJECT-TYPE
    SYNTAX     Integer32 (1..2147483647)
    MAX-ACCESS read-only
    STATUS     current
    DESCRIPTION
        "The value of this object uniquely identifies the
        instance entry for this class."
    ::= { msvmKvpExchangeComponentEntry 1 }

msvmkvpAdditionalAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Additional availability and status of the Device
        in addition to that specified in the Availability
        property. The Availability property denotes the
        primary status and availability of the Device. In
        some cases, this property will not be sufficient to
        denote the complete status of the Device. In those
        cases, the AdditionalAvailability property can be
        used to provide further information. For example,
        the primary Availability of a device might be 'Off
        line' (value=8) or in a low-power state
        (AdditionalAvailability value=14), or the Device
        could be running Diagnostics
        (AdditionalAvailability value=5, 'In Test')."
    ::= { msvmKvpExchangeComponentEntry 2 }

msvmkvpAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Note: The use of this property has been
        deprecated. 
        Deprecated description: The primary availability
        and status of the Device. (Additional status
        information can be specified using the Additional
        Availability array property.) For example, the
        Availability property indicates that the Device is
        running and has full power (value=3), or is in a
        warning (4), test (5), degraded (10) or power save
        state (values 13-15 and 17). The Power Save states
        are defined as follows: Value 13 ('Power Save -
        Unknown') indicates that the Device is known to be
        in a power save mode, but its exact status in this
        mode is unknown; value 14 ('Power Save - Low Power
        Mode') indicates that the Device is in a power save
        state but still functioning, and might exhibit
        degraded performance; value 15 ('Power Save -
        Standby') indicates that the Device is not
        functioning but could be brought to full power
        'quickly'; and value 17 ('Power Save - Warning')
        indicates that the Device is in a warning state,
        but is also in a power save mode."
    ::= { msvmKvpExchangeComponentEntry 3 }

msvmkvpCaption OBJECT-TYPE
    SYNTAX     WtcsDisplayString (SIZE (0..64))
    MAX-ACCESS read-only
    STATUS     current
    DESCRIPTION
        "The Caption property is a short textual
        description (one- line string) of the object."
    ::= { msvmKvpExchangeComponentEntry 4 }

msvmkvpCreationClassName OBJECT-TYPE
    SYNTAX     WtcsDisplayString (SIZE (0..256))
    MAX-ACCESS read-only
    STATUS     current
    DESCRIPTION
        "CreationClassName indicates the name of the class
        or the subclass used in the creation of an
        instance. When used with the other key properties
        of this class, this property allows all instances
        of this class and its subclasses to be uniquely
        identified."
    ::= { msvmKvpExchangeComponentEntry 5 }

msvmkvpDescription OBJECT-TYPE
    SYNTAX     WtcsDisplayString
    MAX-ACCESS read-only
    STATUS     current
    DESCRIPTION
        "The Description property provides a textual
        description of the object."
    ::= { msvmKvpExchangeComponentEntry 6 }

msvmkvpDeviceID OBJECT-TYPE
    SYNTAX     WtcsDisplayString (SIZE (0..64))
    MAX-ACCESS read-only
    STATUS     current
    DESCRIPTION
        "An address or other identifying information used
        to uniquely name the LogicalDevice."
    ::= { msvmKvpExchangeComponentEntry 7 }

msvmkvpElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmKvpExchangeComponentEntry 8 }

msvmkvpEnabledDefault OBJECT-TYPE
    SYNTAX     INTEGER {
        enabled(2),
        disabled(3),
        notApplicable(5),
        enabledbutOffline(6),
        noDefault(7)
    }
    MAX-ACCESS read-only
    STATUS     current
    DESCRIPTION
        "An enumerated value indicating an administrator's
        default or startup configuration for the Enabled
        State of an element. By default, the element is
        'Enabled' (value=2)."
    ::= { msvmKvpExchangeComponentEntry 9 }

msvmkvpEnabledState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "EnabledState is an integer enumeration that
        indicates the enabled and disabled states of an
        element. It can also indicate the transitions
        between these requested states. For example,
        shutting down (value=4) and starting (value=10) are
        transient states between enabled and disabled. The
        following text briefly summarizes the various
        enabled and disabled states: 
        Enabled (2) indicates that the element is or could
        be executing commands, will process any queued
        commands, and queues new requests. 
        Disabled (3) indicates that the element will not
        execute commands and will drop any new requests. 
        Shutting Down (4) indicates that the element is in
        the process of going to a Disabled state. 
        Not Applicable (5) indicates the element does not
        support being enabled or disabled. 
        Enabled but Offline (6) indicates that the element
        might be completing commands, and will drop any new
        requests. 
        Test (7) indicates that the element is in a test
        state. 
        Deferred (8) indicates that the element might be
        completing commands, but will queue any new
        requests. 
        Quiesce (9) indicates that the element is enabled
        but in a restricted mode. The behavior of the
        element is similar to the Enabled state, but it
        processes only a restricted set of commands. All
        other requests are queued. 
        Starting (10) indicates that the element is in the
        process of going to an Enabled state. New requests
        are queued."
    ::= { msvmKvpExchangeComponentEntry 10 }

msvmkvpErrorCleared OBJECT-TYPE
    SYNTAX     TruthValue
    MAX-ACCESS read-only
    STATUS     current
    DESCRIPTION
        "Note: The use of this method is deprecated. 
        Deprecated description: ErrorCleared is a Boolean
        property that indicates that the error reported in
        LastErrorCode is now cleared."
    ::= { msvmKvpExchangeComponentEntry 11 }

msvmkvpErrorDescription OBJECT-TYPE
    SYNTAX     WtcsDisplayString
    MAX-ACCESS read-only
    STATUS     current
    DESCRIPTION
        "Note: The use of this method is deprecated. 
        Deprecated description: ErrorDescription is a
        free-form string that supplies more information
        about the error recorded in LastErrorCode and
        information on any corrective actions that can be
        taken."
    ::= { msvmKvpExchangeComponentEntry 12 }

msvmkvpGuestExchangeItems OBJECT-TYPE
    SYNTAX     WtcsDisplayString
    MAX-ACCESS read-only
    STATUS     current
    DESCRIPTION
        "An array of embedded Msvm_KvpExchangeDataItem
        instances which contain the set of key-value pairs
        that components running within the guest operating
        system have pushed up to be available for access by
        external clients. This array will not contain any
        intrinsic items that are pushed by the integration
        component directly. This property is inherited from
        CIM_ManagedElement."
    ::= { msvmKvpExchangeComponentEntry 13 }

msvmkvpGuestIntrinsicExchangeItm OBJECT-TYPE
    SYNTAX     WtcsDisplayString
    MAX-ACCESS read-only
    STATUS     current
    DESCRIPTION
        "An array of embedded Msvm_KvpExchangeDataItem
        instances which contain the set of key-value pairs
        that the guest operating system has pushed up to be
        available for access by external clients. This
        array will not contain any data items pushed by
        other components running within the guest operating
        system. This property is inherited from
        CIM_ManagedElement."
    ::= { msvmKvpExchangeComponentEntry 14 }

msvmkvpHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmKvpExchangeComponentEntry 15 }

msvmkvpIdentifyingDescriptions OBJECT-TYPE
    SYNTAX     WtcsDisplayString
    MAX-ACCESS read-only
    STATUS     current
    DESCRIPTION
        "An array of free-form strings providing
        explanations and details behind the entries in the
        OtherIdentifyingInfo array. Note that each entry of
        this array is related to the entry in
        OtherIdentifyingInfo that is located at the same
        index."
    ::= { msvmKvpExchangeComponentEntry 16 }

msvmkvpInstallDate OBJECT-TYPE
    SYNTAX     DateAndTime
    MAX-ACCESS read-only
    STATUS     current
    DESCRIPTION
        "A datetime value that indicates when the object
        was installed. Lack of a value does not indicate
        that the object is not installed."
    ::= { msvmKvpExchangeComponentEntry 17 }

msvmkvpLastErrorCode OBJECT-TYPE
    SYNTAX     Gauge32
    MAX-ACCESS read-only
    STATUS     current
    DESCRIPTION
        "Note: The use of this method is deprecated. 
        Deprecated description: LastErrorCode captures the
        last error code reported by the LogicalDevice."
    ::= { msvmKvpExchangeComponentEntry 18 }

msvmkvpLocationIndicator OBJECT-TYPE
    SYNTAX     INTEGER {
        unknown(0),
        on(2),
        off(3),
        notSupported(4)
    }
    MAX-ACCESS read-only
    STATUS     current
    DESCRIPTION
        "An integer that reflects the state of an indicator
        (e.g., LED) that is part of a device. Reading the
        value gives the current state. Writing the value
        with 'On'/'Off' turns the indicator on/off, other
        values may not be written."
    ::= { msvmKvpExchangeComponentEntry 19 }

msvmkvpMaxQuiesceTime OBJECT-TYPE
    SYNTAX     Gauge32
    UNITS "MilliSeconds"
    MAX-ACCESS read-only
    STATUS     current
    DESCRIPTION
        "Note: The use of this property has been
        deprecated. When evaluating the use of Quiesce, it
        was determined that this single property is not
        adequate for describing when a device will
        automatically exit a quiescent state. In fact, the
        most likely scenario for a device to exit a
        quiescent state was determined to be based on the
        number of outstanding requests queued rather than
        on a maximum time. This decision will be
        re-evaluated and repositioned later. 
        Deprecated description: Maximum time, in
        milliseconds, that a Device can run in a 'Quiesced'
        state. The state is defined in its Availability and
        AdditionalAvailability properties, where 'Quiesced'
        is conveyed by the value 21. What occurs at the end
        of the time limit is device-specific. The Device
        can unquiesce, can be offline, or can take other
        actions. A value of 0 indicates that a Device can
        remain quiesced indefinitely."
    ::= { msvmKvpExchangeComponentEntry 20 }

msvmkvpName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmKvpExchangeComponentEntry 21 }

msvmkvpOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmKvpExchangeComponentEntry 22 }

msvmkvpOtherEnabledState OBJECT-TYPE
    SYNTAX     WtcsDisplayString
    MAX-ACCESS read-only
    STATUS     current
    DESCRIPTION
        "A string that describes the enabled or disabled
        state of the element when the EnabledState property
        is set to 1 ('Other'). This property must be set to
        null when EnabledState is any value other than 1."
    ::= { msvmKvpExchangeComponentEntry 23 }

msvmkvpOtherIdentifyingInfo OBJECT-TYPE
    SYNTAX     WtcsDisplayString (SIZE (0..256))
    MAX-ACCESS read-only
    STATUS     current
    DESCRIPTION
        "OtherIdentifyingInfo captures data, in addition to
        DeviceID information, that could be used to
        identify a LogicalDevice. For example, you could
        use this property to hold the operating system's
        user-friendly name for the Device."
    ::= { msvmKvpExchangeComponentEntry 24 }

msvmkvpPowerManagementCapability OBJECT-TYPE
    SYNTAX     INTEGER {
        unknown(0),
        notSupported(1),
        disabled(2),
        enabled(3),
        powerSavingModesEnteredAutomatic(4),
        powerStateSettable(5),
        powerCyclingSupported(6),
        timedPowerOnSupported(7)
    }
    MAX-ACCESS read-only
    STATUS     current
    DESCRIPTION
        "Note: The use of this property has been
        deprecated. Instead, use the PowerCapabilites
        property in an associated
        PowerManagementCapabilities class. Deprecated
        description: An enumerated array describing the
        power management capabilities of the Device."
    ::= { msvmKvpExchangeComponentEntry 25 }

msvmkvpPowerManagementSupported OBJECT-TYPE
    SYNTAX     TruthValue
    MAX-ACCESS read-only
    STATUS     current
    DESCRIPTION
        "Note: The use of this property has been
        deprecated. Instead, the existence of an associated
        PowerManagementCapabilities class (associated using
        the ElementCapabilities relationship) indicates
        that power management is supported. Deprecated
        description: Boolean that indicates that the Device
        can use power management."
    ::= { msvmKvpExchangeComponentEntry 26 }

msvmkvpPowerOnHours OBJECT-TYPE
    SYNTAX     Gauge32
    UNITS "Hours"
    MAX-ACCESS read-only
    STATUS     current
    DESCRIPTION
        "Note: The use of this method is deprecated. 
        Deprecated description: The number of consecutive
        hours that this Device has been powered on since
        its last power cycle."
    ::= { msvmKvpExchangeComponentEntry 27 }

msvmkvpRequestedState OBJECT-TYPE
    SYNTAX     INTEGER {
        enabled(2),
        disabled(3),
        shutDown(4),
        noChange(5),
        offline(6),
        test(7),
        deferred(8),
        quiesce(9),
        reboot(10),
        reset(11),
        notApplicable(12)
    }
    MAX-ACCESS read-only
    STATUS     current
    DESCRIPTION
        "RequestedState is an integer enumeration that
        indicates the last requested or desired state for
        the element. The actual state of the element is
        represented by EnabledState. This property is
        provided to compare the last requested and current
        enabled or disabled states. Note that when
        EnabledState is set to 5 ('Not Applicable'), then
        this property has no meaning. By default, the
        RequestedState of the element is 5 ('No Change').
        Refer to the EnabledState property description for
        explanations of the values in the RequestedState
        enumeration. 
        
        It should be noted that there are two new values in
        RequestedState that build on the statuses of
        EnabledState. These are 'Reboot' (10) and 'Reset'
        (11). Reboot refers to doing a 'Shut Down' and then
        moving to an 'Enabled' state. Reset indicates that
        the element is first 'Disabled' and then 'Enabled'.
        The distinction between requesting 'Shut Down' and
        'Disabled' should also be noted. Shut Down requests
        an orderly transition to the Disabled state, and
        might involve removing power, to completely erase
        any existing state. The Disabled state requests an
        immediate disabling of the element, such that it
        will not execute or accept any commands or
        processing requests. 
        
        This property is set as the result of a method
        invocation (such as Start or StopService on
        CIM_Service), or can be overridden and defined as
        WRITEable in a subclass. The method approach is
        considered superior to a WRITEable property,
        because it allows an explicit invocation of the
        operation and the return of a result code. 
        
        A particular instance of EnabledLogicalElement
        might not support RequestedStateChange. If this
        occurs, the value 12 ('Not Applicable') is used."
    ::= { msvmKvpExchangeComponentEntry 28 }

msvmkvpStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmKvpExchangeComponentEntry 29 }

msvmkvpStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmKvpExchangeComponentEntry 30 }

msvmkvpStatusInfo OBJECT-TYPE
    SYNTAX     INTEGER {
        other(1),
        unknown(2),
        enabled(3),
        disabled(4),
        notApplicable(5)
    }
    MAX-ACCESS read-only
    STATUS     current
    DESCRIPTION
        "Note: The use of this method is deprecated in lieu
        of a more clearly named property (EnabledState)
        that is inherited from ManagedSystemElement and
        that has additional enumerated values. 
        Deprecated description: The StatusInfo property
        indicates whether the Logical Device is in an
        enabled state (value=3), disabled state (value=4),
        some other state (value=1), or an unknown state
        (value=2). If this property does not apply to the
        LogicalDevice, the value 5 ('Not Applicable')
        should be used. If a Device is
        ('Enabled')(value=3), it has been powered up and is
        configured and operational. The Device might or
        might not be functionally active, depending on
        whether its Availability (or
        AdditionalAvailability) indicates that it is
        ('Running/Full Power')(value=3) or ('Off line')
        (value=8). In an enabled but offline mode, a Device
        might be performing out-of-band requests, such as
        running Diagnostics. If StatusInfo is ('Disabled')
        (value=4), a Device can only be 'enabled' or
        powered off. In a personal computer environment,
        ('Disabled') means that the driver of the device is
        not available in the stack. In other environments,
        a Device can be disabled by removing its
        configuration file. A disabled device is physically
        present in a System and consuming resources, but it
        cannot be communicated with until a driver is
        loaded, a configuration file is loaded, or some
        other 'enabling' activity has occurred."
    ::= { msvmKvpExchangeComponentEntry 31 }

msvmkvpSystemCreationClassName OBJECT-TYPE
    SYNTAX     WtcsDisplayString (SIZE (0..256))
    MAX-ACCESS read-only
    STATUS     current
    DESCRIPTION
        "The CreationClassName of the scoping system."
    ::= { msvmKvpExchangeComponentEntry 32 }

msvmkvpSystemName OBJECT-TYPE
    SYNTAX     WtcsDisplayString (SIZE (0..256))
    MAX-ACCESS read-only
    STATUS     current
    DESCRIPTION
        "The System Name of the scoping system."
    ::= { msvmKvpExchangeComponentEntry 33 }

msvmkvpTimeOfLastStateChange OBJECT-TYPE
    SYNTAX     DateAndTime
    MAX-ACCESS read-only
    STATUS     current
    DESCRIPTION
        "The date or time when the EnabledState of the
        element last changed. If the state of the element
        has not changed and this property is populated,
        then it must be set to a 0 interval value. If a
        state change was requested, but rejected or not yet
        processed, the property must not be updated."
    ::= { msvmKvpExchangeComponentEntry 34 }

msvmkvpTotalPowerOnHours OBJECT-TYPE
    SYNTAX     Gauge32
    UNITS "Hours"
    MAX-ACCESS read-only
    STATUS     current
    DESCRIPTION
        "Note: The use of this method is deprecated. 
        Deprecated description: The total number of hours
        that this Device has been powered on."
    ::= { msvmKvpExchangeComponentEntry 35 }

msvmKvpExchangeCompSetDataTable OBJECT-TYPE
    SYNTAX     SEQUENCE OF MsvmKvpExchangeCompSetData
    MAX-ACCESS not-accessible
    STATUS     current
    DESCRIPTION
        "Represents the configured state of the key/value
        pair exchange component."
    ::= { msvmIntegrationComponents 4 }

msvmKvpExchangeCompSetDataEntry OBJECT-TYPE
    SYNTAX     MsvmKvpExchangeCompSetData
    MAX-ACCESS not-accessible
    STATUS     current
    DESCRIPTION
        "None"
    INDEX      { msvmecsIndex }
    ::= { msvmKvpExchangeCompSetDataTable 1 }

MsvmKvpExchangeCompSetData ::= SEQUENCE {
    msvmecsIndex Integer32,
    msvmecsAddress WtcsDisplayString,
    msvmecsAllocationUnits WtcsDisplayString,
    msvmecsAutomaticAllocation TruthValue,
    msvmecsAutomaticDeallocation TruthValue,
    msvmecsCaption WtcsDisplayString,
    msvmecsConnection WtcsDisplayString,
    msvmecsConsumerVisibility INTEGER,
    msvmecsDescription WtcsDisplayString,
    msvmecsElementName WtcsDisplayString,
    msvmecsEnabledState Integer32,
    msvmecsHostExchangeItems WtcsDisplayString,
    msvmecsHostResource WtcsDisplayString,
    msvmecsInstanceID WtcsDisplayString,
    msvmecsLimit Gauge32,
    msvmecsMappingBehavior INTEGER,
    msvmecsOtherResourceType WtcsDisplayString,
    msvmecsParent WtcsDisplayString,
    msvmecsPoolID WtcsDisplayString,
    msvmecsReservation Gauge32,
    msvmecsResourceSubType WtcsDisplayString,
    msvmecsResourceType INTEGER,
    msvmecsVirtualQuantity Gauge32,
    msvmecsWeight Gauge32
}

msvmecsIndex OBJECT-TYPE
    SYNTAX     Integer32 (1..2147483647)
    MAX-ACCESS read-only
    STATUS     current
    DESCRIPTION
        "The value of this object uniquely identifies the
        instance entry for this class."
    ::= { msvmKvpExchangeCompSetDataEntry 1 }

msvmecsAddress OBJECT-TYPE
    SYNTAX     WtcsDisplayString
    MAX-ACCESS read-only
    STATUS     current
    DESCRIPTION
        "The address of the resource.For example, the MAC
        address of a Ethernet port."
    ::= { msvmKvpExchangeCompSetDataEntry 2 }

msvmecsAllocationUnits OBJECT-TYPE
    SYNTAX     WtcsDisplayString
    MAX-ACCESS read-only
    STATUS     current
    DESCRIPTION
        "This property specifies the units of allocation
        used by the Reservation and Limit properties.  For
        example, when ResourceType=Processor,
        AllocationUnits may be set to MHZ. When
        ResourceType=Memory, AllocationUnits may be set to
        MB"
    ::= { msvmKvpExchangeCompSetDataEntry 3 }

msvmecsAutomaticAllocation OBJECT-TYPE
    SYNTAX     TruthValue
    MAX-ACCESS read-only
    STATUS     current
    DESCRIPTION
        "This property specifies if the resource will be
        automatically allocated.  For example when set to
        true, when the consuming virtual computer system is
        powered on, this resource would be allocated.  A
        value of false indicates the resource must be
        explicitly allocated.  For example, the setting may
        represent removable media (cdrom, floppy, etc.)
        where at power on time, the media isnot present. 
        An explicit operation is required to allocate the
        resource."
    ::= { msvmKvpExchangeCompSetDataEntry 4 }

msvmecsAutomaticDeallocation OBJECT-TYPE
    SYNTAX     TruthValue
    MAX-ACCESS read-only
    STATUS     current
    DESCRIPTION
        "This property specifies if the resource will be
        automatically de-allocated.  For example, when set
        to true, when the consuming virtual computer system
        is powered off, this resource would be
        de-allocated.  When set to false, the resource will
        remain allocated and must be explicitly
        de-allocated."
    ::= { msvmKvpExchangeCompSetDataEntry 5 }

msvmecsCaption OBJECT-TYPE
    SYNTAX     WtcsDisplayString (SIZE (0..64))
    MAX-ACCESS read-only
    STATUS     current
    DESCRIPTION
        "The Caption property is a short textual
        description (one- line string) of the object."
    ::= { msvmKvpExchangeCompSetDataEntry 6 }

msvmecsConnection OBJECT-TYPE
    SYNTAX     WtcsDisplayString
    MAX-ACCESS read-only
    STATUS     current
    DESCRIPTION
        "The thing to which this resource is connected. 
        For example, a named network or switch port."
    ::= { msvmKvpExchangeCompSetDataEntry 7 }

msvmecsConsumerVisibility OBJECT-TYPE
    SYNTAX     INTEGER {
        unknown(0),
        passedThrough(2),
        virtualized(3),
        notrepresented(4)
    }
    MAX-ACCESS read-only
    STATUS     current
    DESCRIPTION
        "Describes the consumers visibility to the
        allocated  resource.
        A value of 'Passed-Through' indicates the
        underlying or host resource is utilized and passed
        through to the consumer, possibly using
        partitioning. At least one item shall be present in
        the DeviceID property.  
        A value of 'Virtualized' indicates the resource is
        virtualized and may not map directly to an
        underlying/host resource. Some implementations may
        support specific assignment for virtualized
        resources, in which case the host resource(s) are
        exposed using the DeviceID property. 
        A value of 'Not represented' indicates a
        representation of the resource does not exist
        within the context of the resource consumer."
    ::= { msvmKvpExchangeCompSetDataEntry 8 }

msvmecsDescription OBJECT-TYPE
    SYNTAX     WtcsDisplayString
    MAX-ACCESS read-only
    STATUS     current
    DESCRIPTION
        "The Description property provides a textual
        description of the object."
    ::= { msvmKvpExchangeCompSetDataEntry 9 }

msvmecsElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmKvpExchangeCompSetDataEntry 10 }

msvmecsEnabledState OBJECT-TYPE
    SYNTAX     Integer32
    MAX-ACCESS read-only
    STATUS     current
    DESCRIPTION
        "An integer enumeration that indicates the enabled
        and disabled states of an element. This property is
        inherited from CIM_EnabledLogicalElement and is
        either set to 2 ('Enabled') or 3 ('Disabled')."
    ::= { msvmKvpExchangeCompSetDataEntry 11 }

msvmecsHostExchangeItems OBJECT-TYPE
    SYNTAX     WtcsDisplayString
    MAX-ACCESS read-only
    STATUS     current
    DESCRIPTION
        "This property is inherited from
        CIM_ResourceAllocationSettingData."
    ::= { msvmKvpExchangeCompSetDataEntry 12 }

msvmecsHostResource OBJECT-TYPE
    SYNTAX     WtcsDisplayString
    MAX-ACCESS read-only
    STATUS     current
    DESCRIPTION
        "This property exposes specific assignment to host
        or underlying resources.        The embedded
        instances shall contain only key properties and be
        treated as Object Paths. If the virtual resource
        may be scheduled on a number of underlying
        resources, this property shall be left NULL. In
        that case, the DeviceAllocatedFromPool or
        ResourceAllocationFromPool associations may be used
        to determine the pool of host resources this
        virtual resource may be scheduled on. If specific
        assignment is utilized, all underlying resources
        used by this virtual resource shall be listed in
        this array.  Typically the array will contain one
        item, however for aggregate allocations, such as
        multiple processors, multiple host resources may be
        specified."
    ::= { msvmKvpExchangeCompSetDataEntry 13 }

msvmecsInstanceID OBJECT-TYPE
    SYNTAX     WtcsDisplayString
    MAX-ACCESS read-only
    STATUS     current
    DESCRIPTION
        "Within the scope of the instantiating Namespace,
        InstanceID opaquely and uniquely identifies an
        instance of this class. To ensure uniqueness within
        the NameSpace, the value of InstanceID should be
        constructed using the following 'preferred'
        algorithm: 
        <OrgID>:<LocalID> 
        Where <OrgID> and <LocalID> are separated by a
        colon (:), and where <OrgID> must include a
        copyrighted, trademarked, or otherwise unique name
        that is owned by the business entity that is
        creating or defining the InstanceID or that is a
        registered ID assigned to the business entity by a
        recognized global authority. (This requirement is
        similar to the <Schema Name>_<Class Name> structure
        of Schema class names.) In addition, to ensure
        uniqueness, <OrgID> must not contain a colon (:).
        When using this algorithm, the first colon to
        appear in InstanceID must appear between <OrgID>
        and <LocalID>. 
        <LocalID> is chosen by the business entity and
        should not be reused to identify different
        underlying (real-world) elements. If the above
        'preferred' algorithm is not used, the defining
        entity must assure that the resulting InstanceID is
        not reused across any InstanceIDs produced by this
        or other providers for the NameSpace of this
        instance. 
        For DMTF-defined instances, the 'preferred'
        algorithm must be used with the <OrgID> set to
        CIM."
    ::= { msvmKvpExchangeCompSetDataEntry 14 }

msvmecsLimit OBJECT-TYPE
    SYNTAX     Gauge32
    MAX-ACCESS read-only
    STATUS     current
    DESCRIPTION
        "This property specifies the upper bound, or
        maximum amount of resource that will be granted for
        this allocation. For example, a system which
        supports memory paging may support setting the
        Limit of a Memory allocation below that of the
        VirtualQuantity, thus forcing paging to occur for
        this allocation."
    ::= { msvmKvpExchangeCompSetDataEntry 15 }

msvmecsMappingBehavior OBJECT-TYPE
    SYNTAX     INTEGER {
        unknown(0),
        notSupported(1),
        dedicated(2),
        softAffinity(3),
        hardAffinity(4)
    }
    MAX-ACCESS read-only
    STATUS     current
    DESCRIPTION
        "Specifies how this resource maps to underlying
        resourcesIf the HostResource array contains any
        entries, this property reflects how the resource
        maps to those specific resources."
    ::= { msvmKvpExchangeCompSetDataEntry 16 }

msvmecsOtherResourceType OBJECT-TYPE
    SYNTAX     WtcsDisplayString
    MAX-ACCESS read-only
    STATUS     current
    DESCRIPTION
        "A string that describes the resource type when a
        well defined value is not available and
        ResourceType has the value 'Other'."
    ::= { msvmKvpExchangeCompSetDataEntry 17 }

msvmecsParent OBJECT-TYPE
    SYNTAX     WtcsDisplayString
    MAX-ACCESS read-only
    STATUS     current
    DESCRIPTION
        "The Parent of the resource.  For example, a
        controller for the current allocation"
    ::= { msvmKvpExchangeCompSetDataEntry 18 }

msvmecsPoolID OBJECT-TYPE
    SYNTAX     WtcsDisplayString
    MAX-ACCESS read-only
    STATUS     current
    DESCRIPTION
        "This property specifies which ResourcePool the
        resource is currently allocated from, or which
        ResourcePool the resource will be allocated from
        when the allocation occurs."
    ::= { msvmKvpExchangeCompSetDataEntry 19 }

msvmecsReservation OBJECT-TYPE
    SYNTAX     Gauge32
    MAX-ACCESS read-only
    STATUS     current
    DESCRIPTION
        "This property specifies the amount of resource
        guaranteed to be available for this allocation.  On
        system which support over-commitment of resources,
        this value is typically used for admission control
        to prevent an an allocation from being accepted
        thus preventing starvation."
    ::= { msvmKvpExchangeCompSetDataEntry 20 }

msvmecsResourceSubType OBJECT-TYPE
    SYNTAX     WtcsDisplayString
    MAX-ACCESS read-only
    STATUS     current
    DESCRIPTION
        "A string describing an implementation specific
        sub-type for this resource.  For example, this may
        be used to distinguish different models of the same
        resource type."
    ::= { msvmKvpExchangeCompSetDataEntry 21 }

msvmecsResourceType OBJECT-TYPE
    SYNTAX     INTEGER {
        other(1),
        computerSystem(2),
        processor(3),
        memory(4),
        ideController(5),
        parallelSCSIHBA(6),
        fcHBA(7),
        iSCSIHBA(8),
        ibHCA(9),
        ethernetAdapter(10),
        iOSlot(11),
        iODevice(12),
        floppyDrive(13),
        cdDrive(14),
        dvddrive(15),
        serialport(16),
        parallelport(17),
        usbController(18),
        graphicscontroller(19),
        storageExtent(20),
        disk(21),
        tape(22),
        otherstoragedevice(23),
        firewireController(24),
        partitionableUnit(25),
        basePartitionableUnit(26),
        powerSupply(27),
        coolingDevice(28),
        dmtfreserved(29)
    }
    MAX-ACCESS read-only
    STATUS     current
    DESCRIPTION
        "The type of resource this allocation setting
        represents."
    ::= { msvmKvpExchangeCompSetDataEntry 22 }

msvmecsVirtualQuantity OBJECT-TYPE
    SYNTAX     Gauge32
    MAX-ACCESS read-only
    STATUS     current
    DESCRIPTION
        "This property specifies the quantity of resources
        presented to the consumer.  For example, when
        ResourceType=Processor,  this property would
        reflect the number of discrete Processors presented
        to the virtual computer system.  When
        ResourceType=Memory, this property could reflect
        the number of MB reported to the virtual computer
        system."
    ::= { msvmKvpExchangeCompSetDataEntry 23 }

msvmecsWeight OBJECT-TYPE
    SYNTAX     Gauge32
    MAX-ACCESS read-only
    STATUS     current
    DESCRIPTION
        "This property specifies a relative priority for
        this allocation in relation to other allocations
        from the same ResourcePool.  This property has no
        unit of measure, and is only relevant when compared
        to other allocations vying for the same host
        resources."
    ::= { msvmKvpExchangeCompSetDataEntry 24 }

msvmKvpExchangeDataItemTable OBJECT-TYPE
    SYNTAX     SEQUENCE OF MsvmKvpExchangeDataItem
    MAX-ACCESS not-accessible
    STATUS     current
    DESCRIPTION
        "Represents a key/value pair."
    ::= { msvmIntegrationComponents 5 }

msvmKvpExchangeDataItemEntry OBJECT-TYPE
    SYNTAX     MsvmKvpExchangeDataItem
    MAX-ACCESS not-accessible
    STATUS     current
    DESCRIPTION
        "None"
    INDEX      { msvmediIndex }
    ::= { msvmKvpExchangeDataItemTable 1 }

MsvmKvpExchangeDataItem ::= SEQUENCE {
    msvmediIndex Integer32,
    msvmediCaption WtcsDisplayString,
    msvmediData WtcsDisplayString,
    msvmediDescription WtcsDisplayString,
    msvmediElementName WtcsDisplayString,
    msvmediName WtcsDisplayString,
    msvmediSource Integer32
}

msvmediIndex OBJECT-TYPE
    SYNTAX     Integer32 (1..2147483647)
    MAX-ACCESS read-only
    STATUS     current
    DESCRIPTION
        "The value of this object uniquely identifies the
        instance entry for this class."
    ::= { msvmKvpExchangeDataItemEntry 1 }

msvmediCaption OBJECT-TYPE
    SYNTAX     WtcsDisplayString (SIZE (0..64))
    MAX-ACCESS read-only
    STATUS     current
    DESCRIPTION
        "The Caption property is a short textual
        description (one- line string) of the object."
    ::= { msvmKvpExchangeDataItemEntry 2 }

msvmediData OBJECT-TYPE
    SYNTAX     WtcsDisplayString (SIZE (0..1024))
    MAX-ACCESS read-only
    STATUS     current
    DESCRIPTION
        "The Data property holds arbitrary string data for
        this item. This property is inherited from
        CIM_ManagedElement."
    ::= { msvmKvpExchangeDataItemEntry 3 }

msvmediDescription OBJECT-TYPE
    SYNTAX     WtcsDisplayString
    MAX-ACCESS read-only
    STATUS     current
    DESCRIPTION
        "The Description property provides a textual
        description of the object."
    ::= { msvmKvpExchangeDataItemEntry 4 }

msvmediElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmKvpExchangeDataItemEntry 5 }

msvmediName OBJECT-TYPE
    SYNTAX     WtcsDisplayString (SIZE (0..256))
    MAX-ACCESS read-only
    STATUS     current
    DESCRIPTION
        "The Name property defines the label by which the
        object is known. The Name property defines the
        label by which the item is identified. This
        property is inherited from CIM_ManagedElement."
    ::= { msvmKvpExchangeDataItemEntry 6 }

msvmediSource OBJECT-TYPE
    SYNTAX     Integer32
    MAX-ACCESS read-only
    STATUS     current
    DESCRIPTION
        "The source of the data. This property is inherited
        from CIM_ManagedElement."
    ::= { msvmKvpExchangeDataItemEntry 7 }

msvmShutdownComponentTable OBJECT-TYPE
    SYNTAX     SEQUENCE OF MsvmShutdownComponent
    MAX-ACCESS not-accessible
    STATUS     current
    DESCRIPTION
        "Represents the state of the shutdown component,
        which provides a mechanism to shut down the
        operation on the associated guest operating
        system."
    ::= { msvmIntegrationComponents 6 }

msvmShutdownComponentEntry OBJECT-TYPE
    SYNTAX     MsvmShutdownComponent
    MAX-ACCESS not-accessible
    STATUS     current
    DESCRIPTION
        "None"
    INDEX      { msvmscIndex }
    ::= { msvmShutdownComponentTable 1 }

MsvmShutdownComponent ::= SEQUENCE {
    msvmscIndex Integer32,
    msvmscAdditionalAvailability INTEGER,
    msvmscAvailability INTEGER,
    msvmscCaption WtcsDisplayString,
    msvmscCreationClassName WtcsDisplayString,
    msvmscDescription WtcsDisplayString,
    msvmscDeviceID WtcsDisplayString,
    msvmscElementName WtcsDisplayString,
    msvmscEnabledDefault INTEGER,
    msvmscEnabledState INTEGER,
    msvmscErrorCleared TruthValue,
    msvmscErrorDescription WtcsDisplayString,
    msvmscHealthState INTEGER,
    msvmscIdentifyingDescriptions WtcsDisplayString,
    msvmscInstallDate DateAndTime,
    msvmscLastErrorCode Gauge32,
    msvmscLocationIndicator INTEGER,
    msvmscMaxQuiesceTime Gauge32,
    msvmscName WtcsDisplayString,
    msvmscOperationalStatus INTEGER,
    msvmscOtherEnabledState WtcsDisplayString,
    msvmscOtherIdentifyingInfo WtcsDisplayString,
    msvmscPowerManagementCapability INTEGER,
    msvmscPowerManagementSupported TruthValue,
    msvmscPowerOnHours Gauge32,
    msvmscRequestedState INTEGER,
    msvmscStatus WtcsDisplayString,
    msvmscStatusDescriptions WtcsDisplayString,
    msvmscStatusInfo INTEGER,
    msvmscSystemCreationClassName WtcsDisplayString,
    msvmscSystemName WtcsDisplayString,
    msvmscTimeOfLastStateChange DateAndTime,
    msvmscTotalPowerOnHours Gauge32
}

msvmscIndex OBJECT-TYPE
    SYNTAX     Integer32 (1..2147483647)
    MAX-ACCESS read-only
    STATUS     current
    DESCRIPTION
        "The value of this object uniquely identifies the
        instance entry for this class."
    ::= { msvmShutdownComponentEntry 1 }

msvmscAdditionalAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Additional availability and status of the Device
        in addition to that specified in the Availability
        property. The Availability property denotes the
        primary status and availability of the Device. In
        some cases, this property will not be sufficient to
        denote the complete status of the Device. In those
        cases, the AdditionalAvailability property can be
        used to provide further information. For example,
        the primary Availability of a device might be 'Off
        line' (value=8) or in a low-power state
        (AdditionalAvailability value=14), or the Device
        could be running Diagnostics
        (AdditionalAvailability value=5, 'In Test')."
    ::= { msvmShutdownComponentEntry 2 }

msvmscAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Note: The use of this property has been
        deprecated. 
        Deprecated description: The primary availability
        and status of the Device. (Additional status
        information can be specified using the Additional
        Availability array property.) For example, the
        Availability property indicates that the Device is
        running and has full power (value=3), or is in a
        warning (4), test (5), degraded (10) or power save
        state (values 13-15 and 17). The Power Save states
        are defined as follows: Value 13 ('Power Save -
        Unknown') indicates that the Device is known to be
        in a power save mode, but its exact status in this
        mode is unknown; value 14 ('Power Save - Low Power
        Mode') indicates that the Device is in a power save
        state but still functioning, and might exhibit
        degraded performance; value 15 ('Power Save -
        Standby') indicates that the Device is not
        functioning but could be brought to full power
        'quickly'; and value 17 ('Power Save - Warning')
        indicates that the Device is in a warning state,
        but is also in a power save mode."
    ::= { msvmShutdownComponentEntry 3 }

msvmscCaption OBJECT-TYPE
    SYNTAX     WtcsDisplayString (SIZE (0..64))
    MAX-ACCESS read-only
    STATUS     current
    DESCRIPTION
        "The Caption property is a short textual
        description (one- line string) of the object."
    ::= { msvmShutdownComponentEntry 4 }

msvmscCreationClassName OBJECT-TYPE
    SYNTAX     WtcsDisplayString (SIZE (0..256))
    MAX-ACCESS read-only
    STATUS     current
    DESCRIPTION
        "CreationClassName indicates the name of the class
        or the subclass used in the creation of an
        instance. When used with the other key properties
        of this class, this property allows all instances
        of this class and its subclasses to be uniquely
        identified."
    ::= { msvmShutdownComponentEntry 5 }

msvmscDescription OBJECT-TYPE
    SYNTAX     WtcsDisplayString
    MAX-ACCESS read-only
    STATUS     current
    DESCRIPTION
        "The Description property provides a textual
        description of the object."
    ::= { msvmShutdownComponentEntry 6 }

msvmscDeviceID OBJECT-TYPE
    SYNTAX     WtcsDisplayString (SIZE (0..64))
    MAX-ACCESS read-only
    STATUS     current
    DESCRIPTION
        "An address or other identifying information used
        to uniquely name the LogicalDevice."
    ::= { msvmShutdownComponentEntry 7 }

msvmscElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmShutdownComponentEntry 8 }

msvmscEnabledDefault OBJECT-TYPE
    SYNTAX     INTEGER {
        enabled(2),
        disabled(3),
        notApplicable(5),
        enabledbutOffline(6),
        noDefault(7)
    }
    MAX-ACCESS read-only
    STATUS     current
    DESCRIPTION
        "An enumerated value indicating an administrator's
        default or startup configuration for the Enabled
        State of an element. By default, the element is
        'Enabled' (value=2)."
    ::= { msvmShutdownComponentEntry 9 }

msvmscEnabledState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "EnabledState is an integer enumeration that
        indicates the enabled and disabled states of an
        element. It can also indicate the transitions
        between these requested states. For example,
        shutting down (value=4) and starting (value=10) are
        transient states between enabled and disabled. The
        following text briefly summarizes the various
        enabled and disabled states: 
        Enabled (2) indicates that the element is or could
        be executing commands, will process any queued
        commands, and queues new requests. 
        Disabled (3) indicates that the element will not
        execute commands and will drop any new requests. 
        Shutting Down (4) indicates that the element is in
        the process of going to a Disabled state. 
        Not Applicable (5) indicates the element does not
        support being enabled or disabled. 
        Enabled but Offline (6) indicates that the element
        might be completing commands, and will drop any new
        requests. 
        Test (7) indicates that the element is in a test
        state. 
        Deferred (8) indicates that the element might be
        completing commands, but will queue any new
        requests. 
        Quiesce (9) indicates that the element is enabled
        but in a restricted mode. The behavior of the
        element is similar to the Enabled state, but it
        processes only a restricted set of commands. All
        other requests are queued. 
        Starting (10) indicates that the element is in the
        process of going to an Enabled state. New requests
        are queued."
    ::= { msvmShutdownComponentEntry 10 }

msvmscErrorCleared OBJECT-TYPE
    SYNTAX     TruthValue
    MAX-ACCESS read-only
    STATUS     current
    DESCRIPTION
        "Note: The use of this method is deprecated. 
        Deprecated description: ErrorCleared is a Boolean
        property that indicates that the error reported in
        LastErrorCode is now cleared."
    ::= { msvmShutdownComponentEntry 11 }

msvmscErrorDescription OBJECT-TYPE
    SYNTAX     WtcsDisplayString
    MAX-ACCESS read-only
    STATUS     current
    DESCRIPTION
        "Note: The use of this method is deprecated. 
        Deprecated description: ErrorDescription is a
        free-form string that supplies more information
        about the error recorded in LastErrorCode and
        information on any corrective actions that can be
        taken."
    ::= { msvmShutdownComponentEntry 12 }

msvmscHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmShutdownComponentEntry 13 }

msvmscIdentifyingDescriptions OBJECT-TYPE
    SYNTAX     WtcsDisplayString
    MAX-ACCESS read-only
    STATUS     current
    DESCRIPTION
        "An array of free-form strings providing
        explanations and details behind the entries in the
        OtherIdentifyingInfo array. Note that each entry of
        this array is related to the entry in
        OtherIdentifyingInfo that is located at the same
        index."
    ::= { msvmShutdownComponentEntry 14 }

msvmscInstallDate OBJECT-TYPE
    SYNTAX     DateAndTime
    MAX-ACCESS read-only
    STATUS     current
    DESCRIPTION
        "A datetime value that indicates when the object
        was installed. Lack of a value does not indicate
        that the object is not installed."
    ::= { msvmShutdownComponentEntry 15 }

msvmscLastErrorCode OBJECT-TYPE
    SYNTAX     Gauge32
    MAX-ACCESS read-only
    STATUS     current
    DESCRIPTION
        "Note: The use of this method is deprecated. 
        Deprecated description: LastErrorCode captures the
        last error code reported by the LogicalDevice."
    ::= { msvmShutdownComponentEntry 16 }

msvmscLocationIndicator OBJECT-TYPE
    SYNTAX     INTEGER {
        unknown(0),
        on(2),
        off(3),
        notSupported(4)
    }
    MAX-ACCESS read-only
    STATUS     current
    DESCRIPTION
        "An integer that reflects the state of an indicator
        (e.g., LED) that is part of a device. Reading the
        value gives the current state. Writing the value
        with 'On'/'Off' turns the indicator on/off, other
        values may not be written."
    ::= { msvmShutdownComponentEntry 17 }

msvmscMaxQuiesceTime OBJECT-TYPE
    SYNTAX     Gauge32
    UNITS "MilliSeconds"
    MAX-ACCESS read-only
    STATUS     current
    DESCRIPTION
        "Note: The use of this property has been
        deprecated. When evaluating the use of Quiesce, it
        was determined that this single property is not
        adequate for describing when a device will
        automatically exit a quiescent state. In fact, the
        most likely scenario for a device to exit a
        quiescent state was determined to be based on the
        number of outstanding requests queued rather than
        on a maximum time. This decision will be
        re-evaluated and repositioned later. 
        Deprecated description: Maximum time, in
        milliseconds, that a Device can run in a 'Quiesced'
        state. The state is defined in its Availability and
        AdditionalAvailability properties, where 'Quiesced'
        is conveyed by the value 21. What occurs at the end
        of the time limit is device-specific. The Device
        can unquiesce, can be offline, or can take other
        actions. A value of 0 indicates that a Device can
        remain quiesced indefinitely."
    ::= { msvmShutdownComponentEntry 18 }

msvmscName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmShutdownComponentEntry 19 }

msvmscOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmShutdownComponentEntry 20 }

msvmscOtherEnabledState OBJECT-TYPE
    SYNTAX     WtcsDisplayString
    MAX-ACCESS read-only
    STATUS     current
    DESCRIPTION
        "A string that describes the enabled or disabled
        state of the element when the EnabledState property
        is set to 1 ('Other'). This property must be set to
        null when EnabledState is any value other than 1."
    ::= { msvmShutdownComponentEntry 21 }

msvmscOtherIdentifyingInfo OBJECT-TYPE
    SYNTAX     WtcsDisplayString (SIZE (0..256))
    MAX-ACCESS read-only
    STATUS     current
    DESCRIPTION
        "OtherIdentifyingInfo captures data, in addition to
        DeviceID information, that could be used to
        identify a LogicalDevice. For example, you could
        use this property to hold the operating system's
        user-friendly name for the Device."
    ::= { msvmShutdownComponentEntry 22 }

msvmscPowerManagementCapability OBJECT-TYPE
    SYNTAX     INTEGER {
        unknown(0),
        notSupported(1),
        disabled(2),
        enabled(3),
        powerSavingModesEnteredAutomatic(4),
        powerStateSettable(5),
        powerCyclingSupported(6),
        timedPowerOnSupported(7)
    }
    MAX-ACCESS read-only
    STATUS     current
    DESCRIPTION
        "Note: The use of this property has been
        deprecated. Instead, use the PowerCapabilites
        property in an associated
        PowerManagementCapabilities class. Deprecated
        description: An enumerated array describing the
        power management capabilities of the Device."
    ::= { msvmShutdownComponentEntry 23 }

msvmscPowerManagementSupported OBJECT-TYPE
    SYNTAX     TruthValue
    MAX-ACCESS read-only
    STATUS     current
    DESCRIPTION
        "Note: The use of this property has been
        deprecated. Instead, the existence of an associated
        PowerManagementCapabilities class (associated using
        the ElementCapabilities relationship) indicates
        that power management is supported. Deprecated
        description: Boolean that indicates that the Device
        can use power management."
    ::= { msvmShutdownComponentEntry 24 }

msvmscPowerOnHours OBJECT-TYPE
    SYNTAX     Gauge32
    UNITS "Hours"
    MAX-ACCESS read-only
    STATUS     current
    DESCRIPTION
        "Note: The use of this method is deprecated. 
        Deprecated description: The number of consecutive
        hours that this Device has been powered on since
        its last power cycle."
    ::= { msvmShutdownComponentEntry 25 }

msvmscRequestedState OBJECT-TYPE
    SYNTAX     INTEGER {
        enabled(2),
        disabled(3),
        shutDown(4),
        noChange(5),
        offline(6),
        test(7),
        deferred(8),
        quiesce(9),
        reboot(10),
        reset(11),
        notApplicable(12)
    }
    MAX-ACCESS read-only
    STATUS     current
    DESCRIPTION
        "RequestedState is an integer enumeration that
        indicates the last requested or desired state for
        the element. The actual state of the element is
        represented by EnabledState. This property is
        provided to compare the last requested and current
        enabled or disabled states. Note that when
        EnabledState is set to 5 ('Not Applicable'), then
        this property has no meaning. By default, the
        RequestedState of the element is 5 ('No Change').
        Refer to the EnabledState property description for
        explanations of the values in the RequestedState
        enumeration. 
        
        It should be noted that there are two new values in
        RequestedState that build on the statuses of
        EnabledState. These are 'Reboot' (10) and 'Reset'
        (11). Reboot refers to doing a 'Shut Down' and then
        moving to an 'Enabled' state. Reset indicates that
        the element is first 'Disabled' and then 'Enabled'.
        The distinction between requesting 'Shut Down' and
        'Disabled' should also be noted. Shut Down requests
        an orderly transition to the Disabled state, and
        might involve removing power, to completely erase
        any existing state. The Disabled state requests an
        immediate disabling of the element, such that it
        will not execute or accept any commands or
        processing requests. 
        
        This property is set as the result of a method
        invocation (such as Start or StopService on
        CIM_Service), or can be overridden and defined as
        WRITEable in a subclass. The method approach is
        considered superior to a WRITEable property,
        because it allows an explicit invocation of the
        operation and the return of a result code. 
        
        A particular instance of EnabledLogicalElement
        might not support RequestedStateChange. If this
        occurs, the value 12 ('Not Applicable') is used."
    ::= { msvmShutdownComponentEntry 26 }

msvmscStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmShutdownComponentEntry 27 }

msvmscStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmShutdownComponentEntry 28 }

msvmscStatusInfo OBJECT-TYPE
    SYNTAX     INTEGER {
        other(1),
        unknown(2),
        enabled(3),
        disabled(4),
        notApplicable(5)
    }
    MAX-ACCESS read-only
    STATUS     current
    DESCRIPTION
        "Note: The use of this method is deprecated in lieu
        of a more clearly named property (EnabledState)
        that is inherited from ManagedSystemElement and
        that has additional enumerated values. 
        Deprecated description: The StatusInfo property
        indicates whether the Logical Device is in an
        enabled state (value=3), disabled state (value=4),
        some other state (value=1), or an unknown state
        (value=2). If this property does not apply to the
        LogicalDevice, the value 5 ('Not Applicable')
        should be used. If a Device is
        ('Enabled')(value=3), it has been powered up and is
        configured and operational. The Device might or
        might not be functionally active, depending on
        whether its Availability (or
        AdditionalAvailability) indicates that it is
        ('Running/Full Power')(value=3) or ('Off line')
        (value=8). In an enabled but offline mode, a Device
        might be performing out-of-band requests, such as
        running Diagnostics. If StatusInfo is ('Disabled')
        (value=4), a Device can only be 'enabled' or
        powered off. In a personal computer environment,
        ('Disabled') means that the driver of the device is
        not available in the stack. In other environments,
        a Device can be disabled by removing its
        configuration file. A disabled device is physically
        present in a System and consuming resources, but it
        cannot be communicated with until a driver is
        loaded, a configuration file is loaded, or some
        other 'enabling' activity has occurred."
    ::= { msvmShutdownComponentEntry 29 }

msvmscSystemCreationClassName OBJECT-TYPE
    SYNTAX     WtcsDisplayString (SIZE (0..256))
    MAX-ACCESS read-only
    STATUS     current
    DESCRIPTION
        "The CreationClassName of the scoping system."
    ::= { msvmShutdownComponentEntry 30 }

msvmscSystemName OBJECT-TYPE
    SYNTAX     WtcsDisplayString (SIZE (0..256))
    MAX-ACCESS read-only
    STATUS     current
    DESCRIPTION
        "The System Name of the scoping system."
    ::= { msvmShutdownComponentEntry 31 }

msvmscTimeOfLastStateChange OBJECT-TYPE
    SYNTAX     DateAndTime
    MAX-ACCESS read-only
    STATUS     current
    DESCRIPTION
        "The date or time when the EnabledState of the
        element last changed. If the state of the element
        has not changed and this property is populated,
        then it must be set to a 0 interval value. If a
        state change was requested, but rejected or not yet
        processed, the property must not be updated."
    ::= { msvmShutdownComponentEntry 32 }

msvmscTotalPowerOnHours OBJECT-TYPE
    SYNTAX     Gauge32
    UNITS "Hours"
    MAX-ACCESS read-only
    STATUS     current
    DESCRIPTION
        "Note: The use of this method is deprecated. 
        Deprecated description: The total number of hours
        that this Device has been powered on."
    ::= { msvmShutdownComponentEntry 33 }

msvmShutdownCompSettingDataTable OBJECT-TYPE
    SYNTAX     SEQUENCE OF MsvmShutdownComponentSettingData
    MAX-ACCESS not-accessible
    STATUS     current
    DESCRIPTION
        "Represents the configured state of the shutdown
        component."
    ::= { msvmIntegrationComponents 7 }

msvmShutdownCompSettingDataEntry OBJECT-TYPE
    SYNTAX     MsvmShutdownComponentSettingData
    MAX-ACCESS not-accessible
    STATUS     current
    DESCRIPTION
        "None"
    INDEX      { msvmscsdIndex }
    ::= { msvmShutdownCompSettingDataTable 1 }

MsvmShutdownComponentSettingData ::= SEQUENCE {
    msvmscsdIndex Integer32,
    msvmscsdAddress WtcsDisplayString,
    msvmscsdAllocationUnits WtcsDisplayString,
    msvmscsdAutomaticAllocation TruthValue,
    msvmscsdAutomaticDeallocation TruthValue,
    msvmscsdCaption WtcsDisplayString,
    msvmscsdConnection WtcsDisplayString,
    msvmscsdConsumerVisibility INTEGER,
    msvmscsdDescription WtcsDisplayString,
    msvmscsdElementName WtcsDisplayString,
    msvmscsdEnabledState Integer32,
    msvmscsdHostResource WtcsDisplayString,
    msvmscsdInstanceID WtcsDisplayString,
    msvmscsdLimit Gauge32,
    msvmscsdMappingBehavior INTEGER,
    msvmscsdOtherResourceType WtcsDisplayString,
    msvmscsdParent WtcsDisplayString,
    msvmscsdPoolID WtcsDisplayString,
    msvmscsdReservation Gauge32,
    msvmscsdResourceSubType WtcsDisplayString,
    msvmscsdResourceType INTEGER,
    msvmscsdVirtualQuantity Gauge32,
    msvmscsdWeight Gauge32
}

msvmscsdIndex OBJECT-TYPE
    SYNTAX     Integer32 (1..2147483647)
    MAX-ACCESS read-only
    STATUS     current
    DESCRIPTION
        "The value of this object uniquely identifies the
        instance entry for this class."
    ::= { msvmShutdownCompSettingDataEntry 1 }

msvmscsdAddress OBJECT-TYPE
    SYNTAX     WtcsDisplayString
    MAX-ACCESS read-only
    STATUS     current
    DESCRIPTION
        "The address of the resource.For example, the MAC
        address of a Ethernet port."
    ::= { msvmShutdownCompSettingDataEntry 2 }

msvmscsdAllocationUnits OBJECT-TYPE
    SYNTAX     WtcsDisplayString
    MAX-ACCESS read-only
    STATUS     current
    DESCRIPTION
        "This property specifies the units of allocation
        used by the Reservation and Limit properties.  For
        example, when ResourceType=Processor,
        AllocationUnits may be set to MHZ. When
        ResourceType=Memory, AllocationUnits may be set to
        MB"
    ::= { msvmShutdownCompSettingDataEntry 3 }

msvmscsdAutomaticAllocation OBJECT-TYPE
    SYNTAX     TruthValue
    MAX-ACCESS read-only
    STATUS     current
    DESCRIPTION
        "This property specifies if the resource will be
        automatically allocated.  For example when set to
        true, when the consuming virtual computer system is
        powered on, this resource would be allocated.  A
        value of false indicates the resource must be
        explicitly allocated.  For example, the setting may
        represent removable media (cdrom, floppy, etc.)
        where at power on time, the media isnot present. 
        An explicit operation is required to allocate the
        resource."
    ::= { msvmShutdownCompSettingDataEntry 4 }

msvmscsdAutomaticDeallocation OBJECT-TYPE
    SYNTAX     TruthValue
    MAX-ACCESS read-only
    STATUS     current
    DESCRIPTION
        "This property specifies if the resource will be
        automatically de-allocated.  For example, when set
        to true, when the consuming virtual computer system
        is powered off, this resource would be
        de-allocated.  When set to false, the resource will
        remain allocated and must be explicitly
        de-allocated."
    ::= { msvmShutdownCompSettingDataEntry 5 }

msvmscsdCaption OBJECT-TYPE
    SYNTAX     WtcsDisplayString (SIZE (0..64))
    MAX-ACCESS read-only
    STATUS     current
    DESCRIPTION
        "The Caption property is a short textual
        description (one- line string) of the object."
    ::= { msvmShutdownCompSettingDataEntry 6 }

msvmscsdConnection OBJECT-TYPE
    SYNTAX     WtcsDisplayString
    MAX-ACCESS read-only
    STATUS     current
    DESCRIPTION
        "The thing to which this resource is connected. 
        For example, a named network or switch port."
    ::= { msvmShutdownCompSettingDataEntry 7 }

msvmscsdConsumerVisibility OBJECT-TYPE
    SYNTAX     INTEGER {
        unknown(0),
        passedThrough(2),
        virtualized(3),
        notrepresented(4)
    }
    MAX-ACCESS read-only
    STATUS     current
    DESCRIPTION
        "Describes the consumers visibility to the
        allocated  resource.
        A value of 'Passed-Through' indicates the
        underlying or host resource is utilized and passed
        through to the consumer, possibly using
        partitioning. At least one item shall be present in
        the DeviceID property.  
        A value of 'Virtualized' indicates the resource is
        virtualized and may not map directly to an
        underlying/host resource. Some implementations may
        support specific assignment for virtualized
        resources, in which case the host resource(s) are
        exposed using the DeviceID property. 
        A value of 'Not represented' indicates a
        representation of the resource does not exist
        within the context of the resource consumer."
    ::= { msvmShutdownCompSettingDataEntry 8 }

msvmscsdDescription OBJECT-TYPE
    SYNTAX     WtcsDisplayString
    MAX-ACCESS read-only
    STATUS     current
    DESCRIPTION
        "The Description property provides a textual
        description of the object."
    ::= { msvmShutdownCompSettingDataEntry 9 }

msvmscsdElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmShutdownCompSettingDataEntry 10 }

msvmscsdEnabledState OBJECT-TYPE
    SYNTAX     Integer32
    MAX-ACCESS read-only
    STATUS     current
    DESCRIPTION
        "An integer enumeration that indicates the enabled
        and disabled states of an element. This property is
        inherited from CIM_EnabledLogicalElement and is
        either set to 2 ('Enabled') or 3 ('Disabled')."
    ::= { msvmShutdownCompSettingDataEntry 11 }

msvmscsdHostResource OBJECT-TYPE
    SYNTAX     WtcsDisplayString
    MAX-ACCESS read-only
    STATUS     current
    DESCRIPTION
        "This property exposes specific assignment to host
        or underlying resources.        The embedded
        instances shall contain only key properties and be
        treated as Object Paths. If the virtual resource
        may be scheduled on a number of underlying
        resources, this property shall be left NULL. In
        that case, the DeviceAllocatedFromPool or
        ResourceAllocationFromPool associations may be used
        to determine the pool of host resources this
        virtual resource may be scheduled on. If specific
        assignment is utilized, all underlying resources
        used by this virtual resource shall be listed in
        this array.  Typically the array will contain one
        item, however for aggregate allocations, such as
        multiple processors, multiple host resources may be
        specified."
    ::= { msvmShutdownCompSettingDataEntry 12 }

msvmscsdInstanceID OBJECT-TYPE
    SYNTAX     WtcsDisplayString
    MAX-ACCESS read-only
    STATUS     current
    DESCRIPTION
        "Within the scope of the instantiating Namespace,
        InstanceID opaquely and uniquely identifies an
        instance of this class. To ensure uniqueness within
        the NameSpace, the value of InstanceID should be
        constructed using the following 'preferred'
        algorithm: 
        <OrgID>:<LocalID> 
        Where <OrgID> and <LocalID> are separated by a
        colon (:), and where <OrgID> must include a
        copyrighted, trademarked, or otherwise unique name
        that is owned by the business entity that is
        creating or defining the InstanceID or that is a
        registered ID assigned to the business entity by a
        recognized global authority. (This requirement is
        similar to the <Schema Name>_<Class Name> structure
        of Schema class names.) In addition, to ensure
        uniqueness, <OrgID> must not contain a colon (:).
        When using this algorithm, the first colon to
        appear in InstanceID must appear between <OrgID>
        and <LocalID>. 
        <LocalID> is chosen by the business entity and
        should not be reused to identify different
        underlying (real-world) elements. If the above
        'preferred' algorithm is not used, the defining
        entity must assure that the resulting InstanceID is
        not reused across any InstanceIDs produced by this
        or other providers for the NameSpace of this
        instance. 
        For DMTF-defined instances, the 'preferred'
        algorithm must be used with the <OrgID> set to
        CIM."
    ::= { msvmShutdownCompSettingDataEntry 13 }

msvmscsdLimit OBJECT-TYPE
    SYNTAX     Gauge32
    MAX-ACCESS read-only
    STATUS     current
    DESCRIPTION
        "This property specifies the upper bound, or
        maximum amount of resource that will be granted for
        this allocation. For example, a system which
        supports memory paging may support setting the
        Limit of a Memory allocation below that of the
        VirtualQuantity, thus forcing paging to occur for
        this allocation."
    ::= { msvmShutdownCompSettingDataEntry 14 }

msvmscsdMappingBehavior OBJECT-TYPE
    SYNTAX     INTEGER {
        unknown(0),
        notSupported(1),
        dedicated(2),
        softAffinity(3),
        hardAffinity(4)
    }
    MAX-ACCESS read-only
    STATUS     current
    DESCRIPTION
        "Specifies how this resource maps to underlying
        resourcesIf the HostResource array contains any
        entries, this property reflects how the resource
        maps to those specific resources."
    ::= { msvmShutdownCompSettingDataEntry 15 }

msvmscsdOtherResourceType OBJECT-TYPE
    SYNTAX     WtcsDisplayString
    MAX-ACCESS read-only
    STATUS     current
    DESCRIPTION
        "A string that describes the resource type when a
        well defined value is not available and
        ResourceType has the value 'Other'."
    ::= { msvmShutdownCompSettingDataEntry 16 }

msvmscsdParent OBJECT-TYPE
    SYNTAX     WtcsDisplayString
    MAX-ACCESS read-only
    STATUS     current
    DESCRIPTION
        "The Parent of the resource.  For example, a
        controller for the current allocation"
    ::= { msvmShutdownCompSettingDataEntry 17 }

msvmscsdPoolID OBJECT-TYPE
    SYNTAX     WtcsDisplayString
    MAX-ACCESS read-only
    STATUS     current
    DESCRIPTION
        "This property specifies which ResourcePool the
        resource is currently allocated from, or which
        ResourcePool the resource will be allocated from
        when the allocation occurs."
    ::= { msvmShutdownCompSettingDataEntry 18 }

msvmscsdReservation OBJECT-TYPE
    SYNTAX     Gauge32
    MAX-ACCESS read-only
    STATUS     current
    DESCRIPTION
        "This property specifies the amount of resource
        guaranteed to be available for this allocation.  On
        system which support over-commitment of resources,
        this value is typically used for admission control
        to prevent an an allocation from being accepted
        thus preventing starvation."
    ::= { msvmShutdownCompSettingDataEntry 19 }

msvmscsdResourceSubType OBJECT-TYPE
    SYNTAX     WtcsDisplayString
    MAX-ACCESS read-only
    STATUS     current
    DESCRIPTION
        "A string describing an implementation specific
        sub-type for this resource.  For example, this may
        be used to distinguish different models of the same
        resource type."
    ::= { msvmShutdownCompSettingDataEntry 20 }

msvmscsdResourceType OBJECT-TYPE
    SYNTAX     INTEGER {
        other(1),
        computerSystem(2),
        processor(3),
        memory(4),
        ideController(5),
        parallelSCSIHBA(6),
        fcHBA(7),
        iSCSIHBA(8),
        ibHCA(9),
        ethernetAdapter(10),
        iOSlot(11),
        iODevice(12),
        floppyDrive(13),
        cdDrive(14),
        dvddrive(15),
        serialport(16),
        parallelport(17),
        usbController(18),
        graphicscontroller(19),
        storageExtent(20),
        disk(21),
        tape(22),
        otherstoragedevice(23),
        firewireController(24),
        partitionableUnit(25),
        basePartitionableUnit(26),
        powerSupply(27),
        coolingDevice(28),
        dmtfreserved(29)
    }
    MAX-ACCESS read-only
    STATUS     current
    DESCRIPTION
        "The type of resource this allocation setting
        represents."
    ::= { msvmShutdownCompSettingDataEntry 21 }

msvmscsdVirtualQuantity OBJECT-TYPE
    SYNTAX     Gauge32
    MAX-ACCESS read-only
    STATUS     current
    DESCRIPTION
        "This property specifies the quantity of resources
        presented to the consumer.  For example, when
        ResourceType=Processor,  this property would
        reflect the number of discrete Processors presented
        to the virtual computer system.  When
        ResourceType=Memory, this property could reflect
        the number of MB reported to the virtual computer
        system."
    ::= { msvmShutdownCompSettingDataEntry 22 }

msvmscsdWeight OBJECT-TYPE
    SYNTAX     Gauge32
    MAX-ACCESS read-only
    STATUS     current
    DESCRIPTION
        "This property specifies a relative priority for
        this allocation in relation to other allocations
        from the same ResourcePool.  This property has no
        unit of measure, and is only relevant when compared
        to other allocations vying for the same host
        resources."
    ::= { msvmShutdownCompSettingDataEntry 23 }

msvmTimeSyncComponentTable OBJECT-TYPE
    SYNTAX     SEQUENCE OF MsvmTimeSyncComponent
    MAX-ACCESS not-accessible
    STATUS     current
    DESCRIPTION
        "Represents the state of the time synchronization
        component, which is responsible for synchronizing
        the system time of a virtual machine with the
        system time of the operating system running in the
        parent partition."
    ::= { msvmIntegrationComponents 8 }

msvmTimeSyncComponentEntry OBJECT-TYPE
    SYNTAX     MsvmTimeSyncComponent
    MAX-ACCESS not-accessible
    STATUS     current
    DESCRIPTION
        "None"
    INDEX      { msvmtscIndex }
    ::= { msvmTimeSyncComponentTable 1 }

MsvmTimeSyncComponent ::= SEQUENCE {
    msvmtscIndex Integer32,
    msvmtscAdditionalAvailability INTEGER,
    msvmtscAvailability INTEGER,
    msvmtscCaption WtcsDisplayString,
    msvmtscCreationClassName WtcsDisplayString,
    msvmtscDescription WtcsDisplayString,
    msvmtscDeviceID WtcsDisplayString,
    msvmtscElementName WtcsDisplayString,
    msvmtscEnabledDefault INTEGER,
    msvmtscEnabledState INTEGER,
    msvmtscErrorCleared TruthValue,
    msvmtscErrorDescription WtcsDisplayString,
    msvmtscHealthState INTEGER,
    msvmtscIdentifyingDescriptions WtcsDisplayString,
    msvmtscInstallDate DateAndTime,
    msvmtscLastErrorCode Gauge32,
    msvmtscLocationIndicator INTEGER,
    msvmtscMaxQuiesceTime Gauge32,
    msvmtscName WtcsDisplayString,
    msvmtscOperationalStatus INTEGER,
    msvmtscOtherEnabledState WtcsDisplayString,
    msvmtscOtherIdentifyingInfo WtcsDisplayString,
    msvmtscPowerManagementCapability INTEGER,
    msvmtscPowerManagementSupported TruthValue,
    msvmtscPowerOnHours Gauge32,
    msvmtscRequestedState INTEGER,
    msvmtscStatus WtcsDisplayString,
    msvmtscStatusDescriptions WtcsDisplayString,
    msvmtscStatusInfo INTEGER,
    msvmtscSystemCreationClassName WtcsDisplayString,
    msvmtscSystemName WtcsDisplayString,
    msvmtscTimeOfLastStateChange DateAndTime,
    msvmtscTotalPowerOnHours Gauge32
}

msvmtscIndex OBJECT-TYPE
    SYNTAX     Integer32 (1..2147483647)
    MAX-ACCESS read-only
    STATUS     current
    DESCRIPTION
        "The value of this object uniquely identifies the
        instance entry for this class."
    ::= { msvmTimeSyncComponentEntry 1 }

msvmtscAdditionalAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Additional availability and status of the Device
        in addition to that specified in the Availability
        property. The Availability property denotes the
        primary status and availability of the Device. In
        some cases, this property will not be sufficient to
        denote the complete status of the Device. In those
        cases, the AdditionalAvailability property can be
        used to provide further information. For example,
        the primary Availability of a device might be 'Off
        line' (value=8) or in a low-power state
        (AdditionalAvailability value=14), or the Device
        could be running Diagnostics
        (AdditionalAvailability value=5, 'In Test')."
    ::= { msvmTimeSyncComponentEntry 2 }

msvmtscAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Note: The use of this property has been
        deprecated. 
        Deprecated description: The primary availability
        and status of the Device. (Additional status
        information can be specified using the Additional
        Availability array property.) For example, the
        Availability property indicates that the Device is
        running and has full power (value=3), or is in a
        warning (4), test (5), degraded (10) or power save
        state (values 13-15 and 17). The Power Save states
        are defined as follows: Value 13 ('Power Save -
        Unknown') indicates that the Device is known to be
        in a power save mode, but its exact status in this
        mode is unknown; value 14 ('Power Save - Low Power
        Mode') indicates that the Device is in a power save
        state but still functioning, and might exhibit
        degraded performance; value 15 ('Power Save -
        Standby') indicates that the Device is not
        functioning but could be brought to full power
        'quickly'; and value 17 ('Power Save - Warning')
        indicates that the Device is in a warning state,
        but is also in a power save mode."
    ::= { msvmTimeSyncComponentEntry 3 }

msvmtscCaption OBJECT-TYPE
    SYNTAX     WtcsDisplayString (SIZE (0..64))
    MAX-ACCESS read-only
    STATUS     current
    DESCRIPTION
        "The Caption property is a short textual
        description (one- line string) of the object."
    ::= { msvmTimeSyncComponentEntry 4 }

msvmtscCreationClassName OBJECT-TYPE
    SYNTAX     WtcsDisplayString (SIZE (0..256))
    MAX-ACCESS read-only
    STATUS     current
    DESCRIPTION
        "CreationClassName indicates the name of the class
        or the subclass used in the creation of an
        instance. When used with the other key properties
        of this class, this property allows all instances
        of this class and its subclasses to be uniquely
        identified."
    ::= { msvmTimeSyncComponentEntry 5 }

msvmtscDescription OBJECT-TYPE
    SYNTAX     WtcsDisplayString
    MAX-ACCESS read-only
    STATUS     current
    DESCRIPTION
        "The Description property provides a textual
        description of the object."
    ::= { msvmTimeSyncComponentEntry 6 }

msvmtscDeviceID OBJECT-TYPE
    SYNTAX     WtcsDisplayString (SIZE (0..64))
    MAX-ACCESS read-only
    STATUS     current
    DESCRIPTION
        "An address or other identifying information used
        to uniquely name the LogicalDevice."
    ::= { msvmTimeSyncComponentEntry 7 }

msvmtscElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmTimeSyncComponentEntry 8 }

msvmtscEnabledDefault OBJECT-TYPE
    SYNTAX     INTEGER {
        enabled(2),
        disabled(3),
        notApplicable(5),
        enabledbutOffline(6),
        noDefault(7)
    }
    MAX-ACCESS read-only
    STATUS     current
    DESCRIPTION
        "An enumerated value indicating an administrator's
        default or startup configuration for the Enabled
        State of an element. By default, the element is
        'Enabled' (value=2)."
    ::= { msvmTimeSyncComponentEntry 9 }

msvmtscEnabledState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "EnabledState is an integer enumeration that
        indicates the enabled and disabled states of an
        element. It can also indicate the transitions
        between these requested states. For example,
        shutting down (value=4) and starting (value=10) are
        transient states between enabled and disabled. The
        following text briefly summarizes the various
        enabled and disabled states: 
        Enabled (2) indicates that the element is or could
        be executing commands, will process any queued
        commands, and queues new requests. 
        Disabled (3) indicates that the element will not
        execute commands and will drop any new requests. 
        Shutting Down (4) indicates that the element is in
        the process of going to a Disabled state. 
        Not Applicable (5) indicates the element does not
        support being enabled or disabled. 
        Enabled but Offline (6) indicates that the element
        might be completing commands, and will drop any new
        requests. 
        Test (7) indicates that the element is in a test
        state. 
        Deferred (8) indicates that the element might be
        completing commands, but will queue any new
        requests. 
        Quiesce (9) indicates that the element is enabled
        but in a restricted mode. The behavior of the
        element is similar to the Enabled state, but it
        processes only a restricted set of commands. All
        other requests are queued. 
        Starting (10) indicates that the element is in the
        process of going to an Enabled state. New requests
        are queued."
    ::= { msvmTimeSyncComponentEntry 10 }

msvmtscErrorCleared OBJECT-TYPE
    SYNTAX     TruthValue
    MAX-ACCESS read-only
    STATUS     current
    DESCRIPTION
        "Note: The use of this method is deprecated. 
        Deprecated description: ErrorCleared is a Boolean
        property that indicates that the error reported in
        LastErrorCode is now cleared."
    ::= { msvmTimeSyncComponentEntry 11 }

msvmtscErrorDescription OBJECT-TYPE
    SYNTAX     WtcsDisplayString
    MAX-ACCESS read-only
    STATUS     current
    DESCRIPTION
        "Note: The use of this method is deprecated. 
        Deprecated description: ErrorDescription is a
        free-form string that supplies more information
        about the error recorded in LastErrorCode and
        information on any corrective actions that can be
        taken."
    ::= { msvmTimeSyncComponentEntry 12 }

msvmtscHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmTimeSyncComponentEntry 13 }

msvmtscIdentifyingDescriptions OBJECT-TYPE
    SYNTAX     WtcsDisplayString
    MAX-ACCESS read-only
    STATUS     current
    DESCRIPTION
        "An array of free-form strings providing
        explanations and details behind the entries in the
        OtherIdentifyingInfo array. Note that each entry of
        this array is related to the entry in
        OtherIdentifyingInfo that is located at the same
        index."
    ::= { msvmTimeSyncComponentEntry 14 }

msvmtscInstallDate OBJECT-TYPE
    SYNTAX     DateAndTime
    MAX-ACCESS read-only
    STATUS     current
    DESCRIPTION
        "A datetime value that indicates when the object
        was installed. Lack of a value does not indicate
        that the object is not installed."
    ::= { msvmTimeSyncComponentEntry 15 }

msvmtscLastErrorCode OBJECT-TYPE
    SYNTAX     Gauge32
    MAX-ACCESS read-only
    STATUS     current
    DESCRIPTION
        "Note: The use of this method is deprecated. 
        Deprecated description: LastErrorCode captures the
        last error code reported by the LogicalDevice."
    ::= { msvmTimeSyncComponentEntry 16 }

msvmtscLocationIndicator OBJECT-TYPE
    SYNTAX     INTEGER {
        unknown(0),
        on(2),
        off(3),
        notSupported(4)
    }
    MAX-ACCESS read-only
    STATUS     current
    DESCRIPTION
        "An integer that reflects the state of an indicator
        (e.g., LED) that is part of a device. Reading the
        value gives the current state. Writing the value
        with 'On'/'Off' turns the indicator on/off, other
        values may not be written."
    ::= { msvmTimeSyncComponentEntry 17 }

msvmtscMaxQuiesceTime OBJECT-TYPE
    SYNTAX     Gauge32
    UNITS "MilliSeconds"
    MAX-ACCESS read-only
    STATUS     current
    DESCRIPTION
        "Note: The use of this property has been
        deprecated. When evaluating the use of Quiesce, it
        was determined that this single property is not
        adequate for describing when a device will
        automatically exit a quiescent state. In fact, the
        most likely scenario for a device to exit a
        quiescent state was determined to be based on the
        number of outstanding requests queued rather than
        on a maximum time. This decision will be
        re-evaluated and repositioned later. 
        Deprecated description: Maximum time, in
        milliseconds, that a Device can run in a 'Quiesced'
        state. The state is defined in its Availability and
        AdditionalAvailability properties, where 'Quiesced'
        is conveyed by the value 21. What occurs at the end
        of the time limit is device-specific. The Device
        can unquiesce, can be offline, or can take other
        actions. A value of 0 indicates that a Device can
        remain quiesced indefinitely."
    ::= { msvmTimeSyncComponentEntry 18 }

msvmtscName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmTimeSyncComponentEntry 19 }

msvmtscOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmTimeSyncComponentEntry 20 }

msvmtscOtherEnabledState OBJECT-TYPE
    SYNTAX     WtcsDisplayString
    MAX-ACCESS read-only
    STATUS     current
    DESCRIPTION
        "A string that describes the enabled or disabled
        state of the element when the EnabledState property
        is set to 1 ('Other'). This property must be set to
        null when EnabledState is any value other than 1."
    ::= { msvmTimeSyncComponentEntry 21 }

msvmtscOtherIdentifyingInfo OBJECT-TYPE
    SYNTAX     WtcsDisplayString (SIZE (0..256))
    MAX-ACCESS read-only
    STATUS     current
    DESCRIPTION
        "OtherIdentifyingInfo captures data, in addition to
        DeviceID information, that could be used to
        identify a LogicalDevice. For example, you could
        use this property to hold the operating system's
        user-friendly name for the Device."
    ::= { msvmTimeSyncComponentEntry 22 }

msvmtscPowerManagementCapability OBJECT-TYPE
    SYNTAX     INTEGER {
        unknown(0),
        notSupported(1),
        disabled(2),
        enabled(3),
        powerSavingModesEnteredAutomatic(4),
        powerStateSettable(5),
        powerCyclingSupported(6),
        timedPowerOnSupported(7)
    }
    MAX-ACCESS read-only
    STATUS     current
    DESCRIPTION
        "Note: The use of this property has been
        deprecated. Instead, use the PowerCapabilites
        property in an associated
        PowerManagementCapabilities class. Deprecated
        description: An enumerated array describing the
        power management capabilities of the Device."
    ::= { msvmTimeSyncComponentEntry 23 }

msvmtscPowerManagementSupported OBJECT-TYPE
    SYNTAX     TruthValue
    MAX-ACCESS read-only
    STATUS     current
    DESCRIPTION
        "Note: The use of this property has been
        deprecated. Instead, the existence of an associated
        PowerManagementCapabilities class (associated using
        the ElementCapabilities relationship) indicates
        that power management is supported. Deprecated
        description: Boolean that indicates that the Device
        can use power management."
    ::= { msvmTimeSyncComponentEntry 24 }

msvmtscPowerOnHours OBJECT-TYPE
    SYNTAX     Gauge32
    UNITS "Hours"
    MAX-ACCESS read-only
    STATUS     current
    DESCRIPTION
        "Note: The use of this method is deprecated. 
        Deprecated description: The number of consecutive
        hours that this Device has been powered on since
        its last power cycle."
    ::= { msvmTimeSyncComponentEntry 25 }

msvmtscRequestedState OBJECT-TYPE
    SYNTAX     INTEGER {
        enabled(2),
        disabled(3),
        shutDown(4),
        noChange(5),
        offline(6),
        test(7),
        deferred(8),
        quiesce(9),
        reboot(10),
        reset(11),
        notApplicable(12)
    }
    MAX-ACCESS read-only
    STATUS     current
    DESCRIPTION
        "RequestedState is an integer enumeration that
        indicates the last requested or desired state for
        the element. The actual state of the element is
        represented by EnabledState. This property is
        provided to compare the last requested and current
        enabled or disabled states. Note that when
        EnabledState is set to 5 ('Not Applicable'), then
        this property has no meaning. By default, the
        RequestedState of the element is 5 ('No Change').
        Refer to the EnabledState property description for
        explanations of the values in the RequestedState
        enumeration. 
        
        It should be noted that there are two new values in
        RequestedState that build on the statuses of
        EnabledState. These are 'Reboot' (10) and 'Reset'
        (11). Reboot refers to doing a 'Shut Down' and then
        moving to an 'Enabled' state. Reset indicates that
        the element is first 'Disabled' and then 'Enabled'.
        The distinction between requesting 'Shut Down' and
        'Disabled' should also be noted. Shut Down requests
        an orderly transition to the Disabled state, and
        might involve removing power, to completely erase
        any existing state. The Disabled state requests an
        immediate disabling of the element, such that it
        will not execute or accept any commands or
        processing requests. 
        
        This property is set as the result of a method
        invocation (such as Start or StopService on
        CIM_Service), or can be overridden and defined as
        WRITEable in a subclass. The method approach is
        considered superior to a WRITEable property,
        because it allows an explicit invocation of the
        operation and the return of a result code. 
        
        A particular instance of EnabledLogicalElement
        might not support RequestedStateChange. If this
        occurs, the value 12 ('Not Applicable') is used."
    ::= { msvmTimeSyncComponentEntry 26 }

msvmtscStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmTimeSyncComponentEntry 27 }

msvmtscStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmTimeSyncComponentEntry 28 }

msvmtscStatusInfo OBJECT-TYPE
    SYNTAX     INTEGER {
        other(1),
        unknown(2),
        enabled(3),
        disabled(4),
        notApplicable(5)
    }
    MAX-ACCESS read-only
    STATUS     current
    DESCRIPTION
        "Note: The use of this method is deprecated in lieu
        of a more clearly named property (EnabledState)
        that is inherited from ManagedSystemElement and
        that has additional enumerated values. 
        Deprecated description: The StatusInfo property
        indicates whether the Logical Device is in an
        enabled state (value=3), disabled state (value=4),
        some other state (value=1), or an unknown state
        (value=2). If this property does not apply to the
        LogicalDevice, the value 5 ('Not Applicable')
        should be used. If a Device is
        ('Enabled')(value=3), it has been powered up and is
        configured and operational. The Device might or
        might not be functionally active, depending on
        whether its Availability (or
        AdditionalAvailability) indicates that it is
        ('Running/Full Power')(value=3) or ('Off line')
        (value=8). In an enabled but offline mode, a Device
        might be performing out-of-band requests, such as
        running Diagnostics. If StatusInfo is ('Disabled')
        (value=4), a Device can only be 'enabled' or
        powered off. In a personal computer environment,
        ('Disabled') means that the driver of the device is
        not available in the stack. In other environments,
        a Device can be disabled by removing its
        configuration file. A disabled device is physically
        present in a System and consuming resources, but it
        cannot be communicated with until a driver is
        loaded, a configuration file is loaded, or some
        other 'enabling' activity has occurred."
    ::= { msvmTimeSyncComponentEntry 29 }

msvmtscSystemCreationClassName OBJECT-TYPE
    SYNTAX     WtcsDisplayString (SIZE (0..256))
    MAX-ACCESS read-only
    STATUS     current
    DESCRIPTION
        "The CreationClassName of the scoping system."
    ::= { msvmTimeSyncComponentEntry 30 }

msvmtscSystemName OBJECT-TYPE
    SYNTAX     WtcsDisplayString (SIZE (0..256))
    MAX-ACCESS read-only
    STATUS     current
    DESCRIPTION
        "The System Name of the scoping system."
    ::= { msvmTimeSyncComponentEntry 31 }

msvmtscTimeOfLastStateChange OBJECT-TYPE
    SYNTAX     DateAndTime
    MAX-ACCESS read-only
    STATUS     current
    DESCRIPTION
        "The date or time when the EnabledState of the
        element last changed. If the state of the element
        has not changed and this property is populated,
        then it must be set to a 0 interval value. If a
        state change was requested, but rejected or not yet
        processed, the property must not be updated."
    ::= { msvmTimeSyncComponentEntry 32 }

msvmtscTotalPowerOnHours OBJECT-TYPE
    SYNTAX     Gauge32
    UNITS "Hours"
    MAX-ACCESS read-only
    STATUS     current
    DESCRIPTION
        "Note: The use of this method is deprecated. 
        Deprecated description: The total number of hours
        that this Device has been powered on."
    ::= { msvmTimeSyncComponentEntry 33 }

msvmTimeSyncCompSettingDataTable OBJECT-TYPE
    SYNTAX     SEQUENCE OF MsvmTimeSyncComponentSettingData
    MAX-ACCESS not-accessible
    STATUS     current
    DESCRIPTION
        "Represents the configured state of the time
        synchronization component."
    ::= { msvmIntegrationComponents 9 }

msvmTimeSyncCompSettingDataEntry OBJECT-TYPE
    SYNTAX     MsvmTimeSyncComponentSettingData
    MAX-ACCESS not-accessible
    STATUS     current
    DESCRIPTION
        "None"
    INDEX      { msvmtscsdIndex }
    ::= { msvmTimeSyncCompSettingDataTable 1 }

MsvmTimeSyncComponentSettingData ::= SEQUENCE {
    msvmtscsdIndex Integer32,
    msvmtscsdAddress WtcsDisplayString,
    msvmtscsdAllocationUnits WtcsDisplayString,
    msvmtscsdAutomaticAllocation TruthValue,
    msvmtscsdAutomaticDeallocation TruthValue,
    msvmtscsdCaption WtcsDisplayString,
    msvmtscsdConnection WtcsDisplayString,
    msvmtscsdConsumerVisibility INTEGER,
    msvmtscsdDescription WtcsDisplayString,
    msvmtscsdElementName WtcsDisplayString,
    msvmtscsdEnabledState Integer32,
    msvmtscsdHostResource WtcsDisplayString,
    msvmtscsdInstanceID WtcsDisplayString,
    msvmtscsdLimit Gauge32,
    msvmtscsdMappingBehavior INTEGER,
    msvmtscsdOtherResourceType WtcsDisplayString,
    msvmtscsdParent WtcsDisplayString,
    msvmtscsdPoolID WtcsDisplayString,
    msvmtscsdReservation Gauge32,
    msvmtscsdResourceSubType WtcsDisplayString,
    msvmtscsdResourceType INTEGER,
    msvmtscsdVirtualQuantity Gauge32,
    msvmtscsdWeight Gauge32
}

msvmtscsdIndex OBJECT-TYPE
    SYNTAX     Integer32 (1..2147483647)
    MAX-ACCESS read-only
    STATUS     current
    DESCRIPTION
        "The value of this object uniquely identifies the
        instance entry for this class."
    ::= { msvmTimeSyncCompSettingDataEntry 1 }

msvmtscsdAddress OBJECT-TYPE
    SYNTAX     WtcsDisplayString
    MAX-ACCESS read-only
    STATUS     current
    DESCRIPTION
        "The address of the resource.For example, the MAC
        address of a Ethernet port."
    ::= { msvmTimeSyncCompSettingDataEntry 2 }

msvmtscsdAllocationUnits OBJECT-TYPE
    SYNTAX     WtcsDisplayString
    MAX-ACCESS read-only
    STATUS     current
    DESCRIPTION
        "This property specifies the units of allocation
        used by the Reservation and Limit properties.  For
        example, when ResourceType=Processor,
        AllocationUnits may be set to MHZ. When
        ResourceType=Memory, AllocationUnits may be set to
        MB"
    ::= { msvmTimeSyncCompSettingDataEntry 3 }

msvmtscsdAutomaticAllocation OBJECT-TYPE
    SYNTAX     TruthValue
    MAX-ACCESS read-only
    STATUS     current
    DESCRIPTION
        "This property specifies if the resource will be
        automatically allocated.  For example when set to
        true, when the consuming virtual computer system is
        powered on, this resource would be allocated.  A
        value of false indicates the resource must be
        explicitly allocated.  For example, the setting may
        represent removable media (cdrom, floppy, etc.)
        where at power on time, the media isnot present. 
        An explicit operation is required to allocate the
        resource."
    ::= { msvmTimeSyncCompSettingDataEntry 4 }

msvmtscsdAutomaticDeallocation OBJECT-TYPE
    SYNTAX     TruthValue
    MAX-ACCESS read-only
    STATUS     current
    DESCRIPTION
        "This property specifies if the resource will be
        automatically de-allocated.  For example, when set
        to true, when the consuming virtual computer system
        is powered off, this resource would be
        de-allocated.  When set to false, the resource will
        remain allocated and must be explicitly
        de-allocated."
    ::= { msvmTimeSyncCompSettingDataEntry 5 }

msvmtscsdCaption OBJECT-TYPE
    SYNTAX     WtcsDisplayString (SIZE (0..64))
    MAX-ACCESS read-only
    STATUS     current
    DESCRIPTION
        "The Caption property is a short textual
        description (one- line string) of the object."
    ::= { msvmTimeSyncCompSettingDataEntry 6 }

msvmtscsdConnection OBJECT-TYPE
    SYNTAX     WtcsDisplayString
    MAX-ACCESS read-only
    STATUS     current
    DESCRIPTION
        "The thing to which this resource is connected. 
        For example, a named network or switch port."
    ::= { msvmTimeSyncCompSettingDataEntry 7 }

msvmtscsdConsumerVisibility OBJECT-TYPE
    SYNTAX     INTEGER {
        unknown(0),
        passedThrough(2),
        virtualized(3),
        notrepresented(4)
    }
    MAX-ACCESS read-only
    STATUS     current
    DESCRIPTION
        "Describes the consumers visibility to the
        allocated  resource.
        A value of 'Passed-Through' indicates the
        underlying or host resource is utilized and passed
        through to the consumer, possibly using
        partitioning. At least one item shall be present in
        the DeviceID property.  
        A value of 'Virtualized' indicates the resource is
        virtualized and may not map directly to an
        underlying/host resource. Some implementations may
        support specific assignment for virtualized
        resources, in which case the host resource(s) are
        exposed using the DeviceID property. 
        A value of 'Not represented' indicates a
        representation of the resource does not exist
        within the context of the resource consumer."
    ::= { msvmTimeSyncCompSettingDataEntry 8 }

msvmtscsdDescription OBJECT-TYPE
    SYNTAX     WtcsDisplayString
    MAX-ACCESS read-only
    STATUS     current
    DESCRIPTION
        "The Description property provides a textual
        description of the object."
    ::= { msvmTimeSyncCompSettingDataEntry 9 }

msvmtscsdElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmTimeSyncCompSettingDataEntry 10 }

msvmtscsdEnabledState OBJECT-TYPE
    SYNTAX     Integer32
    MAX-ACCESS read-only
    STATUS     current
    DESCRIPTION
        "An integer enumeration that indicates the enabled
        and disabled states of an element. This property is
        inherited from CIM_EnabledLogicalElement and is
        either set to 2 ('Enabled') or 3 ('Disabled')."
    ::= { msvmTimeSyncCompSettingDataEntry 11 }

msvmtscsdHostResource OBJECT-TYPE
    SYNTAX     WtcsDisplayString
    MAX-ACCESS read-only
    STATUS     current
    DESCRIPTION
        "This property exposes specific assignment to host
        or underlying resources.        The embedded
        instances shall contain only key properties and be
        treated as Object Paths. If the virtual resource
        may be scheduled on a number of underlying
        resources, this property shall be left NULL. In
        that case, the DeviceAllocatedFromPool or
        ResourceAllocationFromPool associations may be used
        to determine the pool of host resources this
        virtual resource may be scheduled on. If specific
        assignment is utilized, all underlying resources
        used by this virtual resource shall be listed in
        this array.  Typically the array will contain one
        item, however for aggregate allocations, such as
        multiple processors, multiple host resources may be
        specified."
    ::= { msvmTimeSyncCompSettingDataEntry 12 }

msvmtscsdInstanceID OBJECT-TYPE
    SYNTAX     WtcsDisplayString
    MAX-ACCESS read-only
    STATUS     current
    DESCRIPTION
        "Within the scope of the instantiating Namespace,
        InstanceID opaquely and uniquely identifies an
        instance of this class. To ensure uniqueness within
        the NameSpace, the value of InstanceID should be
        constructed using the following 'preferred'
        algorithm: 
        <OrgID>:<LocalID> 
        Where <OrgID> and <LocalID> are separated by a
        colon (:), and where <OrgID> must include a
        copyrighted, trademarked, or otherwise unique name
        that is owned by the business entity that is
        creating or defining the InstanceID or that is a
        registered ID assigned to the business entity by a
        recognized global authority. (This requirement is
        similar to the <Schema Name>_<Class Name> structure
        of Schema class names.) In addition, to ensure
        uniqueness, <OrgID> must not contain a colon (:).
        When using this algorithm, the first colon to
        appear in InstanceID must appear between <OrgID>
        and <LocalID>. 
        <LocalID> is chosen by the business entity and
        should not be reused to identify different
        underlying (real-world) elements. If the above
        'preferred' algorithm is not used, the defining
        entity must assure that the resulting InstanceID is
        not reused across any InstanceIDs produced by this
        or other providers for the NameSpace of this
        instance. 
        For DMTF-defined instances, the 'preferred'
        algorithm must be used with the <OrgID> set to
        CIM."
    ::= { msvmTimeSyncCompSettingDataEntry 13 }

msvmtscsdLimit OBJECT-TYPE
    SYNTAX     Gauge32
    MAX-ACCESS read-only
    STATUS     current
    DESCRIPTION
        "This property specifies the upper bound, or
        maximum amount of resource that will be granted for
        this allocation. For example, a system which
        supports memory paging may support setting the
        Limit of a Memory allocation below that of the
        VirtualQuantity, thus forcing paging to occur for
        this allocation."
    ::= { msvmTimeSyncCompSettingDataEntry 14 }

msvmtscsdMappingBehavior OBJECT-TYPE
    SYNTAX     INTEGER {
        unknown(0),
        notSupported(1),
        dedicated(2),
        softAffinity(3),
        hardAffinity(4)
    }
    MAX-ACCESS read-only
    STATUS     current
    DESCRIPTION
        "Specifies how this resource maps to underlying
        resourcesIf the HostResource array contains any
        entries, this property reflects how the resource
        maps to those specific resources."
    ::= { msvmTimeSyncCompSettingDataEntry 15 }

msvmtscsdOtherResourceType OBJECT-TYPE
    SYNTAX     WtcsDisplayString
    MAX-ACCESS read-only
    STATUS     current
    DESCRIPTION
        "A string that describes the resource type when a
        well defined value is not available and
        ResourceType has the value 'Other'."
    ::= { msvmTimeSyncCompSettingDataEntry 16 }

msvmtscsdParent OBJECT-TYPE
    SYNTAX     WtcsDisplayString
    MAX-ACCESS read-only
    STATUS     current
    DESCRIPTION
        "The Parent of the resource.  For example, a
        controller for the current allocation"
    ::= { msvmTimeSyncCompSettingDataEntry 17 }

msvmtscsdPoolID OBJECT-TYPE
    SYNTAX     WtcsDisplayString
    MAX-ACCESS read-only
    STATUS     current
    DESCRIPTION
        "This property specifies which ResourcePool the
        resource is currently allocated from, or which
        ResourcePool the resource will be allocated from
        when the allocation occurs."
    ::= { msvmTimeSyncCompSettingDataEntry 18 }

msvmtscsdReservation OBJECT-TYPE
    SYNTAX     Gauge32
    MAX-ACCESS read-only
    STATUS     current
    DESCRIPTION
        "This property specifies the amount of resource
        guaranteed to be available for this allocation.  On
        system which support over-commitment of resources,
        this value is typically used for admission control
        to prevent an an allocation from being accepted
        thus preventing starvation."
    ::= { msvmTimeSyncCompSettingDataEntry 19 }

msvmtscsdResourceSubType OBJECT-TYPE
    SYNTAX     WtcsDisplayString
    MAX-ACCESS read-only
    STATUS     current
    DESCRIPTION
        "A string describing an implementation specific
        sub-type for this resource.  For example, this may
        be used to distinguish different models of the same
        resource type."
    ::= { msvmTimeSyncCompSettingDataEntry 20 }

msvmtscsdResourceType OBJECT-TYPE
    SYNTAX     INTEGER {
        other(1),
        computerSystem(2),
        processor(3),
        memory(4),
        ideController(5),
        parallelSCSIHBA(6),
        fcHBA(7),
        iSCSIHBA(8),
        ibHCA(9),
        ethernetAdapter(10),
        iOSlot(11),
        iODevice(12),
        floppyDrive(13),
        cdDrive(14),
        dvddrive(15),
        serialport(16),
        parallelport(17),
        usbController(18),
        graphicscontroller(19),
        storageExtent(20),
        disk(21),
        tape(22),
        otherstoragedevice(23),
        firewireController(24),
        partitionableUnit(25),
        basePartitionableUnit(26),
        powerSupply(27),
        coolingDevice(28),
        dmtfreserved(29)
    }
    MAX-ACCESS read-only
    STATUS     current
    DESCRIPTION
        "The type of resource this allocation setting
        represents."
    ::= { msvmTimeSyncCompSettingDataEntry 21 }

msvmtscsdVirtualQuantity OBJECT-TYPE
    SYNTAX     Gauge32
    MAX-ACCESS read-only
    STATUS     current
    DESCRIPTION
        "This property specifies the quantity of resources
        presented to the consumer.  For example, when
        ResourceType=Processor,  this property would
        reflect the number of discrete Processors presented
        to the virtual computer system.  When
        ResourceType=Memory, this property could reflect
        the number of MB reported to the virtual computer
        system."
    ::= { msvmTimeSyncCompSettingDataEntry 22 }

msvmtscsdWeight OBJECT-TYPE
    SYNTAX     Gauge32
    MAX-ACCESS read-only
    STATUS     current
    DESCRIPTION
        "This property specifies a relative priority for
        this allocation in relation to other allocations
        from the same ResourcePool.  This property has no
        unit of measure, and is only relevant when compared
        to other allocations vying for the same host
        resources."
    ::= { msvmTimeSyncCompSettingDataEntry 23 }

msvmVssComponentTable OBJECT-TYPE
    SYNTAX     SEQUENCE OF MsvmVssComponent
    MAX-ACCESS not-accessible
    STATUS     current
    DESCRIPTION
        "Represents the state of the Volume Shadow Copy
        Service (VSS) component."
    ::= { msvmIntegrationComponents 10 }

msvmVssComponentEntry OBJECT-TYPE
    SYNTAX     MsvmVssComponent
    MAX-ACCESS not-accessible
    STATUS     current
    DESCRIPTION
        "None"
    INDEX      { msvmvcIndex }
    ::= { msvmVssComponentTable 1 }

MsvmVssComponent ::= SEQUENCE {
    msvmvcIndex Integer32,
    msvmvcAdditionalAvailability INTEGER,
    msvmvcAvailability INTEGER,
    msvmvcCaption WtcsDisplayString,
    msvmvcCreationClassName WtcsDisplayString,
    msvmvcDescription WtcsDisplayString,
    msvmvcDeviceID WtcsDisplayString,
    msvmvcElementName WtcsDisplayString,
    msvmvcEnabledDefault INTEGER,
    msvmvcEnabledState INTEGER,
    msvmvcErrorCleared TruthValue,
    msvmvcErrorDescription WtcsDisplayString,
    msvmvcHealthState INTEGER,
    msvmvcIdentifyingDescriptions WtcsDisplayString,
    msvmvcInstallDate DateAndTime,
    msvmvcLastErrorCode Gauge32,
    msvmvcLocationIndicator INTEGER,
    msvmvcMaxQuiesceTime Gauge32,
    msvmvcName WtcsDisplayString,
    msvmvcOperationalStatus INTEGER,
    msvmvcOtherEnabledState WtcsDisplayString,
    msvmvcOtherIdentifyingInfo WtcsDisplayString,
    msvmvcPowerManagementCapability INTEGER,
    msvmvcPowerManagementSupported TruthValue,
    msvmvcPowerOnHours Gauge32,
    msvmvcRequestedState INTEGER,
    msvmvcStatus WtcsDisplayString,
    msvmvcStatusDescriptions WtcsDisplayString,
    msvmvcStatusInfo INTEGER,
    msvmvcSystemCreationClassName WtcsDisplayString,
    msvmvcSystemName WtcsDisplayString,
    msvmvcTimeOfLastStateChange DateAndTime,
    msvmvcTotalPowerOnHours Gauge32
}

msvmvcIndex OBJECT-TYPE
    SYNTAX     Integer32 (1..2147483647)
    MAX-ACCESS read-only
    STATUS     current
    DESCRIPTION
        "The value of this object uniquely identifies the
        instance entry for this class."
    ::= { msvmVssComponentEntry 1 }

msvmvcAdditionalAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Additional availability and status of the Device
        in addition to that specified in the Availability
        property. The Availability property denotes the
        primary status and availability of the Device. In
        some cases, this property will not be sufficient to
        denote the complete status of the Device. In those
        cases, the AdditionalAvailability property can be
        used to provide further information. For example,
        the primary Availability of a device might be 'Off
        line' (value=8) or in a low-power state
        (AdditionalAvailability value=14), or the Device
        could be running Diagnostics
        (AdditionalAvailability value=5, 'In Test')."
    ::= { msvmVssComponentEntry 2 }

msvmvcAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Note: The use of this property has been
        deprecated. 
        Deprecated description: The primary availability
        and status of the Device. (Additional status
        information can be specified using the Additional
        Availability array property.) For example, the
        Availability property indicates that the Device is
        running and has full power (value=3), or is in a
        warning (4), test (5), degraded (10) or power save
        state (values 13-15 and 17). The Power Save states
        are defined as follows: Value 13 ('Power Save -
        Unknown') indicates that the Device is known to be
        in a power save mode, but its exact status in this
        mode is unknown; value 14 ('Power Save - Low Power
        Mode') indicates that the Device is in a power save
        state but still functioning, and might exhibit
        degraded performance; value 15 ('Power Save -
        Standby') indicates that the Device is not
        functioning but could be brought to full power
        'quickly'; and value 17 ('Power Save - Warning')
        indicates that the Device is in a warning state,
        but is also in a power save mode."
    ::= { msvmVssComponentEntry 3 }

msvmvcCaption OBJECT-TYPE
    SYNTAX     WtcsDisplayString (SIZE (0..64))
    MAX-ACCESS read-only
    STATUS     current
    DESCRIPTION
        "The Caption property is a short textual
        description (one- line string) of the object."
    ::= { msvmVssComponentEntry 4 }

msvmvcCreationClassName OBJECT-TYPE
    SYNTAX     WtcsDisplayString (SIZE (0..256))
    MAX-ACCESS read-only
    STATUS     current
    DESCRIPTION
        "CreationClassName indicates the name of the class
        or the subclass used in the creation of an
        instance. When used with the other key properties
        of this class, this property allows all instances
        of this class and its subclasses to be uniquely
        identified."
    ::= { msvmVssComponentEntry 5 }

msvmvcDescription OBJECT-TYPE
    SYNTAX     WtcsDisplayString
    MAX-ACCESS read-only
    STATUS     current
    DESCRIPTION
        "The Description property provides a textual
        description of the object."
    ::= { msvmVssComponentEntry 6 }

msvmvcDeviceID OBJECT-TYPE
    SYNTAX     WtcsDisplayString (SIZE (0..64))
    MAX-ACCESS read-only
    STATUS     current
    DESCRIPTION
        "An address or other identifying information used
        to uniquely name the LogicalDevice."
    ::= { msvmVssComponentEntry 7 }

msvmvcElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmVssComponentEntry 8 }

msvmvcEnabledDefault OBJECT-TYPE
    SYNTAX     INTEGER {
        enabled(2),
        disabled(3),
        notApplicable(5),
        enabledbutOffline(6),
        noDefault(7)
    }
    MAX-ACCESS read-only
    STATUS     current
    DESCRIPTION
        "An enumerated value indicating an administrator's
        default or startup configuration for the Enabled
        State of an element. By default, the element is
        'Enabled' (value=2)."
    ::= { msvmVssComponentEntry 9 }

msvmvcEnabledState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "EnabledState is an integer enumeration that
        indicates the enabled and disabled states of an
        element. It can also indicate the transitions
        between these requested states. For example,
        shutting down (value=4) and starting (value=10) are
        transient states between enabled and disabled. The
        following text briefly summarizes the various
        enabled and disabled states: 
        Enabled (2) indicates that the element is or could
        be executing commands, will process any queued
        commands, and queues new requests. 
        Disabled (3) indicates that the element will not
        execute commands and will drop any new requests. 
        Shutting Down (4) indicates that the element is in
        the process of going to a Disabled state. 
        Not Applicable (5) indicates the element does not
        support being enabled or disabled. 
        Enabled but Offline (6) indicates that the element
        might be completing commands, and will drop any new
        requests. 
        Test (7) indicates that the element is in a test
        state. 
        Deferred (8) indicates that the element might be
        completing commands, but will queue any new
        requests. 
        Quiesce (9) indicates that the element is enabled
        but in a restricted mode. The behavior of the
        element is similar to the Enabled state, but it
        processes only a restricted set of commands. All
        other requests are queued. 
        Starting (10) indicates that the element is in the
        process of going to an Enabled state. New requests
        are queued."
    ::= { msvmVssComponentEntry 10 }

msvmvcErrorCleared OBJECT-TYPE
    SYNTAX     TruthValue
    MAX-ACCESS read-only
    STATUS     current
    DESCRIPTION
        "Note: The use of this method is deprecated. 
        Deprecated description: ErrorCleared is a Boolean
        property that indicates that the error reported in
        LastErrorCode is now cleared."
    ::= { msvmVssComponentEntry 11 }

msvmvcErrorDescription OBJECT-TYPE
    SYNTAX     WtcsDisplayString
    MAX-ACCESS read-only
    STATUS     current
    DESCRIPTION
        "Note: The use of this method is deprecated. 
        Deprecated description: ErrorDescription is a
        free-form string that supplies more information
        about the error recorded in LastErrorCode and
        information on any corrective actions that can be
        taken."
    ::= { msvmVssComponentEntry 12 }

msvmvcHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmVssComponentEntry 13 }

msvmvcIdentifyingDescriptions OBJECT-TYPE
    SYNTAX     WtcsDisplayString
    MAX-ACCESS read-only
    STATUS     current
    DESCRIPTION
        "An array of free-form strings providing
        explanations and details behind the entries in the
        OtherIdentifyingInfo array. Note that each entry of
        this array is related to the entry in
        OtherIdentifyingInfo that is located at the same
        index."
    ::= { msvmVssComponentEntry 14 }

msvmvcInstallDate OBJECT-TYPE
    SYNTAX     DateAndTime
    MAX-ACCESS read-only
    STATUS     current
    DESCRIPTION
        "A datetime value that indicates when the object
        was installed. Lack of a value does not indicate
        that the object is not installed."
    ::= { msvmVssComponentEntry 15 }

msvmvcLastErrorCode OBJECT-TYPE
    SYNTAX     Gauge32
    MAX-ACCESS read-only
    STATUS     current
    DESCRIPTION
        "Note: The use of this method is deprecated. 
        Deprecated description: LastErrorCode captures the
        last error code reported by the LogicalDevice."
    ::= { msvmVssComponentEntry 16 }

msvmvcLocationIndicator OBJECT-TYPE
    SYNTAX     INTEGER {
        unknown(0),
        on(2),
        off(3),
        notSupported(4)
    }
    MAX-ACCESS read-only
    STATUS     current
    DESCRIPTION
        "An integer that reflects the state of an indicator
        (e.g., LED) that is part of a device. Reading the
        value gives the current state. Writing the value
        with 'On'/'Off' turns the indicator on/off, other
        values may not be written."
    ::= { msvmVssComponentEntry 17 }

msvmvcMaxQuiesceTime OBJECT-TYPE
    SYNTAX     Gauge32
    UNITS "MilliSeconds"
    MAX-ACCESS read-only
    STATUS     current
    DESCRIPTION
        "Note: The use of this property has been
        deprecated. When evaluating the use of Quiesce, it
        was determined that this single property is not
        adequate for describing when a device will
        automatically exit a quiescent state. In fact, the
        most likely scenario for a device to exit a
        quiescent state was determined to be based on the
        number of outstanding requests queued rather than
        on a maximum time. This decision will be
        re-evaluated and repositioned later. 
        Deprecated description: Maximum time, in
        milliseconds, that a Device can run in a 'Quiesced'
        state. The state is defined in its Availability and
        AdditionalAvailability properties, where 'Quiesced'
        is conveyed by the value 21. What occurs at the end
        of the time limit is device-specific. The Device
        can unquiesce, can be offline, or can take other
        actions. A value of 0 indicates that a Device can
        remain quiesced indefinitely."
    ::= { msvmVssComponentEntry 18 }

msvmvcName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmVssComponentEntry 19 }

msvmvcOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmVssComponentEntry 20 }

msvmvcOtherEnabledState OBJECT-TYPE
    SYNTAX     WtcsDisplayString
    MAX-ACCESS read-only
    STATUS     current
    DESCRIPTION
        "A string that describes the enabled or disabled
        state of the element when the EnabledState property
        is set to 1 ('Other'). This property must be set to
        null when EnabledState is any value other than 1."
    ::= { msvmVssComponentEntry 21 }

msvmvcOtherIdentifyingInfo OBJECT-TYPE
    SYNTAX     WtcsDisplayString (SIZE (0..256))
    MAX-ACCESS read-only
    STATUS     current
    DESCRIPTION
        "OtherIdentifyingInfo captures data, in addition to
        DeviceID information, that could be used to
        identify a LogicalDevice. For example, you could
        use this property to hold the operating system's
        user-friendly name for the Device."
    ::= { msvmVssComponentEntry 22 }

msvmvcPowerManagementCapability OBJECT-TYPE
    SYNTAX     INTEGER {
        unknown(0),
        notSupported(1),
        disabled(2),
        enabled(3),
        powerSavingModesEnteredAutomatic(4),
        powerStateSettable(5),
        powerCyclingSupported(6),
        timedPowerOnSupported(7)
    }
    MAX-ACCESS read-only
    STATUS     current
    DESCRIPTION
        "Note: The use of this property has been
        deprecated. Instead, use the PowerCapabilites
        property in an associated
        PowerManagementCapabilities class. Deprecated
        description: An enumerated array describing the
        power management capabilities of the Device."
    ::= { msvmVssComponentEntry 23 }

msvmvcPowerManagementSupported OBJECT-TYPE
    SYNTAX     TruthValue
    MAX-ACCESS read-only
    STATUS     current
    DESCRIPTION
        "Note: The use of this property has been
        deprecated. Instead, the existence of an associated
        PowerManagementCapabilities class (associated using
        the ElementCapabilities relationship) indicates
        that power management is supported. Deprecated
        description: Boolean that indicates that the Device
        can use power management."
    ::= { msvmVssComponentEntry 24 }

msvmvcPowerOnHours OBJECT-TYPE
    SYNTAX     Gauge32
    UNITS "Hours"
    MAX-ACCESS read-only
    STATUS     current
    DESCRIPTION
        "Note: The use of this method is deprecated. 
        Deprecated description: The number of consecutive
        hours that this Device has been powered on since
        its last power cycle."
    ::= { msvmVssComponentEntry 25 }

msvmvcRequestedState OBJECT-TYPE
    SYNTAX     INTEGER {
        enabled(2),
        disabled(3),
        shutDown(4),
        noChange(5),
        offline(6),
        test(7),
        deferred(8),
        quiesce(9),
        reboot(10),
        reset(11),
        notApplicable(12)
    }
    MAX-ACCESS read-only
    STATUS     current
    DESCRIPTION
        "RequestedState is an integer enumeration that
        indicates the last requested or desired state for
        the element. The actual state of the element is
        represented by EnabledState. This property is
        provided to compare the last requested and current
        enabled or disabled states. Note that when
        EnabledState is set to 5 ('Not Applicable'), then
        this property has no meaning. By default, the
        RequestedState of the element is 5 ('No Change').
        Refer to the EnabledState property description for
        explanations of the values in the RequestedState
        enumeration. 
        
        It should be noted that there are two new values in
        RequestedState that build on the statuses of
        EnabledState. These are 'Reboot' (10) and 'Reset'
        (11). Reboot refers to doing a 'Shut Down' and then
        moving to an 'Enabled' state. Reset indicates that
        the element is first 'Disabled' and then 'Enabled'.
        The distinction between requesting 'Shut Down' and
        'Disabled' should also be noted. Shut Down requests
        an orderly transition to the Disabled state, and
        might involve removing power, to completely erase
        any existing state. The Disabled state requests an
        immediate disabling of the element, such that it
        will not execute or accept any commands or
        processing requests. 
        
        This property is set as the result of a method
        invocation (such as Start or StopService on
        CIM_Service), or can be overridden and defined as
        WRITEable in a subclass. The method approach is
        considered superior to a WRITEable property,
        because it allows an explicit invocation of the
        operation and the return of a result code. 
        
        A particular instance of EnabledLogicalElement
        might not support RequestedStateChange. If this
        occurs, the value 12 ('Not Applicable') is used."
    ::= { msvmVssComponentEntry 26 }

msvmvcStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmVssComponentEntry 27 }

msvmvcStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmVssComponentEntry 28 }

msvmvcStatusInfo OBJECT-TYPE
    SYNTAX     INTEGER {
        other(1),
        unknown(2),
        enabled(3),
        disabled(4),
        notApplicable(5)
    }
    MAX-ACCESS read-only
    STATUS     current
    DESCRIPTION
        "Note: The use of this method is deprecated in lieu
        of a more clearly named property (EnabledState)
        that is inherited from ManagedSystemElement and
        that has additional enumerated values. 
        Deprecated description: The StatusInfo property
        indicates whether the Logical Device is in an
        enabled state (value=3), disabled state (value=4),
        some other state (value=1), or an unknown state
        (value=2). If this property does not apply to the
        LogicalDevice, the value 5 ('Not Applicable')
        should be used. If a Device is
        ('Enabled')(value=3), it has been powered up and is
        configured and operational. The Device might or
        might not be functionally active, depending on
        whether its Availability (or
        AdditionalAvailability) indicates that it is
        ('Running/Full Power')(value=3) or ('Off line')
        (value=8). In an enabled but offline mode, a Device
        might be performing out-of-band requests, such as
        running Diagnostics. If StatusInfo is ('Disabled')
        (value=4), a Device can only be 'enabled' or
        powered off. In a personal computer environment,
        ('Disabled') means that the driver of the device is
        not available in the stack. In other environments,
        a Device can be disabled by removing its
        configuration file. A disabled device is physically
        present in a System and consuming resources, but it
        cannot be communicated with until a driver is
        loaded, a configuration file is loaded, or some
        other 'enabling' activity has occurred."
    ::= { msvmVssComponentEntry 29 }

msvmvcSystemCreationClassName OBJECT-TYPE
    SYNTAX     WtcsDisplayString (SIZE (0..256))
    MAX-ACCESS read-only
    STATUS     current
    DESCRIPTION
        "The CreationClassName of the scoping system."
    ::= { msvmVssComponentEntry 30 }

msvmvcSystemName OBJECT-TYPE
    SYNTAX     WtcsDisplayString (SIZE (0..256))
    MAX-ACCESS read-only
    STATUS     current
    DESCRIPTION
        "The System Name of the scoping system."
    ::= { msvmVssComponentEntry 31 }

msvmvcTimeOfLastStateChange OBJECT-TYPE
    SYNTAX     DateAndTime
    MAX-ACCESS read-only
    STATUS     current
    DESCRIPTION
        "The date or time when the EnabledState of the
        element last changed. If the state of the element
        has not changed and this property is populated,
        then it must be set to a 0 interval value. If a
        state change was requested, but rejected or not yet
        processed, the property must not be updated."
    ::= { msvmVssComponentEntry 32 }

msvmvcTotalPowerOnHours OBJECT-TYPE
    SYNTAX     Gauge32
    UNITS "Hours"
    MAX-ACCESS read-only
    STATUS     current
    DESCRIPTION
        "Note: The use of this method is deprecated. 
        Deprecated description: The total number of hours
        that this Device has been powered on."
    ::= { msvmVssComponentEntry 33 }

msvmVssComponentSettingDataTable OBJECT-TYPE
    SYNTAX     SEQUENCE OF MsvmVssComponentSettingData
    MAX-ACCESS not-accessible
    STATUS     current
    DESCRIPTION
        "Represents the configured state of the Volume
        Shadow Copy Service (VSS) component."
    ::= { msvmIntegrationComponents 11 }

msvmVssComponentSettingDataEntry OBJECT-TYPE
    SYNTAX     MsvmVssComponentSettingData
    MAX-ACCESS not-accessible
    STATUS     current
    DESCRIPTION
        "None"
    INDEX      { msvmvcsdIndex }
    ::= { msvmVssComponentSettingDataTable 1 }

MsvmVssComponentSettingData ::= SEQUENCE {
    msvmvcsdIndex Integer32,
    msvmvcsdAddress WtcsDisplayString,
    msvmvcsdAllocationUnits WtcsDisplayString,
    msvmvcsdAutomaticAllocation TruthValue,
    msvmvcsdAutomaticDeallocation TruthValue,
    msvmvcsdCaption WtcsDisplayString,
    msvmvcsdConnection WtcsDisplayString,
    msvmvcsdConsumerVisibility INTEGER,
    msvmvcsdDescription WtcsDisplayString,
    msvmvcsdElementName WtcsDisplayString,
    msvmvcsdEnabledState Integer32,
    msvmvcsdHostResource WtcsDisplayString,
    msvmvcsdInstanceID WtcsDisplayString,
    msvmvcsdLimit Gauge32,
    msvmvcsdMappingBehavior INTEGER,
    msvmvcsdOtherResourceType WtcsDisplayString,
    msvmvcsdParent WtcsDisplayString,
    msvmvcsdPoolID WtcsDisplayString,
    msvmvcsdReservation Gauge32,
    msvmvcsdResourceSubType WtcsDisplayString,
    msvmvcsdResourceType INTEGER,
    msvmvcsdVirtualQuantity Gauge32,
    msvmvcsdWeight Gauge32
}

msvmvcsdIndex OBJECT-TYPE
    SYNTAX     Integer32 (1..2147483647)
    MAX-ACCESS read-only
    STATUS     current
    DESCRIPTION
        "The value of this object uniquely identifies the
        instance entry for this class."
    ::= { msvmVssComponentSettingDataEntry 1 }

msvmvcsdAddress OBJECT-TYPE
    SYNTAX     WtcsDisplayString
    MAX-ACCESS read-only
    STATUS     current
    DESCRIPTION
        "The address of the resource.For example, the MAC
        address of a Ethernet port."
    ::= { msvmVssComponentSettingDataEntry 2 }

msvmvcsdAllocationUnits OBJECT-TYPE
    SYNTAX     WtcsDisplayString
    MAX-ACCESS read-only
    STATUS     current
    DESCRIPTION
        "This property specifies the units of allocation
        used by the Reservation and Limit properties.  For
        example, when ResourceType=Processor,
        AllocationUnits may be set to MHZ. When
        ResourceType=Memory, AllocationUnits may be set to
        MB"
    ::= { msvmVssComponentSettingDataEntry 3 }

msvmvcsdAutomaticAllocation OBJECT-TYPE
    SYNTAX     TruthValue
    MAX-ACCESS read-only
    STATUS     current
    DESCRIPTION
        "This property specifies if the resource will be
        automatically allocated.  For example when set to
        true, when the consuming virtual computer system is
        powered on, this resource would be allocated.  A
        value of false indicates the resource must be
        explicitly allocated.  For example, the setting may
        represent removable media (cdrom, floppy, etc.)
        where at power on time, the media isnot present. 
        An explicit operation is required to allocate the
        resource."
    ::= { msvmVssComponentSettingDataEntry 4 }

msvmvcsdAutomaticDeallocation OBJECT-TYPE
    SYNTAX     TruthValue
    MAX-ACCESS read-only
    STATUS     current
    DESCRIPTION
        "This property specifies if the resource will be
        automatically de-allocated.  For example, when set
        to true, when the consuming virtual computer system
        is powered off, this resource would be
        de-allocated.  When set to false, the resource will
        remain allocated and must be explicitly
        de-allocated."
    ::= { msvmVssComponentSettingDataEntry 5 }

msvmvcsdCaption OBJECT-TYPE
    SYNTAX     WtcsDisplayString (SIZE (0..64))
    MAX-ACCESS read-only
    STATUS     current
    DESCRIPTION
        "The Caption property is a short textual
        description (one- line string) of the object."
    ::= { msvmVssComponentSettingDataEntry 6 }

msvmvcsdConnection OBJECT-TYPE
    SYNTAX     WtcsDisplayString
    MAX-ACCESS read-only
    STATUS     current
    DESCRIPTION
        "The thing to which this resource is connected. 
        For example, a named network or switch port."
    ::= { msvmVssComponentSettingDataEntry 7 }

msvmvcsdConsumerVisibility OBJECT-TYPE
    SYNTAX     INTEGER {
        unknown(0),
        passedThrough(2),
        virtualized(3),
        notrepresented(4)
    }
    MAX-ACCESS read-only
    STATUS     current
    DESCRIPTION
        "Describes the consumers visibility to the
        allocated  resource.
        A value of 'Passed-Through' indicates the
        underlying or host resource is utilized and passed
        through to the consumer, possibly using
        partitioning. At least one item shall be present in
        the DeviceID property.  
        A value of 'Virtualized' indicates the resource is
        virtualized and may not map directly to an
        underlying/host resource. Some implementations may
        support specific assignment for virtualized
        resources, in which case the host resource(s) are
        exposed using the DeviceID property. 
        A value of 'Not represented' indicates a
        representation of the resource does not exist
        within the context of the resource consumer."
    ::= { msvmVssComponentSettingDataEntry 8 }

msvmvcsdDescription OBJECT-TYPE
    SYNTAX     WtcsDisplayString
    MAX-ACCESS read-only
    STATUS     current
    DESCRIPTION
        "The Description property provides a textual
        description of the object."
    ::= { msvmVssComponentSettingDataEntry 9 }

msvmvcsdElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmVssComponentSettingDataEntry 10 }

msvmvcsdEnabledState OBJECT-TYPE
    SYNTAX     Integer32
    MAX-ACCESS read-only
    STATUS     current
    DESCRIPTION
        "An integer enumeration that indicates the enabled
        and disabled states of an element. This property is
        inherited from CIM_EnabledLogicalElement and is
        either set to 2 ('Enabled') or 3 ('Disabled')."
    ::= { msvmVssComponentSettingDataEntry 11 }

msvmvcsdHostResource OBJECT-TYPE
    SYNTAX     WtcsDisplayString
    MAX-ACCESS read-only
    STATUS     current
    DESCRIPTION
        "This property exposes specific assignment to host
        or underlying resources.        The embedded
        instances shall contain only key properties and be
        treated as Object Paths. If the virtual resource
        may be scheduled on a number of underlying
        resources, this property shall be left NULL. In
        that case, the DeviceAllocatedFromPool or
        ResourceAllocationFromPool associations may be used
        to determine the pool of host resources this
        virtual resource may be scheduled on. If specific
        assignment is utilized, all underlying resources
        used by this virtual resource shall be listed in
        this array.  Typically the array will contain one
        item, however for aggregate allocations, such as
        multiple processors, multiple host resources may be
        specified."
    ::= { msvmVssComponentSettingDataEntry 12 }

msvmvcsdInstanceID OBJECT-TYPE
    SYNTAX     WtcsDisplayString
    MAX-ACCESS read-only
    STATUS     current
    DESCRIPTION
        "Within the scope of the instantiating Namespace,
        InstanceID opaquely and uniquely identifies an
        instance of this class. To ensure uniqueness within
        the NameSpace, the value of InstanceID should be
        constructed using the following 'preferred'
        algorithm: 
        <OrgID>:<LocalID> 
        Where <OrgID> and <LocalID> are separated by a
        colon (:), and where <OrgID> must include a
        copyrighted, trademarked, or otherwise unique name
        that is owned by the business entity that is
        creating or defining the InstanceID or that is a
        registered ID assigned to the business entity by a
        recognized global authority. (This requirement is
        similar to the <Schema Name>_<Class Name> structure
        of Schema class names.) In addition, to ensure
        uniqueness, <OrgID> must not contain a colon (:).
        When using this algorithm, the first colon to
        appear in InstanceID must appear between <OrgID>
        and <LocalID>. 
        <LocalID> is chosen by the business entity and
        should not be reused to identify different
        underlying (real-world) elements. If the above
        'preferred' algorithm is not used, the defining
        entity must assure that the resulting InstanceID is
        not reused across any InstanceIDs produced by this
        or other providers for the NameSpace of this
        instance. 
        For DMTF-defined instances, the 'preferred'
        algorithm must be used with the <OrgID> set to
        CIM."
    ::= { msvmVssComponentSettingDataEntry 13 }

msvmvcsdLimit OBJECT-TYPE
    SYNTAX     Gauge32
    MAX-ACCESS read-only
    STATUS     current
    DESCRIPTION
        "This property specifies the upper bound, or
        maximum amount of resource that will be granted for
        this allocation. For example, a system which
        supports memory paging may support setting the
        Limit of a Memory allocation below that of the
        VirtualQuantity, thus forcing paging to occur for
        this allocation."
    ::= { msvmVssComponentSettingDataEntry 14 }

msvmvcsdMappingBehavior OBJECT-TYPE
    SYNTAX     INTEGER {
        unknown(0),
        notSupported(1),
        dedicated(2),
        softAffinity(3),
        hardAffinity(4)
    }
    MAX-ACCESS read-only
    STATUS     current
    DESCRIPTION
        "Specifies how this resource maps to underlying
        resourcesIf the HostResource array contains any
        entries, this property reflects how the resource
        maps to those specific resources."
    ::= { msvmVssComponentSettingDataEntry 15 }

msvmvcsdOtherResourceType OBJECT-TYPE
    SYNTAX     WtcsDisplayString
    MAX-ACCESS read-only
    STATUS     current
    DESCRIPTION
        "A string that describes the resource type when a
        well defined value is not available and
        ResourceType has the value 'Other'."
    ::= { msvmVssComponentSettingDataEntry 16 }

msvmvcsdParent OBJECT-TYPE
    SYNTAX     WtcsDisplayString
    MAX-ACCESS read-only
    STATUS     current
    DESCRIPTION
        "The Parent of the resource.  For example, a
        controller for the current allocation"
    ::= { msvmVssComponentSettingDataEntry 17 }

msvmvcsdPoolID OBJECT-TYPE
    SYNTAX     WtcsDisplayString
    MAX-ACCESS read-only
    STATUS     current
    DESCRIPTION
        "This property specifies which ResourcePool the
        resource is currently allocated from, or which
        ResourcePool the resource will be allocated from
        when the allocation occurs."
    ::= { msvmVssComponentSettingDataEntry 18 }

msvmvcsdReservation OBJECT-TYPE
    SYNTAX     Gauge32
    MAX-ACCESS read-only
    STATUS     current
    DESCRIPTION
        "This property specifies the amount of resource
        guaranteed to be available for this allocation.  On
        system which support over-commitment of resources,
        this value is typically used for admission control
        to prevent an an allocation from being accepted
        thus preventing starvation."
    ::= { msvmVssComponentSettingDataEntry 19 }

msvmvcsdResourceSubType OBJECT-TYPE
    SYNTAX     WtcsDisplayString
    MAX-ACCESS read-only
    STATUS     current
    DESCRIPTION
        "A string describing an implementation specific
        sub-type for this resource.  For example, this may
        be used to distinguish different models of the same
        resource type."
    ::= { msvmVssComponentSettingDataEntry 20 }

msvmvcsdResourceType OBJECT-TYPE
    SYNTAX     INTEGER {
        other(1),
        computerSystem(2),
        processor(3),
        memory(4),
        ideController(5),
        parallelSCSIHBA(6),
        fcHBA(7),
        iSCSIHBA(8),
        ibHCA(9),
        ethernetAdapter(10),
        iOSlot(11),
        iODevice(12),
        floppyDrive(13),
        cdDrive(14),
        dvddrive(15),
        serialport(16),
        parallelport(17),
        usbController(18),
        graphicscontroller(19),
        storageExtent(20),
        disk(21),
        tape(22),
        otherstoragedevice(23),
        firewireController(24),
        partitionableUnit(25),
        basePartitionableUnit(26),
        powerSupply(27),
        coolingDevice(28),
        dmtfreserved(29)
    }
    MAX-ACCESS read-only
    STATUS     current
    DESCRIPTION
        "The type of resource this allocation setting
        represents."
    ::= { msvmVssComponentSettingDataEntry 21 }

msvmvcsdVirtualQuantity OBJECT-TYPE
    SYNTAX     Gauge32
    MAX-ACCESS read-only
    STATUS     current
    DESCRIPTION
        "This property specifies the quantity of resources
        presented to the consumer.  For example, when
        ResourceType=Processor,  this property would
        reflect the number of discrete Processors presented
        to the virtual computer system.  When
        ResourceType=Memory, this property could reflect
        the number of MB reported to the virtual computer
        system."
    ::= { msvmVssComponentSettingDataEntry 22 }

msvmvcsdWeight OBJECT-TYPE
    SYNTAX     Gauge32
    MAX-ACCESS read-only
    STATUS     current
    DESCRIPTION
        "This property specifies a relative priority for
        this allocation in relation to other allocations
        from the same ResourcePool.  This property has no
        unit of measure, and is only relevant when compared
        to other allocations vying for the same host
        resources."
    ::= { msvmVssComponentSettingDataEntry 23 }

msvmMemory OBJECT-IDENTITY
    STATUS     current
    DESCRIPTION
        "The memory classes model the memory for a virtual
        system."
    ::= { informantHyperV 4 }

msvmMemoryTable OBJECT-TYPE
    SYNTAX     SEQUENCE OF MsvmMemory
    MAX-ACCESS not-accessible
    STATUS     current
    DESCRIPTION
        "Represents the memory currently allocated to a
        virtual system."
    ::= { msvmMemory 1 }

msvmMemoryEntry OBJECT-TYPE
    SYNTAX     MsvmMemory
    MAX-ACCESS not-accessible
    STATUS     current
    DESCRIPTION
        "None"
    INDEX      { msvmmemIndex }
    ::= { msvmMemoryTable 1 }

MsvmMemory ::= SEQUENCE {
    msvmmemIndex Integer32,
    msvmmemAccess INTEGER,
    msvmmemAdditionalAvailability INTEGER,
    msvmmemAdditionalErrorData Integer32,
    msvmmemAvailability INTEGER,
    msvmmemBlockSize Gauge32,
    msvmmemCaption WtcsDisplayString,
    msvmmemConsumableBlocks Gauge32,
    msvmmemCorrectableError TruthValue,
    msvmmemCreationClassName WtcsDisplayString,
    msvmmemDataOrganization INTEGER,
    msvmmemDataRedundancy Integer32,
    msvmmemDeltaReservation Integer32,
    msvmmemDescription WtcsDisplayString,
    msvmmemDeviceID WtcsDisplayString,
    msvmmemElementName WtcsDisplayString,
    msvmmemEnabledDefault INTEGER,
    msvmmemEnabledState INTEGER,
    msvmmemEndingAddress Gauge32,
    msvmmemErrorAccess INTEGER,
    msvmmemErrorAddress Gauge32,
    msvmmemErrorCleared TruthValue,
    msvmmemErrorData Integer32,
    msvmmemErrorDataOrder INTEGER,
    msvmmemErrorDescription WtcsDisplayString,
    msvmmemErrorInfo INTEGER,
    msvmmemErrorMethodology WtcsDisplayString,
    msvmmemErrorResolution Gauge32,
    msvmmemErrorTime DateAndTime,
    msvmmemErrorTransferSize Gauge32,
    msvmmemExtentStatus INTEGER,
    msvmmemHealthState INTEGER,
    msvmmemIdentifyingDescriptions WtcsDisplayString,
    msvmmemInstallDate DateAndTime,
    msvmmemBasedOnUnderlyRedundancy TruthValue,
    msvmmemLastErrorCode Gauge32,
    msvmmemLocationIndicator INTEGER,
    msvmmemMaxQuiesceTime Gauge32,
    msvmmemName WtcsDisplayString,
    msvmmemNameFormat INTEGER,
    msvmmemNameNamespace INTEGER,
    msvmmemNoSinglePointOfFailure TruthValue,
    msvmmemNumberOfBlocks Gauge32,
    msvmmemOperationalStatus INTEGER,
    msvmmemOtherEnabledState INTEGER,
    msvmmemOtherErrorDescription INTEGER,
    msvmmemOtherIdentifyingInfo WtcsDisplayString,
    msvmmemOtherNameFormat INTEGER,
    msvmmemOtherNameNamespace INTEGER,
    msvmmemPackageRedundancy Integer32,
    msvmmemPowerManagementCapability INTEGER,
    msvmmemPowerManagementSupported TruthValue,
    msvmmemPowerOnHours Gauge32,
    msvmmemPrimordial TruthValue,
    msvmmemPurpose WtcsDisplayString,
    msvmmemRequestedState INTEGER,
    msvmmemSequentialAccess TruthValue,
    msvmmemStartingAddress Gauge32,
    msvmmemStatus WtcsDisplayString,
    msvmmemStatusDescriptions INTEGER,
    msvmmemStatusInfo INTEGER,
    msvmmemSystemCreationClassName WtcsDisplayString,
    msvmmemSystemLevelAddress TruthValue,
    msvmmemSystemName WtcsDisplayString,
    msvmmemTimeOfLastStateChange DateAndTime,
    msvmmemTotalPowerOnHours Gauge32,
    msvmmemvolatile TruthValue
}

msvmmemIndex OBJECT-TYPE
    SYNTAX     Integer32 (1..2147483647)
    MAX-ACCESS read-only
    STATUS     current
    DESCRIPTION
        "The value of this object uniquely identifies the
        instance entry for this class."
    ::= { msvmMemoryEntry 1 }

msvmmemAccess OBJECT-TYPE
    SYNTAX     INTEGER {
        unknown(0),
        readable(1),
        writeable(2),
        readWriteSupported(3),
        writeOnce(4)
    }
    MAX-ACCESS read-only
    STATUS     current
    DESCRIPTION
        "Access describes whether the media is readable
        (value=1), writeable (value=2), or both (value=3).
        'Unknown' (0) and 'Write Once' (4) can also be
        defined."
    ::= { msvmMemoryEntry 2 }

msvmmemAdditionalAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Note: The use of this property has been
        deprecated. 
        Deprecated description: The primary availability
        and status of the Device. (Additional status
        information can be specified using the Additional
        Availability array property.) For example, the
        Availability property indicates that the Device is
        running and has full power (value=3), or is in a
        warning (4), test (5), degraded (10) or power save
        state (values 13-15 and 17). The Power Save states
        are defined as follows: Value 13 ('Power Save -
        Unknown') indicates that the Device is known to be
        in a power save mode, but its exact status in this
        mode is unknown; value 14 ('Power Save - Low Power
        Mode') indicates that the Device is in a power save
        state but still functioning, and might exhibit
        degraded performance; value 15 ('Power Save -
        Standby') indicates that the Device is not
        functioning but could be brought to full power
        'quickly'; and value 17 ('Power Save - Warning')
        indicates that the Device is in a warning state,
        but is also in a power save mode."
    ::= { msvmMemoryEntry 3 }

msvmmemAdditionalErrorData OBJECT-TYPE
    SYNTAX     Integer32
    MAX-ACCESS read-only
    STATUS     current
    DESCRIPTION
        "An array of octets holding additional error
        information. An example is ECC Syndrome or the
        return of the check bits if a CRC-based
        ErrorMethodology is used. In the latter case, if a
        single bit error is recognized and the CRC
        algorithm is known, it is possible to determine the
        exact bit that failed. This type of data (ECC
        Syndrome, Check Bit or Parity Bit data, or other
        vendor supplied information) is included in this
        field. If the ErrorInfo property is equal to 3,
        'OK', then AdditionalErrorData has no meaning."
    ::= { msvmMemoryEntry 4 }

msvmmemAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Additional availability and status of the Device
        in addition to that specified in the Availability
        property. The Availability property denotes the
        primary status and availability of the Device. In
        some cases, this property will not be sufficient to
        denote the complete status of the Device. In those
        cases, the AdditionalAvailability property can be
        used to provide further information. For example,
        the primary Availability of a device might be 'Off
        line' (value=8) or in a low-power state
        (AdditionalAvailability value=14), or the Device
        could be running Diagnostics
        (AdditionalAvailability value=5, 'In Test')."
    ::= { msvmMemoryEntry 5 }

msvmmemBlockSize OBJECT-TYPE
    SYNTAX     Gauge32
    UNITS "Bytes"
    MAX-ACCESS read-only
    STATUS     current
    DESCRIPTION
        "Size in bytes of the blocks which form this
        StorageExtent. If variable block size, then the
        maximum block size in bytes should be specified. If
        the block size is unknown or if a block concept is
        not valid (for example, for AggregateExtents,
        Memory or LogicalDisks), enter a 1."
    ::= { msvmMemoryEntry 6 }

msvmmemCaption OBJECT-TYPE
    SYNTAX     WtcsDisplayString (SIZE (0..64))
    MAX-ACCESS read-only
    STATUS     current
    DESCRIPTION
        "The Caption property is a short textual
        description (one- line string) of the object."
    ::= { msvmMemoryEntry 7 }

msvmmemConsumableBlocks OBJECT-TYPE
    SYNTAX     Gauge32
    MAX-ACCESS read-only
    STATUS     current
    DESCRIPTION
        "The maximum number of blocks, of size BlockSize,
        which are available for consumption when layering
        StorageExtents using the BasedOn association. This
        property only has meaning when this StorageExtent
        is an Antecedent reference in a BasedOn
        relationship. For example, a StorageExtent could be
        composed of 120 blocks. However, the Extent itself
        may use 20 blocks for redundancy data. If another
        StorageExtent is BasedOn this Extent, only 100
        blocks would be available to it. This information
        ('100 blocks is available for consumption') is
        indicated in the ConsumableBlocks property."
    ::= { msvmMemoryEntry 8 }

msvmmemCorrectableError OBJECT-TYPE
    SYNTAX     TruthValue
    MAX-ACCESS read-only
    STATUS     current
    DESCRIPTION
        "Boolean indicating that the most recent error was
        correctable. If the ErrorInfo property is equal to
        3, 'OK', then this property has no meaning."
    ::= { msvmMemoryEntry 9 }

msvmmemCreationClassName OBJECT-TYPE
    SYNTAX     WtcsDisplayString (SIZE (0..256))
    MAX-ACCESS read-only
    STATUS     current
    DESCRIPTION
        "CreationClassName indicates the name of the class
        or the subclass used in the creation of an
        instance. When used with the other key properties
        of this class, this property allows all instances
        of this class and its subclasses to be uniquely
        identified."
    ::= { msvmMemoryEntry 10 }

msvmmemDataOrganization OBJECT-TYPE
    SYNTAX     INTEGER {
        other(0),
        unknown(1),
        fixedBlock(2),
        variableBlock(3),
        countKeyData(4)
    }
    MAX-ACCESS read-only
    STATUS     current
    DESCRIPTION
        "Type of data organization used."
    ::= { msvmMemoryEntry 11 }

msvmmemDataRedundancy OBJECT-TYPE
    SYNTAX     Integer32
    MAX-ACCESS read-only
    STATUS     current
    DESCRIPTION
        "Number of complete copies of data currently
        maintained."
    ::= { msvmMemoryEntry 12 }

msvmmemDeltaReservation OBJECT-TYPE
    SYNTAX     Integer32
    UNITS "Percentage"
    MAX-ACCESS read-only
    STATUS     current
    DESCRIPTION
        "Current value for Delta reservation. This is a
        percentage that specifies the amount of space that
        should be reserved in a replica for caching
        changes."
    ::= { msvmMemoryEntry 13 }

msvmmemDescription OBJECT-TYPE
    SYNTAX     WtcsDisplayString
    MAX-ACCESS read-only
    STATUS     current
    DESCRIPTION
        "The Description property provides a textual
        description of the object."
    ::= { msvmMemoryEntry 14 }

msvmmemDeviceID OBJECT-TYPE
    SYNTAX     WtcsDisplayString (SIZE (0..64))
    MAX-ACCESS read-only
    STATUS     current
    DESCRIPTION
        "An address or other identifying information used
        to uniquely name the LogicalDevice."
    ::= { msvmMemoryEntry 15 }

msvmmemElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmMemoryEntry 16 }

msvmmemEnabledDefault OBJECT-TYPE
    SYNTAX     INTEGER {
        enabled(2),
        disabled(3),
        notApplicable(5),
        enabledbutOffline(6),
        noDefault(7)
    }
    MAX-ACCESS read-only
    STATUS     current
    DESCRIPTION
        "An enumerated value indicating an administrator's
        default or startup configuration for the Enabled
        State of an element. By default, the element is
        'Enabled' (value=2)."
    ::= { msvmMemoryEntry 17 }

msvmmemEnabledState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "A string that describes the enabled or disabled
        state of the element when the EnabledState property
        is set to 1 ('Other'). This property must be set to
        null when EnabledState is any value other than 1."
    ::= { msvmMemoryEntry 18 }

msvmmemEndingAddress OBJECT-TYPE
    SYNTAX     Gauge32
    UNITS "KiloBytes"
    MAX-ACCESS read-only
    STATUS     current
    DESCRIPTION
        "The ending address, referenced by an application
        or operating system and mapped by a memory
        controller, for this Memory object. The ending
        address is specified in KBytes."
    ::= { msvmMemoryEntry 19 }

msvmmemErrorAccess OBJECT-TYPE
    SYNTAX     INTEGER {
        other(1),
        unknown(2),
        read(3),
        write(4),
        partialWrite(5)
    }
    MAX-ACCESS read-only
    STATUS     current
    DESCRIPTION
        "An integer enumeration indicating the memory
        access operation that caused the last error. The
        type of error is described by the ErrorInfo
        property. If the ErrorInfo property is equal to 3,
        'OK', then this property has no meaning."
    ::= { msvmMemoryEntry 20 }

msvmmemErrorAddress OBJECT-TYPE
    SYNTAX     Gauge32
    MAX-ACCESS read-only
    STATUS     current
    DESCRIPTION
        "Specifies the address of the last memory error.
        The type of error is described by the ErrorInfo
        property. If the ErrorInfo property is equal to 3,
        'OK', then this property has no meaning."
    ::= { msvmMemoryEntry 21 }

msvmmemErrorCleared OBJECT-TYPE
    SYNTAX     TruthValue
    MAX-ACCESS read-only
    STATUS     current
    DESCRIPTION
        "Note: The use of this method is deprecated. 
        Deprecated description: ErrorCleared is a Boolean
        property that indicates that the error reported in
        LastErrorCode is now cleared."
    ::= { msvmMemoryEntry 22 }

msvmmemErrorData OBJECT-TYPE
    SYNTAX     Integer32
    MAX-ACCESS read-only
    STATUS     current
    DESCRIPTION
        "Data captured during the last erroneous mebmory
        access. The data occupies the first n octets of the
        array necessary to hold the number of bits
        specified by the ErrorTransferSize property. If
        ErrorTransferSize is 0, then this property has no
        meaning."
    ::= { msvmMemoryEntry 23 }

msvmmemErrorDataOrder OBJECT-TYPE
    SYNTAX     INTEGER {
        unknown(0),
        leastSignificantByteFirst(1),
        mostSignificantByteFirst(2)
    }
    MAX-ACCESS read-only
    STATUS     current
    DESCRIPTION
        "The ordering for data stored in the ErrorData
        property. 'Least Significant Byte First' (value=1)
        or 'Most Significant Byte First' (2) can be
        specified. If ErrorTransferSize is 0, then this
        property has no meaning."
    ::= { msvmMemoryEntry 24 }

msvmmemErrorDescription OBJECT-TYPE
    SYNTAX     WtcsDisplayString
    MAX-ACCESS read-only
    STATUS     current
    DESCRIPTION
        "Note: The use of this method is deprecated. 
        Deprecated description: ErrorDescription is a
        free-form string that supplies more information
        about the error recorded in LastErrorCode and
        information on any corrective actions that can be
        taken."
    ::= { msvmMemoryEntry 25 }

msvmmemErrorInfo OBJECT-TYPE
    SYNTAX     INTEGER {
        other(1),
        unknown(2),
        ok(3),
        badRead(4),
        parityError(5),
        singleBitError(6),
        doubleBitError(7),
        multiBitError(8),
        nibbleError(9),
        checksumError(10),
        crcError(11)
    }
    MAX-ACCESS read-only
    STATUS     current
    DESCRIPTION
        "Free form string providing more information if the
        Error Type property is set to 1, 'Other'. If not
        set to 1, this string has no meaning."
    ::= { msvmMemoryEntry 26 }

msvmmemErrorMethodology OBJECT-TYPE
    SYNTAX     WtcsDisplayString
    MAX-ACCESS read-only
    STATUS     current
    DESCRIPTION
        "ErrorMethodology is a free-form string describing
        the type of error detection and correction
        supported by this StorageExtent."
    ::= { msvmMemoryEntry 27 }

msvmmemErrorResolution OBJECT-TYPE
    SYNTAX     Gauge32
    UNITS "Bytes"
    MAX-ACCESS read-only
    STATUS     current
    DESCRIPTION
        "Specifies the range, in bytes, to which the last
        error can be resolved. For example, if error
        addresses are resolved to bit 11 (ie, on a typical
        page basis), then errors can be resolved to 4K
        boundaries and this property is set to 4000. If the
        ErrorInfo property is equal to 3, 'OK', then this
        property has no meaning."
    ::= { msvmMemoryEntry 28 }

msvmmemErrorTime OBJECT-TYPE
    SYNTAX     DateAndTime
    MAX-ACCESS read-only
    STATUS     current
    DESCRIPTION
        "The time that the last memory error occurred. The
        type of error is described by the ErrorInfo
        property. If the Error Info property is equal to 3,
        'OK', then this property has no meaning."
    ::= { msvmMemoryEntry 29 }

msvmmemErrorTransferSize OBJECT-TYPE
    SYNTAX     Gauge32
    UNITS "Bits"
    MAX-ACCESS read-only
    STATUS     current
    DESCRIPTION
        "The size of the data transfer in bits that caused
        the last error. 0 indicates no error. If the
        ErrorInfo property is equal to 3, 'OK', then this
        property should be set to 0."
    ::= { msvmMemoryEntry 30 }

msvmmemExtentStatus OBJECT-TYPE
    SYNTAX     INTEGER {
        other(0),
        unknown(1),
        noneNotApplicable(2),
        broken(3),
        dataLost(4),
        dynamicReconfig(5),
        exposed(6),
        fractionallyExposed(7),
        partiallyExposed(8),
        protectionDisabled(9),
        readying(10),
        rebuild(11),
        recalculate(12),
        spareinUse(13),
        verifyInProgress(14),
        inBandAccessGranted(15),
        imported(16),
        exported(17)
    }
    MAX-ACCESS read-only
    STATUS     current
    DESCRIPTION
        "StorageExtents have additional status information
        beyond that captured in the OperationalStatus and
        other properties, inherited from
        ManagedSystemElement. This additional information
        (for example, 'Protection Disabled', value=9) is
        captured in the ExtentStatus property. 
        'In-Band Access Granted' says that access to data
        on an extent is granted to some consumer and is
        only valid when 'Exported' is also set. It is set
        as a side effect of
        PrivilegeManagementService.ChangeAccess or
        equivalent interfaces. 
        'Imported' indicates that the extent is used in the
        current system, but known to be managed by some
        other system. For example, a server imports volumes
        from a disk array. 
        'Exported' indicates the extent is meant to be used
        by some comsumer. A disk array's logical units are
        exported. 
        Intermediate composite extents may be neither
        imported nor exported."
    ::= { msvmMemoryEntry 31 }

msvmmemHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmMemoryEntry 32 }

msvmmemIdentifyingDescriptions OBJECT-TYPE
    SYNTAX     WtcsDisplayString
    MAX-ACCESS read-only
    STATUS     current
    DESCRIPTION
        "OtherIdentifyingInfo captures data, in addition to
        DeviceID information, that could be used to
        identify a LogicalDevice. For example, you could
        use this property to hold the operating system's
        user-friendly name for the Device."
    ::= { msvmMemoryEntry 33 }

msvmmemInstallDate OBJECT-TYPE
    SYNTAX     DateAndTime
    MAX-ACCESS read-only
    STATUS     current
    DESCRIPTION
        "A datetime value that indicates when the object
        was installed. Lack of a value does not indicate
        that the object is not installed."
    ::= { msvmMemoryEntry 34 }

msvmmemBasedOnUnderlyRedundancy OBJECT-TYPE
    SYNTAX     TruthValue
    MAX-ACCESS read-only
    STATUS     current
    DESCRIPTION
        "True indicates that the underlying
        StorageExtent(s) participate in a
        StorageRedundancyGroup."
    ::= { msvmMemoryEntry 35 }

msvmmemLastErrorCode OBJECT-TYPE
    SYNTAX     Gauge32
    MAX-ACCESS read-only
    STATUS     current
    DESCRIPTION
        "Note: The use of this method is deprecated. 
        Deprecated description: LastErrorCode captures the
        last error code reported by the LogicalDevice."
    ::= { msvmMemoryEntry 36 }

msvmmemLocationIndicator OBJECT-TYPE
    SYNTAX     INTEGER {
        unknown(0),
        on(2),
        off(3),
        notSupported(4)
    }
    MAX-ACCESS read-only
    STATUS     current
    DESCRIPTION
        "An integer that reflects the state of an indicator
        (e.g., LED) that is part of a device. Reading the
        value gives the current state. Writing the value
        with 'On'/'Off' turns the indicator on/off, other
        values may not be written."
    ::= { msvmMemoryEntry 37 }

msvmmemMaxQuiesceTime OBJECT-TYPE
    SYNTAX     Gauge32
    UNITS "MilliSeconds"
    MAX-ACCESS read-only
    STATUS     current
    DESCRIPTION
        "Note: The use of this property has been
        deprecated. When evaluating the use of Quiesce, it
        was determined that this single property is not
        adequate for describing when a device will
        automatically exit a quiescent state. In fact, the
        most likely scenario for a device to exit a
        quiescent state was determined to be based on the
        number of outstanding requests queued rather than
        on a maximum time. This decision will be
        re-evaluated and repositioned later. 
        Deprecated description: Maximum time, in
        milliseconds, that a Device can run in a 'Quiesced'
        state. The state is defined in its Availability and
        AdditionalAvailability properties, where 'Quiesced'
        is conveyed by the value 21. What occurs at the end
        of the time limit is device-specific. The Device
        can unquiesce, can be offline, or can take other
        actions. A value of 0 indicates that a Device can
        remain quiesced indefinitely."
    ::= { msvmMemoryEntry 38 }

msvmmemName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmMemoryEntry 39 }

msvmmemNameFormat OBJECT-TYPE
    SYNTAX     INTEGER {
        unknown(0),
        other(1),
        vpd83Type3(2),
        vpd83Type2(3),
        vpd83Type1(4),
        vpd80(5),
        nodeWWN(6),
        snvm(7),
        osDeviceNamespace(8)
    }
    MAX-ACCESS read-only
    STATUS     current
    DESCRIPTION
        "A unique identifier for the Extent."
    ::= { msvmMemoryEntry 40 }

msvmmemNameNamespace OBJECT-TYPE
    SYNTAX     INTEGER {
        unknown(0),
        other(1),
        vpd83NAA6(2),
        vpd83NAA5(3),
        vpd83Type2(4),
        vpd83Type1(5),
        vpd83Type0(6),
        snvm(7),
        nodeWWN(8),
        naa(9),
        eui64(10),
        t10VID(11),
        osDeviceName(12)
    }
    MAX-ACCESS read-only
    STATUS     current
    DESCRIPTION
        "A unique identifier for the Extent."
    ::= { msvmMemoryEntry 41 }

msvmmemNoSinglePointOfFailure OBJECT-TYPE
    SYNTAX     TruthValue
    MAX-ACCESS read-only
    STATUS     current
    DESCRIPTION
        "Indicates whether or not there exists no single
        point of failure."
    ::= { msvmMemoryEntry 42 }

msvmmemNumberOfBlocks OBJECT-TYPE
    SYNTAX     Gauge32
    MAX-ACCESS read-only
    STATUS     current
    DESCRIPTION
        "Total number of logically contiguous blocks, of
        size Block Size, which form this Extent. The total
        size of the Extent can be calculated by multiplying
        BlockSize by NumberOfBlocks. If the BlockSize is 1,
        this property is the total size of the Extent."
    ::= { msvmMemoryEntry 43 }

msvmmemOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmMemoryEntry 44 }

msvmmemOtherEnabledState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "EnabledState is an integer enumeration that
        indicates the enabled and disabled states of an
        element. It can also indicate the transitions
        between these requested states. For example,
        shutting down (value=4) and starting (value=10) are
        transient states between enabled and disabled. The
        following text briefly summarizes the various
        enabled and disabled states: 
        Enabled (2) indicates that the element is or could
        be executing commands, will process any queued
        commands, and queues new requests. 
        Disabled (3) indicates that the element will not
        execute commands and will drop any new requests. 
        Shutting Down (4) indicates that the element is in
        the process of going to a Disabled state. 
        Not Applicable (5) indicates the element does not
        support being enabled or disabled. 
        Enabled but Offline (6) indicates that the element
        might be completing commands, and will drop any new
        requests. 
        Test (7) indicates that the element is in a test
        state. 
        Deferred (8) indicates that the element might be
        completing commands, but will queue any new
        requests. 
        Quiesce (9) indicates that the element is enabled
        but in a restricted mode. The behavior of the
        element is similar to the Enabled state, but it
        processes only a restricted set of commands. All
        other requests are queued. 
        Starting (10) indicates that the element is in the
        process of going to an Enabled state. New requests
        are queued."
    ::= { msvmMemoryEntry 45 }

msvmmemOtherErrorDescription OBJECT-TYPE
    SYNTAX     INTEGER {
        other(1),
        unknown(2),
        ok(3),
        badRead(4),
        parityError(5),
        singleBitError(6),
        doubleBitError(7),
        multiBitError(8),
        nibbleError(9),
        checksumError(10),
        crcError(11)
    }
    MAX-ACCESS read-only
    STATUS     current
    DESCRIPTION
        "An integer enumeration describing the type of
        error that occurred most recently. For example,
        single (value=6) or double bit errors (7) can be
        specified using this property. The values, 12-14,
        are undefined in the CIM Schema since in DMI, they
        mix the semantics of the type of error and whether
        it was correctable or not. The latter is indicated
        in the property, CorrectableError."
    ::= { msvmMemoryEntry 46 }

msvmmemOtherIdentifyingInfo OBJECT-TYPE
    SYNTAX     WtcsDisplayString (SIZE (0..256))
    MAX-ACCESS read-only
    STATUS     current
    DESCRIPTION
        "An array of free-form strings providing
        explanations and details behind the entries in the
        OtherIdentifyingInfo array. Note that each entry of
        this array is related to the entry in
        OtherIdentifyingInfo that is located at the same
        index."
    ::= { msvmMemoryEntry 47 }

msvmmemOtherNameFormat OBJECT-TYPE
    SYNTAX     INTEGER {
        unknown(0),
        other(1),
        vpd83NAA6(2),
        vpd83NAA5(3),
        vpd83Type2(4),
        vpd83Type1(5),
        vpd83Type0(6),
        snvm(7),
        nodeWWN(8),
        naa(9),
        eui64(10),
        t10VID(11),
        osDeviceName(12)
    }
    MAX-ACCESS read-only
    STATUS     current
    DESCRIPTION
        "The list here applies to all StorageExtent
        subclasses. Please look at the Description in each
        subclass for guidelines on the approriate values
        for that subclass. Note that any of these formats
        could apply to a CompositeExtent. 
        
        Note - this property originally touched on two
        concepts that are now separated into this property
        and NameNamespace. Values 2,3,4,5,6, and 8 are
        retained for backwards compatibility but are
        deprecated in lieu of the corresponding values in
        CIM_StorageExtent.NameNamespace. 
        
        For example, the preferred source for SCSI virtual
        (RAID) disk names is from Inquiry VPD page 83
        response, type 3 identifiers. These will have
        NameFormat set to 'NAA' and NameNamespace to
        'VPD83Type3'. 
        
        Format of the Name property. Values for extents
        representing SCSI volumes are (per SCSI SPC-3): 
        2 = VPD Page 83, NAA IEEE Registered Extended
        (VPD83NAA6) 
        (DEPRECATED) 
        3 = VPD Page 83, NAA IEEE Registered (VPD83NAA5) 
        (DEPRECATED) 
        4 = VPD Page 83, (VPD83Type2) (DEPRECATED) 
        5 = VPD Page 83, 
        T10 Vendor Identification (VPD83Type1) (DEPRECATED)
        
        6 = VPD Page 83, Vendor Specific (VPD83Type0)
        (DEPRECATED) 
        7 = Serial Number/Vendor/Model (SNVM) SNVM is 3
        strings representing the vendor name, product name
        within the vendor namespace, and the serial number
        within the model namespace. Strings are delimited
        with a '+'. Spaces may be included and are
        significant. The serial number is the text
        representation of the serial number in hexadecimal
        upper case. This represents the vendor and model ID
        from SCSI Inquiry data; the vendor field MUST be 8
        characters wide and the product field MUST be 16
        characters wide. For example, 
        'ACME____+SUPER DISK______+124437458' (_ is a space
        character) 
        8 = Node WWN (for single LUN/controller) (NodeWWN) 
        (DEPRECATED) 
        9 = NAA as a generic format. See 
        http://standards.ieee.org/regauth/oui/tutorials/fib
        recomp_id.html. Formatted as 16 or 32 unseparated
        uppercase hex characters (2 per binary byte). For
        example '21000020372D3C73' 
        10 = EUI as a generic format (EUI64) See 
        http://standards.ieee.org/regauth/oui/tutorials/EUI
        64.html. 
        Formatted as 16 unseparated uppercase hex
        characters (2 per binary byte) 
        11 = T10 vendor identifier format as returned by
        SCSI Inquiry VPD page 83, identifier type 1. See
        T10 SPC-3 specification. This is the 8-byte ASCII
        vendor ID from the T10 registry followed by a
        vendor specific ASCII identifier; spaces are
        permitted. For non SCSI volumes, 'SNVM' may be the
        most appropriate choice. 12 = OS Device Name (for
        LogicalDisks). See LogicalDisk Name description for
        details."
    ::= { msvmMemoryEntry 48 }

msvmmemOtherNameNamespace OBJECT-TYPE
    SYNTAX     INTEGER {
        unknown(0),
        other(1),
        vpd83Type3(2),
        vpd83Type2(3),
        vpd83Type1(4),
        vpd80(5),
        nodeWWN(6),
        snvm(7),
        osDeviceNamespace(8)
    }
    MAX-ACCESS read-only
    STATUS     current
    DESCRIPTION
        "The preferred source SCSI for volume names is SCSI
        VPD Page 83 responses. Page 83 returns a list of
        identifiers for various device elements. The
        metadata for each identifier includes an
        Association field, identifiers with association of
        0 apply to volumes. Page 83 supports several
        namespaces specified in the Type field in the
        identifier metadata. See SCSI SPC-3 specification. 
        2 = VPD Page 83, Type 3 NAA (NameFormat SHOULD be
        NAA) 
        3 = VPD Page 83, Type 2 EUI64 (NameFormat EUI) 
        4 = VPD Page 83, Type 1 T10 Vendor Identification 
        (NameFormat T10) 
        Less preferred volume namespaces from other
        interfaces: 
        5 = VPD page 80, Serial number (NameFormat SHOULD
        be Other) 
        6 = FC NodeWWN (NameFormat SHOULD be NAA or EUI) 
        7 = Serial Number/Vendor/Model (NameFormat SHOULD
        be SNVM) 
        The preferred namespace for LogigicalDisk names is
        platform specific device namespace; see
        LogigicalDIsk Description. 
        8 = OS Device Namespace."
    ::= { msvmMemoryEntry 49 }

msvmmemPackageRedundancy OBJECT-TYPE
    SYNTAX     Integer32
    MAX-ACCESS read-only
    STATUS     current
    DESCRIPTION
        "How many physical packages can currently fail
        without data loss. For example, in the storage
        domain, this might be disk spindles."
    ::= { msvmMemoryEntry 50 }

msvmmemPowerManagementCapability OBJECT-TYPE
    SYNTAX     INTEGER {
        unknown(0),
        notSupported(1),
        disabled(2),
        enabled(3),
        powerSavingModesEnteredAutomatic(4),
        powerStateSettable(5),
        powerCyclingSupported(6),
        timedPowerOnSupported(7)
    }
    MAX-ACCESS read-only
    STATUS     current
    DESCRIPTION
        "Note: The use of this property has been
        deprecated. Instead, use the PowerCapabilites
        property in an associated
        PowerManagementCapabilities class. Deprecated
        description: An enumerated array describing the
        power management capabilities of the Device."
    ::= { msvmMemoryEntry 51 }

msvmmemPowerManagementSupported OBJECT-TYPE
    SYNTAX     TruthValue
    MAX-ACCESS read-only
    STATUS     current
    DESCRIPTION
        "Note: The use of this property has been
        deprecated. Instead, the existence of an associated
        PowerManagementCapabilities class (associated using
        the ElementCapabilities relationship) indicates
        that power management is supported. Deprecated
        description: Boolean that indicates that the Device
        can use power management."
    ::= { msvmMemoryEntry 52 }

msvmmemPowerOnHours OBJECT-TYPE
    SYNTAX     Gauge32
    UNITS "Hours"
    MAX-ACCESS read-only
    STATUS     current
    DESCRIPTION
        "Note: The use of this method is deprecated. 
        Deprecated description: The number of consecutive
        hours that this Device has been powered on since
        its last power cycle."
    ::= { msvmMemoryEntry 53 }

msvmmemPrimordial OBJECT-TYPE
    SYNTAX     TruthValue
    MAX-ACCESS read-only
    STATUS     current
    DESCRIPTION
        "If true, 'Primordial' indicates that the
        containing System does not have the ability to
        create or delete this operational element. This is
        important because StorageExtents are assembled into
        higher-level abstractions using the BasedOn
        association. Although the higher-level abstractions
        can be created and deleted, the most basic, (i.e.
        primordial), hardware-based storage entities
        cannot. They are physically realized as part of the
        System, or are actually managed by some other
        System and imported as if they were physically
        realized. In other words, a Primordial
        StorageExtent exists in, but is not created by its
        System and conversely a non-Primordial
        StorageExtent is created in the context of its
        System. For StorageVolumes, this property will
        generally be false. One use of this property is to
        enable algorithms that aggregate
        StorageExtent.ConsumableSpace across all,
        StorageExtents but that also want to distinquish
        the space that underlies Primordial StoragePools.
        Since implementations are not required to surface
        all Component StorageExtents of a StoragePool, this
        information is not accessible in any other way."
    ::= { msvmMemoryEntry 54 }

msvmmemPurpose OBJECT-TYPE
    SYNTAX     WtcsDisplayString
    MAX-ACCESS read-only
    STATUS     current
    DESCRIPTION
        "A free form string describing the media and/or its
        use."
    ::= { msvmMemoryEntry 55 }

msvmmemRequestedState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "EnabledState is an integer enumeration that
        indicates the enabled and disabled states of an
        element. It can also indicate the transitions
        between these requested states. For example,
        shutting down (value=4) and starting (value=10) are
        transient states between enabled and disabled. The
        following text briefly summarizes the various
        enabled and disabled states: 
        Enabled (2) indicates that the element is or could
        be executing commands, will process any queued
        commands, and queues new requests. 
        Disabled (3) indicates that the element will not
        execute commands and will drop any new requests. 
        Shutting Down (4) indicates that the element is in
        the process of going to a Disabled state. 
        Not Applicable (5) indicates the element does not
        support being enabled or disabled. 
        Enabled but Offline (6) indicates that the element
        might be completing commands, and will drop any new
        requests. 
        Test (7) indicates that the element is in a test
        state. 
        Deferred (8) indicates that the element might be
        completing commands, but will queue any new
        requests. 
        Quiesce (9) indicates that the element is enabled
        but in a restricted mode. The behavior of the
        element is similar to the Enabled state, but it
        processes only a restricted set of commands. All
        other requests are queued. 
        Starting (10) indicates that the element is in the
        process of going to an Enabled state. New requests
        are queued."
    ::= { msvmMemoryEntry 56 }

msvmmemSequentialAccess OBJECT-TYPE
    SYNTAX     TruthValue
    MAX-ACCESS read-only
    STATUS     current
    DESCRIPTION
        "Boolean set to TRUE if the Storage is sequentially
        accessed by a MediaAccessDevice. A TapePartition is
        an example of a sequentially accessed
        StorageExtent. StorageVolumes, Disk Partitions and
        LogicalDisks represent randomly accessed Extents."
    ::= { msvmMemoryEntry 57 }

msvmmemStartingAddress OBJECT-TYPE
    SYNTAX     Gauge32
    UNITS "KiloBytes"
    MAX-ACCESS read-only
    STATUS     current
    DESCRIPTION
        "The beginning address, referenced by an
        application or operating system and mapped by a
        memory controller, for this Memory object. The
        starting address is specified in KBytes."
    ::= { msvmMemoryEntry 58 }

msvmmemStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmMemoryEntry 59 }

msvmmemStatusDescriptions OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmMemoryEntry 60 }

msvmmemStatusInfo OBJECT-TYPE
    SYNTAX     INTEGER {
        other(1),
        unknown(2),
        enabled(3),
        disabled(4),
        notApplicable(5)
    }
    MAX-ACCESS read-only
    STATUS     current
    DESCRIPTION
        "Note: The use of this method is deprecated in lieu
        of a more clearly named property (EnabledState)
        that is inherited from ManagedSystemElement and
        that has additional enumerated values. 
        Deprecated description: The StatusInfo property
        indicates whether the Logical Device is in an
        enabled state (value=3), disabled state (value=4),
        some other state (value=1), or an unknown state
        (value=2). If this property does not apply to the
        LogicalDevice, the value 5 ('Not Applicable')
        should be used. If a Device is
        ('Enabled')(value=3), it has been powered up and is
        configured and operational. The Device might or
        might not be functionally active, depending on
        whether its Availability (or
        AdditionalAvailability) indicates that it is
        ('Running/Full Power')(value=3) or ('Off line')
        (value=8). In an enabled but offline mode, a Device
        might be performing out-of-band requests, such as
        running Diagnostics. If StatusInfo is ('Disabled')
        (value=4), a Device can only be 'enabled' or
        powered off. In a personal computer environment,
        ('Disabled') means that the driver of the device is
        not available in the stack. In other environments,
        a Device can be disabled by removing its
        configuration file. A disabled device is physically
        present in a System and consuming resources, but it
        cannot be communicated with until a driver is
        loaded, a configuration file is loaded, or some
        other 'enabling' activity has occurred."
    ::= { msvmMemoryEntry 61 }

msvmmemSystemCreationClassName OBJECT-TYPE
    SYNTAX     WtcsDisplayString (SIZE (0..256))
    MAX-ACCESS read-only
    STATUS     current
    DESCRIPTION
        "The CreationClassName of the scoping system."
    ::= { msvmMemoryEntry 62 }

msvmmemSystemLevelAddress OBJECT-TYPE
    SYNTAX     TruthValue
    MAX-ACCESS read-only
    STATUS     current
    DESCRIPTION
        "Boolean indicating whether the address information
        in the property, ErrorAddress, is a system-level
        address (TRUE) or a physical address (FALSE). If
        the ErrorInfo property is equal to 3, 'OK', then
        this property has no meaning."
    ::= { msvmMemoryEntry 63 }

msvmmemSystemName OBJECT-TYPE
    SYNTAX     WtcsDisplayString (SIZE (0..256))
    MAX-ACCESS read-only
    STATUS     current
    DESCRIPTION
        "The System Name of the scoping system."
    ::= { msvmMemoryEntry 64 }

msvmmemTimeOfLastStateChange OBJECT-TYPE
    SYNTAX     DateAndTime
    MAX-ACCESS read-only
    STATUS     current
    DESCRIPTION
        "The date or time when the EnabledState of the
        element last changed. If the state of the element
        has not changed and this property is populated,
        then it must be set to a 0 interval value. If a
        state change was requested, but rejected or not yet
        processed, the property must not be updated."
    ::= { msvmMemoryEntry 65 }

msvmmemTotalPowerOnHours OBJECT-TYPE
    SYNTAX     Gauge32
    UNITS "Hours"
    MAX-ACCESS read-only
    STATUS     current
    DESCRIPTION
        "Note: The use of this method is deprecated. 
        Deprecated description: The total number of hours
        that this Device has been powered on."
    ::= { msvmMemoryEntry 66 }

msvmmemvolatile OBJECT-TYPE
    SYNTAX     TruthValue
    MAX-ACCESS read-only
    STATUS     current
    DESCRIPTION
        "Volatile is a property that indicates whether this
        memory is volatile or not."
    ::= { msvmMemoryEntry 67 }

msvmMemorySettingDataTable OBJECT-TYPE
    SYNTAX     SEQUENCE OF MsvmMemorySettingData
    MAX-ACCESS not-accessible
    STATUS     current
    DESCRIPTION
        "Represents the configured state of the memory for
        a virtual system."
    ::= { msvmMemory 2 }

msvmMemorySettingDataEntry OBJECT-TYPE
    SYNTAX     MsvmMemorySettingData
    MAX-ACCESS not-accessible
    STATUS     current
    DESCRIPTION
        "None"
    INDEX      { msvmmsdIndex }
    ::= { msvmMemorySettingDataTable 1 }

MsvmMemorySettingData ::= SEQUENCE {
    msvmmsdIndex Integer32,
    msvmmsdAddress WtcsDisplayString,
    msvmmsdAllocationUnits WtcsDisplayString,
    msvmmsdAutomaticAllocation TruthValue,
    msvmmsdAutomaticDeallocation TruthValue,
    msvmmsdCaption WtcsDisplayString,
    msvmmsdConnection WtcsDisplayString,
    msvmmsdConsumerVisibility INTEGER,
    msvmmsdDescription WtcsDisplayString,
    msvmmsdDeviceID WtcsDisplayString,
    msvmmsdDeviceIDFormat WtcsDisplayString,
    msvmmsdElementName WtcsDisplayString,
    msvmmsdHostResource WtcsDisplayString,
    msvmmsdInstanceID WtcsDisplayString,
    msvmmsdIsVirtualized TruthValue,
    msvmmsdLimit Gauge32,
    msvmmsdMappingBehavior INTEGER,
    msvmmsdOtherResourceType INTEGER,
    msvmmsdParent WtcsDisplayString,
    msvmmsdPoolID WtcsDisplayString,
    msvmmsdReservation Gauge32,
    msvmmsdResourceSubType WtcsDisplayString,
    msvmmsdResourceType INTEGER,
    msvmmsdVirtualQuantity Gauge32,
    msvmmsdWeight Gauge32
}

msvmmsdIndex OBJECT-TYPE
    SYNTAX     Integer32 (1..2147483647)
    MAX-ACCESS read-only
    STATUS     current
    DESCRIPTION
        "The value of this object uniquely identifies the
        instance entry for this class."
    ::= { msvmMemorySettingDataEntry 1 }

msvmmsdAddress OBJECT-TYPE
    SYNTAX     WtcsDisplayString
    MAX-ACCESS read-only
    STATUS     current
    DESCRIPTION
        "The address of the resource.For example, the MAC
        address of a Ethernet port."
    ::= { msvmMemorySettingDataEntry 2 }

msvmmsdAllocationUnits OBJECT-TYPE
    SYNTAX     WtcsDisplayString
    MAX-ACCESS read-only
    STATUS     current
    DESCRIPTION
        "This property specifies the units of allocation
        used by the Reservation and Limit properties.  For
        example, when ResourceType=Processor,
        AllocationUnits may be set to MHZ. When
        ResourceType=Memory, AllocationUnits may be set to
        MB"
    ::= { msvmMemorySettingDataEntry 3 }

msvmmsdAutomaticAllocation OBJECT-TYPE
    SYNTAX     TruthValue
    MAX-ACCESS read-only
    STATUS     current
    DESCRIPTION
        "This property specifies if the resource will be
        automatically allocated.  For example when set to
        true, when the consuming virtual computer system is
        powered on, this resource would be allocated.  A
        value of false indicates the resource must be
        explicitly allocated.  For example, the setting may
        represent removable media (cdrom, floppy, etc.)
        where at power on time, the media isnot present. 
        An explicit operation is required to allocate the
        resource."
    ::= { msvmMemorySettingDataEntry 4 }

msvmmsdAutomaticDeallocation OBJECT-TYPE
    SYNTAX     TruthValue
    MAX-ACCESS read-only
    STATUS     current
    DESCRIPTION
        "This property specifies if the resource will be
        automatically de-allocated.  For example, when set
        to true, when the consuming virtual computer system
        is powered off, this resource would be
        de-allocated.  When set to false, the resource will
        remain allocated and must be explicitly
        de-allocated."
    ::= { msvmMemorySettingDataEntry 5 }

msvmmsdCaption OBJECT-TYPE
    SYNTAX     WtcsDisplayString (SIZE (0..64))
    MAX-ACCESS read-only
    STATUS     current
    DESCRIPTION
        "The Caption property is a short textual
        description (one- line string) of the object."
    ::= { msvmMemorySettingDataEntry 6 }

msvmmsdConnection OBJECT-TYPE
    SYNTAX     WtcsDisplayString
    MAX-ACCESS read-only
    STATUS     current
    DESCRIPTION
        "The thing to which this resource is connected. 
        For example, a named network or switch port."
    ::= { msvmMemorySettingDataEntry 7 }

msvmmsdConsumerVisibility OBJECT-TYPE
    SYNTAX     INTEGER {
        unknown(0),
        passedThrough(2),
        virtualized(3),
        notrepresented(4)
    }
    MAX-ACCESS read-only
    STATUS     current
    DESCRIPTION
        "Describes the consumers visibility to the
        allocated  resource.
        A value of 'Passed-Through' indicates the
        underlying or host resource is utilized and passed
        through to the consumer, possibly using
        partitioning. At least one item shall be present in
        the DeviceID property.  
        A value of 'Virtualized' indicates the resource is
        virtualized and may not map directly to an
        underlying/host resource. Some implementations may
        support specific assignment for virtualized
        resources, in which case the host resource(s) are
        exposed using the DeviceID property. 
        A value of 'Not represented' indicates a
        representation of the resource does not exist
        within the context of the resource consumer."
    ::= { msvmMemorySettingDataEntry 8 }

msvmmsdDescription OBJECT-TYPE
    SYNTAX     WtcsDisplayString
    MAX-ACCESS read-only
    STATUS     current
    DESCRIPTION
        "The Description property provides a textual
        description of the object."
    ::= { msvmMemorySettingDataEntry 9 }

msvmmsdDeviceID OBJECT-TYPE
    SYNTAX     WtcsDisplayString
    MAX-ACCESS read-only
    STATUS     current
    DESCRIPTION
        "Address or other identifying information to
        uniquely name the logical device. This property is
        inherited from CIM_LogicalDevice and it is always
        set to 'Microsoft:<GUID>'."
    ::= { msvmMemorySettingDataEntry 10 }

msvmmsdDeviceIDFormat OBJECT-TYPE
    SYNTAX     WtcsDisplayString
    MAX-ACCESS read-only
    STATUS     current
    DESCRIPTION
        "Address or other identifying information to
        uniquely name the logical device. This property is
        inherited from CIM_LogicalDevice and it is always
        set to 'Microsoft:<GUID>'."
    ::= { msvmMemorySettingDataEntry 11 }

msvmmsdElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmMemorySettingDataEntry 12 }

msvmmsdHostResource OBJECT-TYPE
    SYNTAX     WtcsDisplayString
    MAX-ACCESS read-only
    STATUS     current
    DESCRIPTION
        "This property exposes specific assignment to host
        or underlying resources.        The embedded
        instances shall contain only key properties and be
        treated as Object Paths. If the virtual resource
        may be scheduled on a number of underlying
        resources, this property shall be left NULL. In
        that case, the DeviceAllocatedFromPool or
        ResourceAllocationFromPool associations may be used
        to determine the pool of host resources this
        virtual resource may be scheduled on. If specific
        assignment is utilized, all underlying resources
        used by this virtual resource shall be listed in
        this array.  Typically the array will contain one
        item, however for aggregate allocations, such as
        multiple processors, multiple host resources may be
        specified."
    ::= { msvmMemorySettingDataEntry 13 }

msvmmsdInstanceID OBJECT-TYPE
    SYNTAX     WtcsDisplayString
    MAX-ACCESS read-only
    STATUS     current
    DESCRIPTION
        "Within the scope of the instantiating Namespace,
        InstanceID opaquely and uniquely identifies an
        instance of this class. To ensure uniqueness within
        the NameSpace, the value of InstanceID should be
        constructed using the following 'preferred'
        algorithm: 
        <OrgID>:<LocalID> 
        Where <OrgID> and <LocalID> are separated by a
        colon (:), and where <OrgID> must include a
        copyrighted, trademarked, or otherwise unique name
        that is owned by the business entity that is
        creating or defining the InstanceID or that is a
        registered ID assigned to the business entity by a
        recognized global authority. (This requirement is
        similar to the <Schema Name>_<Class Name> structure
        of Schema class names.) In addition, to ensure
        uniqueness, <OrgID> must not contain a colon (:).
        When using this algorithm, the first colon to
        appear in InstanceID must appear between <OrgID>
        and <LocalID>. 
        <LocalID> is chosen by the business entity and
        should not be reused to identify different
        underlying (real-world) elements. If the above
        'preferred' algorithm is not used, the defining
        entity must assure that the resulting InstanceID is
        not reused across any InstanceIDs produced by this
        or other providers for the NameSpace of this
        instance. 
        For DMTF-defined instances, the 'preferred'
        algorithm must be used with the <OrgID> set to
        CIM."
    ::= { msvmMemorySettingDataEntry 14 }

msvmmsdIsVirtualized OBJECT-TYPE
    SYNTAX     TruthValue
    MAX-ACCESS read-only
    STATUS     current
    DESCRIPTION
        "Specifies if this device is virtualized or passed
        through, possibly using partitioning. When set to
        false, the underlying or host resource is utilized.
        At least one item shall be present in the DeviceID
        property. When set to true, the resource is
        virtualized and may not map directly to an
        underlying/host resource. Some implementations may
        support specific assignment for virtualized
        resources, in which case the host resource(s) are
        exposed using the DeviceID property. This property
        is always set to True."
    ::= { msvmMemorySettingDataEntry 15 }

msvmmsdLimit OBJECT-TYPE
    SYNTAX     Gauge32
    MAX-ACCESS read-only
    STATUS     current
    DESCRIPTION
        "This property specifies the upper bound, or
        maximum amount of resource that will be granted for
        this allocation. For example, a system which
        supports memory paging may support setting the
        Limit of a Memory allocation below that of the
        VirtualQuantity, thus forcing paging to occur for
        this allocation."
    ::= { msvmMemorySettingDataEntry 16 }

msvmmsdMappingBehavior OBJECT-TYPE
    SYNTAX     INTEGER {
        unknown(0),
        notSupported(1),
        dedicated(2),
        softAffinity(3),
        hardAffinity(4)
    }
    MAX-ACCESS read-only
    STATUS     current
    DESCRIPTION
        "Specifies how this resource maps to underlying
        resourcesIf the HostResource array contains any
        entries, this property reflects how the resource
        maps to those specific resources."
    ::= { msvmMemorySettingDataEntry 17 }

msvmmsdOtherResourceType OBJECT-TYPE
    SYNTAX     INTEGER {
        other(1),
        computerSystem(2),
        processor(3),
        memory(4),
        ideController(5),
        parallelSCSIHBA(6),
        fcHBA(7),
        iSCSIHBA(8),
        ibHCA(9),
        ethernetAdapter(10),
        iOSlot(11),
        iODevice(12),
        floppyDrive(13),
        cdDrive(14),
        dvddrive(15),
        serialport(16),
        parallelport(17),
        usbController(18),
        graphicscontroller(19),
        storageExtent(20),
        disk(21),
        tape(22),
        otherstoragedevice(23),
        firewireController(24),
        partitionableUnit(25),
        basePartitionableUnit(26),
        powerSupply(27),
        coolingDevice(28),
        dmtfreserved(29)
    }
    MAX-ACCESS read-only
    STATUS     current
    DESCRIPTION
        "The type of resource this allocation setting
        represents."
    ::= { msvmMemorySettingDataEntry 18 }

msvmmsdParent OBJECT-TYPE
    SYNTAX     WtcsDisplayString
    MAX-ACCESS read-only
    STATUS     current
    DESCRIPTION
        "The Parent of the resource.  For example, a
        controller for the current allocation"
    ::= { msvmMemorySettingDataEntry 19 }

msvmmsdPoolID OBJECT-TYPE
    SYNTAX     WtcsDisplayString
    MAX-ACCESS read-only
    STATUS     current
    DESCRIPTION
        "This property specifies which ResourcePool the
        resource is currently allocated from, or which
        ResourcePool the resource will be allocated from
        when the allocation occurs."
    ::= { msvmMemorySettingDataEntry 20 }

msvmmsdReservation OBJECT-TYPE
    SYNTAX     Gauge32
    MAX-ACCESS read-only
    STATUS     current
    DESCRIPTION
        "This property specifies the amount of resource
        guaranteed to be available for this allocation.  On
        system which support over-commitment of resources,
        this value is typically used for admission control
        to prevent an an allocation from being accepted
        thus preventing starvation."
    ::= { msvmMemorySettingDataEntry 21 }

msvmmsdResourceSubType OBJECT-TYPE
    SYNTAX     WtcsDisplayString
    MAX-ACCESS read-only
    STATUS     current
    DESCRIPTION
        "A string describing an implementation specific
        sub-type for this resource.  For example, this may
        be used to distinguish different models of the same
        resource type."
    ::= { msvmMemorySettingDataEntry 22 }

msvmmsdResourceType OBJECT-TYPE
    SYNTAX     INTEGER {
        other(0),
        computerSystem(1),
        cpu(2),
        memory(3),
        ideController(4),
        parallelSCSIHBA(5),
        fcSCSIHBA(6),
        iSCSIHBA(7),
        fcpAdapter(8),
        ibHCA(9),
        ethernetAdapter(10),
        iOSlot(11),
        iODevice(12),
        floppyDrive(13),
        cdDVDdrive(14),
        serialport(15),
        parallelport(16),
        usbController(17),
        graphicscontroller(18),
        disk(19),
        tape(20),
        otherstoragedevice(21),
        firewireController(22),
        partitionableUnit(23),
        dmtfreserved(24)
    }
    MAX-ACCESS read-only
    STATUS     current
    DESCRIPTION
        "A string that describes the resource type when a
        well defined value is not available and
        ResourceType has the value 'Other'."
    ::= { msvmMemorySettingDataEntry 23 }

msvmmsdVirtualQuantity OBJECT-TYPE
    SYNTAX     Gauge32
    MAX-ACCESS read-only
    STATUS     current
    DESCRIPTION
        "This property specifies the quantity of resources
        presented to the consumer.  For example, when
        ResourceType=Processor,  this property would
        reflect the number of discrete Processors presented
        to the virtual computer system.  When
        ResourceType=Memory, this property could reflect
        the number of MB reported to the virtual computer
        system."
    ::= { msvmMemorySettingDataEntry 24 }

msvmmsdWeight OBJECT-TYPE
    SYNTAX     Gauge32
    MAX-ACCESS read-only
    STATUS     current
    DESCRIPTION
        "This property specifies a relative priority for
        this allocation in relation to other allocations
        from the same ResourcePool.  This property has no
        unit of measure, and is only relevant when compared
        to other allocations vying for the same host
        resources."
    ::= { msvmMemorySettingDataEntry 25 }

msvmNetworking OBJECT-IDENTITY
    STATUS     current
    DESCRIPTION
        "The networking architecture for virtualization
        models the physical networking architecture. It
        uses standard networking objects such as switches,
        switch ports, and network adapters."
    ::= { informantHyperV 5 }

msvmActiveConnectionTable OBJECT-TYPE
    SYNTAX     SEQUENCE OF MsvmActiveConnection
    MAX-ACCESS not-accessible
    STATUS     current
    DESCRIPTION
        "Connects a switch port to the LAN endpoint to
        which the port is connected. The existence of this
        object means that the switch port and the LAN
        endpoint are actively connected and the Ethernet
        port associated with the LAN endpoint can
        communicate with the network through the switch
        port."
    ::= { msvmNetworking 1 }

msvmActiveConnectionEntry OBJECT-TYPE
    SYNTAX     MsvmActiveConnection
    MAX-ACCESS not-accessible
    STATUS     current
    DESCRIPTION
        "None"
    INDEX      { msvmacIndex }
    ::= { msvmActiveConnectionTable 1 }

MsvmActiveConnection ::= SEQUENCE {
    msvmacIndex Integer32,
    msvmacAntecedent WtcsDisplayString,
    msvmacDependent WtcsDisplayString,
    msvmacIsUnidirectional TruthValue,
    msvmacOtherTrafficDescription WtcsDisplayString,
    msvmacTrafficType INTEGER
}

msvmacIndex OBJECT-TYPE
    SYNTAX     Integer32 (1..2147483647)
    MAX-ACCESS read-only
    STATUS     current
    DESCRIPTION
        "The value of this object uniquely identifies the
        instance entry for this class."
    ::= { msvmActiveConnectionEntry 1 }

msvmacAntecedent OBJECT-TYPE
    SYNTAX     WtcsDisplayString
    MAX-ACCESS read-only
    STATUS     current
    DESCRIPTION
        "Antecedent represents the independent object in
        this association."
    ::= { msvmActiveConnectionEntry 2 }

msvmacDependent OBJECT-TYPE
    SYNTAX     WtcsDisplayString
    MAX-ACCESS read-only
    STATUS     current
    DESCRIPTION
        "Dependent represents the object that is dependent
        on the Antecedent."
    ::= { msvmActiveConnectionEntry 3 }

msvmacIsUnidirectional OBJECT-TYPE
    SYNTAX     TruthValue
    MAX-ACCESS read-only
    STATUS     current
    DESCRIPTION
        "TRUE means that this connection is unidirectional;
        FALSE means that this connection is bidirectional.
        When the connection is unidirectional, the
        'speaker' should be defined as the Antecedent
        reference. In a bidirectional connection, the
        selection of which AccessPoint is the Antecedent or
        Dependent is immaterial."
    ::= { msvmActiveConnectionEntry 4 }

msvmacOtherTrafficDescription OBJECT-TYPE
    SYNTAX     WtcsDisplayString (SIZE (0..64))
    MAX-ACCESS read-only
    STATUS     current
    DESCRIPTION
        "Note: The use of this element is deprecated
        because it is incorrectly placed on the
        association. Unicast, broadcast, or other traffic
        types are not a function of the connection between
        the referenced endpoints, but rather are a function
        of the addressing, protocol and basic functionality
        of the endpoints. 
        Deprecated description: A string that describes the
        type of traffic that is being carried over this
        instance when its Type property is set, for
        example, to 1 (Other)."
    ::= { msvmActiveConnectionEntry 5 }

msvmacTrafficType OBJECT-TYPE
    SYNTAX     INTEGER {
        unknown(0),
        other(1),
        unicast(2),
        broadcast(3),
        multicast(4),
        anycast(5)
    }
    MAX-ACCESS read-only
    STATUS     current
    DESCRIPTION
        "Note: The use of this element is deprecated
        because it is incorrectly placed on the
        association. Unicast, broadcast, or other traffic
        types are not a function of the connection between
        the referenced endpoints, but rather are a function
        of the addressing, protocol and basic functionality
        of the endpoints. 
        Deprecated description: The type of traffic that is
        carried over this connection."
    ::= { msvmActiveConnectionEntry 6 }

msvmBindsToTable OBJECT-TYPE
    SYNTAX     SEQUENCE OF MsvmBindsTo
    MAX-ACCESS not-accessible
    STATUS     current
    DESCRIPTION
        "This association establishes a ServiceAccessPoint
        as a requester of protocol services from a
        ProtocolEndpoint."
    ::= { msvmNetworking 2 }

msvmBindsToEntry OBJECT-TYPE
    SYNTAX     MsvmBindsTo
    MAX-ACCESS not-accessible
    STATUS     current
    DESCRIPTION
        "None"
    INDEX      { msvmBindsToIndex }
    ::= { msvmBindsToTable 1 }

MsvmBindsTo ::= SEQUENCE {
    msvmBindsToIndex Integer32,
    msvmBindsToAntecedent WtcsDisplayString,
    msvmBindsToDependent WtcsDisplayString
}

msvmBindsToIndex OBJECT-TYPE
    SYNTAX     Integer32 (1..2147483647)
    MAX-ACCESS read-only
    STATUS     current
    DESCRIPTION
        "The value of this object uniquely identifies the
        instance entry for this class."
    ::= { msvmBindsToEntry 1 }

msvmBindsToAntecedent OBJECT-TYPE
    SYNTAX     WtcsDisplayString
    MAX-ACCESS read-only
    STATUS     current
    DESCRIPTION
        "Antecedent represents the independent object in
        this association."
    ::= { msvmBindsToEntry 2 }

msvmBindsToDependent OBJECT-TYPE
    SYNTAX     WtcsDisplayString
    MAX-ACCESS read-only
    STATUS     current
    DESCRIPTION
        "Dependent represents the object that is dependent
        on the Antecedent."
    ::= { msvmBindsToEntry 3 }

msvmDeviceSAPImplementationTable OBJECT-TYPE
    SYNTAX     SEQUENCE OF MsvmDeviceSAPImplementation
    MAX-ACCESS not-accessible
    STATUS     current
    DESCRIPTION
        "An association between a ServiceAccessPoint (SAP)
        and how it is implemented."
    ::= { msvmNetworking 3 }

msvmDeviceSAPImplementationEntry OBJECT-TYPE
    SYNTAX     MsvmDeviceSAPImplementation
    MAX-ACCESS not-accessible
    STATUS     current
    DESCRIPTION
        "None"
    INDEX      { msvmdsiIndex }
    ::= { msvmDeviceSAPImplementationTable 1 }

MsvmDeviceSAPImplementation ::= SEQUENCE {
    msvmdsiIndex Integer32,
    msvmdsiAntecedent WtcsDisplayString,
    msvmdsiDependent WtcsDisplayString
}

msvmdsiIndex OBJECT-TYPE
    SYNTAX     Integer32 (1..2147483647)
    MAX-ACCESS read-only
    STATUS     current
    DESCRIPTION
        "The value of this object uniquely identifies the
        instance entry for this class."
    ::= { msvmDeviceSAPImplementationEntry 1 }

msvmdsiAntecedent OBJECT-TYPE
    SYNTAX     WtcsDisplayString
    MAX-ACCESS read-only
    STATUS     current
    DESCRIPTION
        "Antecedent represents the independent object in
        this association."
    ::= { msvmDeviceSAPImplementationEntry 2 }

msvmdsiDependent OBJECT-TYPE
    SYNTAX     WtcsDisplayString
    MAX-ACCESS read-only
    STATUS     current
    DESCRIPTION
        "Dependent represents the object that is dependent
        on the Antecedent."
    ::= { msvmDeviceSAPImplementationEntry 3 }

msvmDynamicForwardingEntryTable OBJECT-TYPE
    SYNTAX     SEQUENCE OF MsvmDynamicForwardingEntry
    MAX-ACCESS not-accessible
    STATUS     current
    DESCRIPTION
        "A DynamicForwardingEntry represents an entry in
        the forwarding (filtering) database associated with
        the TransparentBridgingService."
    ::= { msvmNetworking 4 }

msvmDynamicForwardingEntryEntry OBJECT-TYPE
    SYNTAX     MsvmDynamicForwardingEntry
    MAX-ACCESS not-accessible
    STATUS     current
    DESCRIPTION
        "None"
    INDEX      { msvmdfeIndex }
    ::= { msvmDynamicForwardingEntryTable 1 }

MsvmDynamicForwardingEntry ::= SEQUENCE {
    msvmdfeIndex Integer32,
    msvmdfeCaption WtcsDisplayString,
    msvmdfeCreationClassName WtcsDisplayString,
    msvmdfeDescription WtcsDisplayString,
    msvmdfeDynamicStatus INTEGER,
    msvmdfeElementName WtcsDisplayString,
    msvmdfeHealthState INTEGER,
    msvmdfeInstallDate DateAndTime,
    msvmdfeMACAddress WtcsDisplayString,
    msvmdfeName WtcsDisplayString,
    msvmdfeOperationalStatus INTEGER,
    msvmdfeServiceCreationClassName WtcsDisplayString,
    msvmdfeServiceName WtcsDisplayString,
    msvmdfeStatus WtcsDisplayString,
    msvmdfeStatusDescriptions WtcsDisplayString,
    msvmdfeSystemCreationClassName WtcsDisplayString,
    msvmdfeSystemName WtcsDisplayString
}

msvmdfeIndex OBJECT-TYPE
    SYNTAX     Integer32 (1..2147483647)
    MAX-ACCESS read-only
    STATUS     current
    DESCRIPTION
        "The value of this object uniquely identifies the
        instance entry for this class."
    ::= { msvmDynamicForwardingEntryEntry 1 }

msvmdfeCaption OBJECT-TYPE
    SYNTAX     WtcsDisplayString (SIZE (0..64))
    MAX-ACCESS read-only
    STATUS     current
    DESCRIPTION
        "The Caption property is a short textual
        description (one- line string) of the object."
    ::= { msvmDynamicForwardingEntryEntry 2 }

msvmdfeCreationClassName OBJECT-TYPE
    SYNTAX     WtcsDisplayString (SIZE (0..256))
    MAX-ACCESS read-only
    STATUS     current
    DESCRIPTION
        "CreationClassName indicates the name of the class
        or the subclass used in the creation of an
        instance. When used with the other key properties
        of this class, this property allows all instances
        of this class and its subclasses to be uniquely
        identified."
    ::= { msvmDynamicForwardingEntryEntry 3 }

msvmdfeDescription OBJECT-TYPE
    SYNTAX     WtcsDisplayString
    MAX-ACCESS read-only
    STATUS     current
    DESCRIPTION
        "The Description property provides a textual
        description of the object."
    ::= { msvmDynamicForwardingEntryEntry 4 }

msvmdfeDynamicStatus OBJECT-TYPE
    SYNTAX     INTEGER {
        other(1),
        invalid(2),
        learned(3),
        self(4),
        mgmt(5)
    }
    MAX-ACCESS read-only
    STATUS     current
    DESCRIPTION
        "The status of the entry."
    ::= { msvmDynamicForwardingEntryEntry 5 }

msvmdfeElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmDynamicForwardingEntryEntry 6 }

msvmdfeHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmDynamicForwardingEntryEntry 7 }

msvmdfeInstallDate OBJECT-TYPE
    SYNTAX     DateAndTime
    MAX-ACCESS read-only
    STATUS     current
    DESCRIPTION
        "A datetime value that indicates when the object
        was installed. Lack of a value does not indicate
        that the object is not installed."
    ::= { msvmDynamicForwardingEntryEntry 8 }

msvmdfeMACAddress OBJECT-TYPE
    SYNTAX     WtcsDisplayString (SIZE (0..12))
    MAX-ACCESS read-only
    STATUS     current
    DESCRIPTION
        "Unicast MAC address for which the
        TransparentBridging Service has forwarding and/or
        filtering information. Note that the MAC address is
        formatted as twelve hexadecimal digits (e.g.,
        '010203040506'), with each pair representing one of
        the six octets of the MAC address in 'canonical'
        bit order according to RFC 2469."
    ::= { msvmDynamicForwardingEntryEntry 9 }

msvmdfeName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmDynamicForwardingEntryEntry 10 }

msvmdfeOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmDynamicForwardingEntryEntry 11 }

msvmdfeServiceCreationClassName OBJECT-TYPE
    SYNTAX     WtcsDisplayString (SIZE (0..256))
    MAX-ACCESS read-only
    STATUS     current
    DESCRIPTION
        "The scoping Service's CreationClassName."
    ::= { msvmDynamicForwardingEntryEntry 12 }

msvmdfeServiceName OBJECT-TYPE
    SYNTAX     WtcsDisplayString (SIZE (0..256))
    MAX-ACCESS read-only
    STATUS     current
    DESCRIPTION
        "The scoping Service's Name."
    ::= { msvmDynamicForwardingEntryEntry 13 }

msvmdfeStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmDynamicForwardingEntryEntry 14 }

msvmdfeStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmDynamicForwardingEntryEntry 15 }

msvmdfeSystemCreationClassName OBJECT-TYPE
    SYNTAX     WtcsDisplayString (SIZE (0..256))
    MAX-ACCESS read-only
    STATUS     current
    DESCRIPTION
        "The scoping System's CreationClassName."
    ::= { msvmDynamicForwardingEntryEntry 16 }

msvmdfeSystemName OBJECT-TYPE
    SYNTAX     WtcsDisplayString (SIZE (0..256))
    MAX-ACCESS read-only
    STATUS     current
    DESCRIPTION
        "The scoping System's Name."
    ::= { msvmDynamicForwardingEntryEntry 17 }

msvmEmulatedEthernetPortTable OBJECT-TYPE
    SYNTAX     SEQUENCE OF MsvmEmulatedEthernetPort
    MAX-ACCESS not-accessible
    STATUS     current
    DESCRIPTION
        "Represents an emulated Ethernet adapter. This
        adapter is used when a virtual machine is not
        capable of running the synthetic Ethernet port."
    ::= { msvmNetworking 5 }

msvmEmulatedEthernetPortEntry OBJECT-TYPE
    SYNTAX     MsvmEmulatedEthernetPort
    MAX-ACCESS not-accessible
    STATUS     current
    DESCRIPTION
        "None"
    INDEX      { msvmeepIndex }
    ::= { msvmEmulatedEthernetPortTable 1 }

MsvmEmulatedEthernetPort ::= SEQUENCE {
    msvmeepIndex Integer32,
    msvmeepActiveMaxTransmissionUnit Gauge32,
    msvmeepAdditionalAvailability INTEGER,
    msvmeepAutoSense TruthValue,
    msvmeepAvailability INTEGER,
    msvmeepCapabilities INTEGER,
    msvmeepCapabilityDescriptions WtcsDisplayString,
    msvmeepCaption WtcsDisplayString,
    msvmeepCreationClassName WtcsDisplayString,
    msvmeepDescription WtcsDisplayString,
    msvmeepDeviceID WtcsDisplayString,
    msvmeepElementName WtcsDisplayString,
    msvmeepEnabledCapabilities INTEGER,
    msvmeepEnabledDefault INTEGER,
    msvmeepEnabledState INTEGER,
    msvmeepErrorCleared TruthValue,
    msvmeepErrorDescription WtcsDisplayString,
    msvmeepFullDuplex TruthValue,
    msvmeepHealthState INTEGER,
    msvmeepIdentifyingDescriptions WtcsDisplayString,
    msvmeepInstallDate DateAndTime,
    msvmeepLastErrorCode Gauge32,
    msvmeepLinkTechnology INTEGER,
    msvmeepLocationIndicator INTEGER,
    msvmeepMaxDataSize Gauge32,
    msvmeepMaxQuiesceTime Gauge32,
    msvmeepMaxSpeed Gauge32,
    msvmeepName WtcsDisplayString,
    msvmeepNetworkAddresses WtcsDisplayString,
    msvmeepOperationalStatus INTEGER,
    msvmeepOtherEnabledCapabilities WtcsDisplayString,
    msvmeepOtherEnabledState WtcsDisplayString,
    msvmeepOtherIdentifyingInfo WtcsDisplayString,
    msvmeepOtherLinkTechnology WtcsDisplayString,
    msvmeepOtherNetworkPortType WtcsDisplayString,
    msvmeepOtherPortType WtcsDisplayString,
    msvmeepPermanentAddress WtcsDisplayString,
    msvmeepPortNumber Integer32,
    msvmeepPortType INTEGER,
    msvmeepPowerManagementCapability INTEGER,
    msvmeepPowerManagementSupported TruthValue,
    msvmeepPowerOnHours Gauge32,
    msvmeepRequestedSpeed Gauge32,
    msvmeepRequestedState INTEGER,
    msvmeepSpeed Gauge32,
    msvmeepStatus WtcsDisplayString,
    msvmeepStatusDescriptions WtcsDisplayString,
    msvmeepStatusInfo INTEGER,
    msvmeepSupportMaxTransmissionUnt Gauge32,
    msvmeepSystemCreationClassName WtcsDisplayString,
    msvmeepSystemName WtcsDisplayString,
    msvmeepTimeOfLastStateChange DateAndTime,
    msvmeepTotalPowerOnHours Gauge32,
    msvmeepUsageRestriction INTEGER
}

msvmeepIndex OBJECT-TYPE
    SYNTAX     Integer32 (1..2147483647)
    MAX-ACCESS read-only
    STATUS     current
    DESCRIPTION
        "The value of this object uniquely identifies the
        instance entry for this class."
    ::= { msvmEmulatedEthernetPortEntry 1 }

msvmeepActiveMaxTransmissionUnit OBJECT-TYPE
    SYNTAX     Gauge32
    UNITS "Bytes"
    MAX-ACCESS read-only
    STATUS     current
    DESCRIPTION
        "The active or negotiated maximum transmission unit
        (MTU) that can be supported."
    ::= { msvmEmulatedEthernetPortEntry 2 }

msvmeepAdditionalAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Additional availability and status of the Device
        in addition to that specified in the Availability
        property. The Availability property denotes the
        primary status and availability of the Device. In
        some cases, this property will not be sufficient to
        denote the complete status of the Device. In those
        cases, the AdditionalAvailability property can be
        used to provide further information. For example,
        the primary Availability of a device might be 'Off
        line' (value=8) or in a low-power state
        (AdditionalAvailability value=14), or the Device
        could be running Diagnostics
        (AdditionalAvailability value=5, 'In Test')."
    ::= { msvmEmulatedEthernetPortEntry 3 }

msvmeepAutoSense OBJECT-TYPE
    SYNTAX     TruthValue
    MAX-ACCESS read-only
    STATUS     current
    DESCRIPTION
        "A Boolean that indicates whether the NetworkPort
        is capable of automatically determining the speed
        or other communications characteristics of the
        attached network media."
    ::= { msvmEmulatedEthernetPortEntry 4 }

msvmeepAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Note: The use of this property has been
        deprecated. 
        Deprecated description: The primary availability
        and status of the Device. (Additional status
        information can be specified using the Additional
        Availability array property.) For example, the
        Availability property indicates that the Device is
        running and has full power (value=3), or is in a
        warning (4), test (5), degraded (10) or power save
        state (values 13-15 and 17). The Power Save states
        are defined as follows: Value 13 ('Power Save -
        Unknown') indicates that the Device is known to be
        in a power save mode, but its exact status in this
        mode is unknown; value 14 ('Power Save - Low Power
        Mode') indicates that the Device is in a power save
        state but still functioning, and might exhibit
        degraded performance; value 15 ('Power Save -
        Standby') indicates that the Device is not
        functioning but could be brought to full power
        'quickly'; and value 17 ('Power Save - Warning')
        indicates that the Device is in a warning state,
        but is also in a power save mode."
    ::= { msvmEmulatedEthernetPortEntry 5 }

msvmeepCapabilities OBJECT-TYPE
    SYNTAX     INTEGER {
        unknown(0),
        other(1),
        alertOnLan(2),
        wakeOnLan(3),
        failOver(4),
        loadBalancing(5)
    }
    MAX-ACCESS read-only
    STATUS     current
    DESCRIPTION
        "Capabilities of the EthernetPort. For example, the
        Device might support AlertOnLan, WakeOnLan, Load
        Balancing, or FailOver. If failover or load
        balancing capabilities are listed, a SpareGroup
        (failover) or ExtraCapacityGroup (load balancing)
        should also be defined to completely describe the
        capability."
    ::= { msvmEmulatedEthernetPortEntry 6 }

msvmeepCapabilityDescriptions OBJECT-TYPE
    SYNTAX     WtcsDisplayString
    MAX-ACCESS read-only
    STATUS     current
    DESCRIPTION
        "An array of free-form strings that provides more
        detailed explanations for any of the EthernetPort
        features that are indicated in the Capabilities
        array. Note, each entry of this array is related to
        the entry in the Capabilities array that is located
        at the same index."
    ::= { msvmEmulatedEthernetPortEntry 7 }

msvmeepCaption OBJECT-TYPE
    SYNTAX     WtcsDisplayString (SIZE (0..64))
    MAX-ACCESS read-only
    STATUS     current
    DESCRIPTION
        "The Caption property is a short textual
        description (one- line string) of the object."
    ::= { msvmEmulatedEthernetPortEntry 8 }

msvmeepCreationClassName OBJECT-TYPE
    SYNTAX     WtcsDisplayString (SIZE (0..256))
    MAX-ACCESS read-only
    STATUS     current
    DESCRIPTION
        "CreationClassName indicates the name of the class
        or the subclass used in the creation of an
        instance. When used with the other key properties
        of this class, this property allows all instances
        of this class and its subclasses to be uniquely
        identified."
    ::= { msvmEmulatedEthernetPortEntry 9 }

msvmeepDescription OBJECT-TYPE
    SYNTAX     WtcsDisplayString
    MAX-ACCESS read-only
    STATUS     current
    DESCRIPTION
        "The Description property provides a textual
        description of the object."
    ::= { msvmEmulatedEthernetPortEntry 10 }

msvmeepDeviceID OBJECT-TYPE
    SYNTAX     WtcsDisplayString (SIZE (0..64))
    MAX-ACCESS read-only
    STATUS     current
    DESCRIPTION
        "An address or other identifying information used
        to uniquely name the LogicalDevice."
    ::= { msvmEmulatedEthernetPortEntry 11 }

msvmeepElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmEmulatedEthernetPortEntry 12 }

msvmeepEnabledCapabilities OBJECT-TYPE
    SYNTAX     INTEGER {
        unknown(0),
        other(1),
        alertOnLan(2),
        wakeOnLan(3),
        failOver(4),
        loadBalancing(5)
    }
    MAX-ACCESS read-only
    STATUS     current
    DESCRIPTION
        "Specifies which capabilities are enabled from the
        list of all supported ones, which are defined in
        the Capabilities array."
    ::= { msvmEmulatedEthernetPortEntry 13 }

msvmeepEnabledDefault OBJECT-TYPE
    SYNTAX     INTEGER {
        enabled(2),
        disabled(3),
        notApplicable(5),
        enabledbutOffline(6),
        noDefault(7)
    }
    MAX-ACCESS read-only
    STATUS     current
    DESCRIPTION
        "An enumerated value indicating an administrator's
        default or startup configuration for the Enabled
        State of an element. By default, the element is
        'Enabled' (value=2)."
    ::= { msvmEmulatedEthernetPortEntry 14 }

msvmeepEnabledState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "EnabledState is an integer enumeration that
        indicates the enabled and disabled states of an
        element. It can also indicate the transitions
        between these requested states. For example,
        shutting down (value=4) and starting (value=10) are
        transient states between enabled and disabled. The
        following text briefly summarizes the various
        enabled and disabled states: 
        Enabled (2) indicates that the element is or could
        be executing commands, will process any queued
        commands, and queues new requests. 
        Disabled (3) indicates that the element will not
        execute commands and will drop any new requests. 
        Shutting Down (4) indicates that the element is in
        the process of going to a Disabled state. 
        Not Applicable (5) indicates the element does not
        support being enabled or disabled. 
        Enabled but Offline (6) indicates that the element
        might be completing commands, and will drop any new
        requests. 
        Test (7) indicates that the element is in a test
        state. 
        Deferred (8) indicates that the element might be
        completing commands, but will queue any new
        requests. 
        Quiesce (9) indicates that the element is enabled
        but in a restricted mode. The behavior of the
        element is similar to the Enabled state, but it
        processes only a restricted set of commands. All
        other requests are queued. 
        Starting (10) indicates that the element is in the
        process of going to an Enabled state. New requests
        are queued."
    ::= { msvmEmulatedEthernetPortEntry 15 }

msvmeepErrorCleared OBJECT-TYPE
    SYNTAX     TruthValue
    MAX-ACCESS read-only
    STATUS     current
    DESCRIPTION
        "Note: The use of this method is deprecated. 
        Deprecated description: ErrorCleared is a Boolean
        property that indicates that the error reported in
        LastErrorCode is now cleared."
    ::= { msvmEmulatedEthernetPortEntry 16 }

msvmeepErrorDescription OBJECT-TYPE
    SYNTAX     WtcsDisplayString
    MAX-ACCESS read-only
    STATUS     current
    DESCRIPTION
        "Note: The use of this method is deprecated. 
        Deprecated description: ErrorDescription is a
        free-form string that supplies more information
        about the error recorded in LastErrorCode and
        information on any corrective actions that can be
        taken."
    ::= { msvmEmulatedEthernetPortEntry 17 }

msvmeepFullDuplex OBJECT-TYPE
    SYNTAX     TruthValue
    MAX-ACCESS read-only
    STATUS     current
    DESCRIPTION
        "Boolean that indicates that the port is operating
        in full duplex mode."
    ::= { msvmEmulatedEthernetPortEntry 18 }

msvmeepHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmEmulatedEthernetPortEntry 19 }

msvmeepIdentifyingDescriptions OBJECT-TYPE
    SYNTAX     WtcsDisplayString
    MAX-ACCESS read-only
    STATUS     current
    DESCRIPTION
        "An array of free-form strings providing
        explanations and details behind the entries in the
        OtherIdentifyingInfo array. Note that each entry of
        this array is related to the entry in
        OtherIdentifyingInfo that is located at the same
        index."
    ::= { msvmEmulatedEthernetPortEntry 20 }

msvmeepInstallDate OBJECT-TYPE
    SYNTAX     DateAndTime
    MAX-ACCESS read-only
    STATUS     current
    DESCRIPTION
        "A datetime value that indicates when the object
        was installed. Lack of a value does not indicate
        that the object is not installed."
    ::= { msvmEmulatedEthernetPortEntry 21 }

msvmeepLastErrorCode OBJECT-TYPE
    SYNTAX     Gauge32
    MAX-ACCESS read-only
    STATUS     current
    DESCRIPTION
        "Note: The use of this method is deprecated. 
        Deprecated description: LastErrorCode captures the
        last error code reported by the LogicalDevice."
    ::= { msvmEmulatedEthernetPortEntry 22 }

msvmeepLinkTechnology OBJECT-TYPE
    SYNTAX     INTEGER {
        unknown(0),
        other(1),
        ethernet(2),
        ib(3),
        fc(4),
        fddi(5),
        atm(6),
        tokenRing(7),
        frameRelay(8),
        infrared(9),
        blueTooth(10),
        wirelessLAN(11)
    }
    MAX-ACCESS read-only
    STATUS     current
    DESCRIPTION
        "An enumeration of the types of links. When set to
        1 ('Other'), the related property
        OtherLinkTechnology contains a string description
        of the type of link."
    ::= { msvmEmulatedEthernetPortEntry 23 }

msvmeepLocationIndicator OBJECT-TYPE
    SYNTAX     INTEGER {
        unknown(0),
        on(2),
        off(3),
        notSupported(4)
    }
    MAX-ACCESS read-only
    STATUS     current
    DESCRIPTION
        "An integer that reflects the state of an indicator
        (e.g., LED) that is part of a device. Reading the
        value gives the current state. Writing the value
        with 'On'/'Off' turns the indicator on/off, other
        values may not be written."
    ::= { msvmEmulatedEthernetPortEntry 24 }

msvmeepMaxDataSize OBJECT-TYPE
    SYNTAX     Gauge32
    MAX-ACCESS read-only
    STATUS     current
    DESCRIPTION
        "The maximum size of the INFO (non-MAC) field that
        will be received or transmitted."
    ::= { msvmEmulatedEthernetPortEntry 25 }

msvmeepMaxQuiesceTime OBJECT-TYPE
    SYNTAX     Gauge32
    UNITS "MilliSeconds"
    MAX-ACCESS read-only
    STATUS     current
    DESCRIPTION
        "Note: The use of this property has been
        deprecated. When evaluating the use of Quiesce, it
        was determined that this single property is not
        adequate for describing when a device will
        automatically exit a quiescent state. In fact, the
        most likely scenario for a device to exit a
        quiescent state was determined to be based on the
        number of outstanding requests queued rather than
        on a maximum time. This decision will be
        re-evaluated and repositioned later. 
        Deprecated description: Maximum time, in
        milliseconds, that a Device can run in a 'Quiesced'
        state. The state is defined in its Availability and
        AdditionalAvailability properties, where 'Quiesced'
        is conveyed by the value 21. What occurs at the end
        of the time limit is device-specific. The Device
        can unquiesce, can be offline, or can take other
        actions. A value of 0 indicates that a Device can
        remain quiesced indefinitely."
    ::= { msvmEmulatedEthernetPortEntry 26 }

msvmeepMaxSpeed OBJECT-TYPE
    SYNTAX     Gauge32
    UNITS "Bits per Second"
    MAX-ACCESS read-only
    STATUS     current
    DESCRIPTION
        "The maximum bandwidth of the Port in Bits per
        Second."
    ::= { msvmEmulatedEthernetPortEntry 27 }

msvmeepName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmEmulatedEthernetPortEntry 28 }

msvmeepNetworkAddresses OBJECT-TYPE
    SYNTAX     WtcsDisplayString (SIZE (0..64))
    MAX-ACCESS read-only
    STATUS     current
    DESCRIPTION
        "An array of strings that indicates the network
        addresses for the port."
    ::= { msvmEmulatedEthernetPortEntry 29 }

msvmeepOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmEmulatedEthernetPortEntry 30 }

msvmeepOtherEnabledCapabilities OBJECT-TYPE
    SYNTAX     WtcsDisplayString
    MAX-ACCESS read-only
    STATUS     current
    DESCRIPTION
        "An array of free-form strings that provides more
        detailed explanations for any of the enabled
        capabilities that are specified as 'Other'."
    ::= { msvmEmulatedEthernetPortEntry 31 }

msvmeepOtherEnabledState OBJECT-TYPE
    SYNTAX     WtcsDisplayString
    MAX-ACCESS read-only
    STATUS     current
    DESCRIPTION
        "A string that describes the enabled or disabled
        state of the element when the EnabledState property
        is set to 1 ('Other'). This property must be set to
        null when EnabledState is any value other than 1."
    ::= { msvmEmulatedEthernetPortEntry 32 }

msvmeepOtherIdentifyingInfo OBJECT-TYPE
    SYNTAX     WtcsDisplayString (SIZE (0..256))
    MAX-ACCESS read-only
    STATUS     current
    DESCRIPTION
        "OtherIdentifyingInfo captures data, in addition to
        DeviceID information, that could be used to
        identify a LogicalDevice. For example, you could
        use this property to hold the operating system's
        user-friendly name for the Device."
    ::= { msvmEmulatedEthernetPortEntry 33 }

msvmeepOtherLinkTechnology OBJECT-TYPE
    SYNTAX     WtcsDisplayString
    MAX-ACCESS read-only
    STATUS     current
    DESCRIPTION
        "A string value that describes LinkTechnology when
        it is set to 1, 'Other'."
    ::= { msvmEmulatedEthernetPortEntry 34 }

msvmeepOtherNetworkPortType OBJECT-TYPE
    SYNTAX     WtcsDisplayString
    MAX-ACCESS read-only
    STATUS     current
    DESCRIPTION
        "Note: The use of this property is deprecated in
        lieu of CIM_LogicalPort.PortType. 
        Deprecated description: The type of module, when
        PortType is set to 1 ('Other'.)"
    ::= { msvmEmulatedEthernetPortEntry 35 }

msvmeepOtherPortType OBJECT-TYPE
    SYNTAX     WtcsDisplayString
    MAX-ACCESS read-only
    STATUS     current
    DESCRIPTION
        "Describes the type of module, when PortType is set
        to 1 ('Other')."
    ::= { msvmEmulatedEthernetPortEntry 36 }

msvmeepPermanentAddress OBJECT-TYPE
    SYNTAX     WtcsDisplayString (SIZE (0..64))
    MAX-ACCESS read-only
    STATUS     current
    DESCRIPTION
        "PermanentAddress defines the network address that
        is hardcoded into a port. This 'hardcoded' address
        can be changed using a firmware upgrade or a
        software configuration. When this change is made,
        the field should be updated at the same time.
        PermanentAddress should be left blank if no
        'hardcoded' address exists for the NetworkAdapter."
    ::= { msvmEmulatedEthernetPortEntry 37 }

msvmeepPortNumber OBJECT-TYPE
    SYNTAX     Integer32
    MAX-ACCESS read-only
    STATUS     current
    DESCRIPTION
        "NetworkPorts are often numbered relative to either
        a logical module or a network element."
    ::= { msvmEmulatedEthernetPortEntry 38 }

msvmeepPortType OBJECT-TYPE
    SYNTAX     INTEGER {
        unknown(0),
        other(1),
        notApplicable(2)
    }
    MAX-ACCESS read-only
    STATUS     current
    DESCRIPTION
        "PortType is defined to force consistent naming of
        the 'type' property in subclasses and to guarantee
        unique enum values for all instances of
        NetworkPort. When set to 1 ('Other'), related
        property OtherPortType contains a string
        description of the type of port. A range of values,
        DMTF_Reserved, has been defined that allows
        subclasses to override and define their specific
        types of ports."
    ::= { msvmEmulatedEthernetPortEntry 39 }

msvmeepPowerManagementCapability OBJECT-TYPE
    SYNTAX     INTEGER {
        unknown(0),
        notSupported(1),
        disabled(2),
        enabled(3),
        powerSavingModesEnteredAutomatic(4),
        powerStateSettable(5),
        powerCyclingSupported(6),
        timedPowerOnSupported(7)
    }
    MAX-ACCESS read-only
    STATUS     current
    DESCRIPTION
        "Note: The use of this property has been
        deprecated. Instead, use the PowerCapabilites
        property in an associated
        PowerManagementCapabilities class. Deprecated
        description: An enumerated array describing the
        power management capabilities of the Device."
    ::= { msvmEmulatedEthernetPortEntry 40 }

msvmeepPowerManagementSupported OBJECT-TYPE
    SYNTAX     TruthValue
    MAX-ACCESS read-only
    STATUS     current
    DESCRIPTION
        "Note: The use of this property has been
        deprecated. Instead, the existence of an associated
        PowerManagementCapabilities class (associated using
        the ElementCapabilities relationship) indicates
        that power management is supported. Deprecated
        description: Boolean that indicates that the Device
        can use power management."
    ::= { msvmEmulatedEthernetPortEntry 41 }

msvmeepPowerOnHours OBJECT-TYPE
    SYNTAX     Gauge32
    UNITS "Hours"
    MAX-ACCESS read-only
    STATUS     current
    DESCRIPTION
        "Note: The use of this method is deprecated. 
        Deprecated description: The number of consecutive
        hours that this Device has been powered on since
        its last power cycle."
    ::= { msvmEmulatedEthernetPortEntry 42 }

msvmeepRequestedSpeed OBJECT-TYPE
    SYNTAX     Gauge32
    UNITS "Bits per Second"
    MAX-ACCESS read-only
    STATUS     current
    DESCRIPTION
        "The requested bandwidth of the Port in Bits per
        Second. The actual bandwidth is reported in
        LogicalPort.Speed."
    ::= { msvmEmulatedEthernetPortEntry 43 }

msvmeepRequestedState OBJECT-TYPE
    SYNTAX     INTEGER {
        enabled(2),
        disabled(3),
        shutDown(4),
        noChange(5),
        offline(6),
        test(7),
        deferred(8),
        quiesce(9),
        reboot(10),
        reset(11),
        notApplicable(12)
    }
    MAX-ACCESS read-only
    STATUS     current
    DESCRIPTION
        "RequestedState is an integer enumeration that
        indicates the last requested or desired state for
        the element. The actual state of the element is
        represented by EnabledState. This property is
        provided to compare the last requested and current
        enabled or disabled states. Note that when
        EnabledState is set to 5 ('Not Applicable'), then
        this property has no meaning. By default, the
        RequestedState of the element is 5 ('No Change').
        Refer to the EnabledState property description for
        explanations of the values in the RequestedState
        enumeration. 
        
        It should be noted that there are two new values in
        RequestedState that build on the statuses of
        EnabledState. These are 'Reboot' (10) and 'Reset'
        (11). Reboot refers to doing a 'Shut Down' and then
        moving to an 'Enabled' state. Reset indicates that
        the element is first 'Disabled' and then 'Enabled'.
        The distinction between requesting 'Shut Down' and
        'Disabled' should also be noted. Shut Down requests
        an orderly transition to the Disabled state, and
        might involve removing power, to completely erase
        any existing state. The Disabled state requests an
        immediate disabling of the element, such that it
        will not execute or accept any commands or
        processing requests. 
        
        This property is set as the result of a method
        invocation (such as Start or StopService on
        CIM_Service), or can be overridden and defined as
        WRITEable in a subclass. The method approach is
        considered superior to a WRITEable property,
        because it allows an explicit invocation of the
        operation and the return of a result code. 
        
        A particular instance of EnabledLogicalElement
        might not support RequestedStateChange. If this
        occurs, the value 12 ('Not Applicable') is used."
    ::= { msvmEmulatedEthernetPortEntry 44 }

msvmeepSpeed OBJECT-TYPE
    SYNTAX     Gauge32
    UNITS "Bits per Second"
    MAX-ACCESS read-only
    STATUS     current
    DESCRIPTION
        "The bandwidth of the Port in Bits per Second."
    ::= { msvmEmulatedEthernetPortEntry 45 }

msvmeepStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmEmulatedEthernetPortEntry 46 }

msvmeepStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmEmulatedEthernetPortEntry 47 }

msvmeepStatusInfo OBJECT-TYPE
    SYNTAX     INTEGER {
        other(1),
        unknown(2),
        enabled(3),
        disabled(4),
        notApplicable(5)
    }
    MAX-ACCESS read-only
    STATUS     current
    DESCRIPTION
        "Note: The use of this method is deprecated in lieu
        of a more clearly named property (EnabledState)
        that is inherited from ManagedSystemElement and
        that has additional enumerated values. 
        Deprecated description: The StatusInfo property
        indicates whether the Logical Device is in an
        enabled state (value=3), disabled state (value=4),
        some other state (value=1), or an unknown state
        (value=2). If this property does not apply to the
        LogicalDevice, the value 5 ('Not Applicable')
        should be used. If a Device is
        ('Enabled')(value=3), it has been powered up and is
        configured and operational. The Device might or
        might not be functionally active, depending on
        whether its Availability (or
        AdditionalAvailability) indicates that it is
        ('Running/Full Power')(value=3) or ('Off line')
        (value=8). In an enabled but offline mode, a Device
        might be performing out-of-band requests, such as
        running Diagnostics. If StatusInfo is ('Disabled')
        (value=4), a Device can only be 'enabled' or
        powered off. In a personal computer environment,
        ('Disabled') means that the driver of the device is
        not available in the stack. In other environments,
        a Device can be disabled by removing its
        configuration file. A disabled device is physically
        present in a System and consuming resources, but it
        cannot be communicated with until a driver is
        loaded, a configuration file is loaded, or some
        other 'enabling' activity has occurred."
    ::= { msvmEmulatedEthernetPortEntry 48 }

msvmeepSupportMaxTransmissionUnt OBJECT-TYPE
    SYNTAX     Gauge32
    UNITS "Bytes"
    MAX-ACCESS read-only
    STATUS     current
    DESCRIPTION
        "The maximum transmission unit (MTU) that can be
        supported."
    ::= { msvmEmulatedEthernetPortEntry 49 }

msvmeepSystemCreationClassName OBJECT-TYPE
    SYNTAX     WtcsDisplayString (SIZE (0..256))
    MAX-ACCESS read-only
    STATUS     current
    DESCRIPTION
        "The CreationClassName of the scoping system."
    ::= { msvmEmulatedEthernetPortEntry 50 }

msvmeepSystemName OBJECT-TYPE
    SYNTAX     WtcsDisplayString (SIZE (0..256))
    MAX-ACCESS read-only
    STATUS     current
    DESCRIPTION
        "The System Name of the scoping system."
    ::= { msvmEmulatedEthernetPortEntry 51 }

msvmeepTimeOfLastStateChange OBJECT-TYPE
    SYNTAX     DateAndTime
    MAX-ACCESS read-only
    STATUS     current
    DESCRIPTION
        "The date or time when the EnabledState of the
        element last changed. If the state of the element
        has not changed and this property is populated,
        then it must be set to a 0 interval value. If a
        state change was requested, but rejected or not yet
        processed, the property must not be updated."
    ::= { msvmEmulatedEthernetPortEntry 52 }

msvmeepTotalPowerOnHours OBJECT-TYPE
    SYNTAX     Gauge32
    UNITS "Hours"
    MAX-ACCESS read-only
    STATUS     current
    DESCRIPTION
        "Note: The use of this method is deprecated. 
        Deprecated description: The total number of hours
        that this Device has been powered on."
    ::= { msvmEmulatedEthernetPortEntry 53 }

msvmeepUsageRestriction OBJECT-TYPE
    SYNTAX     INTEGER {
        unknown(0),
        frontendonly(2),
        backendonly(3),
        notrestricted(4)
    }
    MAX-ACCESS read-only
    STATUS     current
    DESCRIPTION
        "In some circumstances, a LogicalPort might be
        identifiable as a front end or back end port. An
        example of this situation would be a storage array
        that might have back end ports to communicate with
        disk drives and front end ports to communicate with
        hosts. If there is no restriction on the use of the
        port, then the value should be set to 'not
        restricted'."
    ::= { msvmEmulatedEthernetPortEntry 54 }

msvmEmulateEthernetPortDataTable OBJECT-TYPE
    SYNTAX     SEQUENCE OF MsvmEmulatedEthernetPortSetData
    MAX-ACCESS not-accessible
    STATUS     current
    DESCRIPTION
        "Represents the configured state of an emulated
        Ethernet adapter."
    ::= { msvmNetworking 6 }

msvmEmulateEthernetPortDataEntry OBJECT-TYPE
    SYNTAX     MsvmEmulatedEthernetPortSetData
    MAX-ACCESS not-accessible
    STATUS     current
    DESCRIPTION
        "None"
    INDEX      { msvmeepsdIndex }
    ::= { msvmEmulateEthernetPortDataTable 1 }

MsvmEmulatedEthernetPortSetData ::= SEQUENCE {
    msvmeepsdIndex Integer32,
    msvmeepsdAddress WtcsDisplayString,
    msvmeepsdAllocationUnits WtcsDisplayString,
    msvmeepsdAutomaticAllocation TruthValue,
    msvmeepsdAutomaticDeallocation TruthValue,
    msvmeepsdCaption WtcsDisplayString,
    msvmeepsdConnection WtcsDisplayString,
    msvmeepsdConsumerVisibility INTEGER,
    msvmeepsdDescription WtcsDisplayString,
    msvmeepsdElementName WtcsDisplayString,
    msvmeepsdHostResource WtcsDisplayString,
    msvmeepsdInstanceID WtcsDisplayString,
    msvmeepsdLimit Gauge32,
    msvmeepsdMappingBehavior INTEGER,
    msvmeepsdOtherResourceType WtcsDisplayString,
    msvmeepsdParent WtcsDisplayString,
    msvmeepsdPoolID WtcsDisplayString,
    msvmeepsdReservation Gauge32,
    msvmeepsdResourceSubType WtcsDisplayString,
    msvmeepsdResourceType INTEGER,
    msvmeepsdStaticMacAddress TruthValue,
    msvmeepsdVirtualQuantity Gauge32,
    msvmeepsdVirtualSystemIdentifier WtcsDisplayString,
    msvmeepsdWeight Gauge32
}

msvmeepsdIndex OBJECT-TYPE
    SYNTAX     Integer32 (1..2147483647)
    MAX-ACCESS read-only
    STATUS     current
    DESCRIPTION
        "The value of this object uniquely identifies the
        instance entry for this class."
    ::= { msvmEmulateEthernetPortDataEntry 1 }

msvmeepsdAddress OBJECT-TYPE
    SYNTAX     WtcsDisplayString
    MAX-ACCESS read-only
    STATUS     current
    DESCRIPTION
        "The address of the resource.For example, the MAC
        address of a Ethernet port."
    ::= { msvmEmulateEthernetPortDataEntry 2 }

msvmeepsdAllocationUnits OBJECT-TYPE
    SYNTAX     WtcsDisplayString
    MAX-ACCESS read-only
    STATUS     current
    DESCRIPTION
        "This property specifies the units of allocation
        used by the Reservation and Limit properties.  For
        example, when ResourceType=Processor,
        AllocationUnits may be set to MHZ. When
        ResourceType=Memory, AllocationUnits may be set to
        MB"
    ::= { msvmEmulateEthernetPortDataEntry 3 }

msvmeepsdAutomaticAllocation OBJECT-TYPE
    SYNTAX     TruthValue
    MAX-ACCESS read-only
    STATUS     current
    DESCRIPTION
        "This property specifies if the resource will be
        automatically allocated.  For example when set to
        true, when the consuming virtual computer system is
        powered on, this resource would be allocated.  A
        value of false indicates the resource must be
        explicitly allocated.  For example, the setting may
        represent removable media (cdrom, floppy, etc.)
        where at power on time, the media isnot present. 
        An explicit operation is required to allocate the
        resource."
    ::= { msvmEmulateEthernetPortDataEntry 4 }

msvmeepsdAutomaticDeallocation OBJECT-TYPE
    SYNTAX     TruthValue
    MAX-ACCESS read-only
    STATUS     current
    DESCRIPTION
        "This property specifies if the resource will be
        automatically de-allocated.  For example, when set
        to true, when the consuming virtual computer system
        is powered off, this resource would be
        de-allocated.  When set to false, the resource will
        remain allocated and must be explicitly
        de-allocated."
    ::= { msvmEmulateEthernetPortDataEntry 5 }

msvmeepsdCaption OBJECT-TYPE
    SYNTAX     WtcsDisplayString (SIZE (0..64))
    MAX-ACCESS read-only
    STATUS     current
    DESCRIPTION
        "The Caption property is a short textual
        description (one- line string) of the object."
    ::= { msvmEmulateEthernetPortDataEntry 6 }

msvmeepsdConnection OBJECT-TYPE
    SYNTAX     WtcsDisplayString
    MAX-ACCESS read-only
    STATUS     current
    DESCRIPTION
        "The thing to which this resource is connected. 
        For example, a named network or switch port."
    ::= { msvmEmulateEthernetPortDataEntry 7 }

msvmeepsdConsumerVisibility OBJECT-TYPE
    SYNTAX     INTEGER {
        unknown(0),
        passedThrough(2),
        virtualized(3),
        notrepresented(4)
    }
    MAX-ACCESS read-only
    STATUS     current
    DESCRIPTION
        "Describes the consumers visibility to the
        allocated  resource.
        A value of 'Passed-Through' indicates the
        underlying or host resource is utilized and passed
        through to the consumer, possibly using
        partitioning. At least one item shall be present in
        the DeviceID property.  
        A value of 'Virtualized' indicates the resource is
        virtualized and may not map directly to an
        underlying/host resource. Some implementations may
        support specific assignment for virtualized
        resources, in which case the host resource(s) are
        exposed using the DeviceID property. 
        A value of 'Not represented' indicates a
        representation of the resource does not exist
        within the context of the resource consumer."
    ::= { msvmEmulateEthernetPortDataEntry 8 }

msvmeepsdDescription OBJECT-TYPE
    SYNTAX     WtcsDisplayString
    MAX-ACCESS read-only
    STATUS     current
    DESCRIPTION
        "The Description property provides a textual
        description of the object."
    ::= { msvmEmulateEthernetPortDataEntry 9 }

msvmeepsdElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmEmulateEthernetPortDataEntry 10 }

msvmeepsdHostResource OBJECT-TYPE
    SYNTAX     WtcsDisplayString
    MAX-ACCESS read-only
    STATUS     current
    DESCRIPTION
        "This property exposes specific assignment to host
        or underlying resources.        The embedded
        instances shall contain only key properties and be
        treated as Object Paths. If the virtual resource
        may be scheduled on a number of underlying
        resources, this property shall be left NULL. In
        that case, the DeviceAllocatedFromPool or
        ResourceAllocationFromPool associations may be used
        to determine the pool of host resources this
        virtual resource may be scheduled on. If specific
        assignment is utilized, all underlying resources
        used by this virtual resource shall be listed in
        this array.  Typically the array will contain one
        item, however for aggregate allocations, such as
        multiple processors, multiple host resources may be
        specified."
    ::= { msvmEmulateEthernetPortDataEntry 11 }

msvmeepsdInstanceID OBJECT-TYPE
    SYNTAX     WtcsDisplayString
    MAX-ACCESS read-only
    STATUS     current
    DESCRIPTION
        "Within the scope of the instantiating Namespace,
        InstanceID opaquely and uniquely identifies an
        instance of this class. To ensure uniqueness within
        the NameSpace, the value of InstanceID should be
        constructed using the following 'preferred'
        algorithm: 
        <OrgID>:<LocalID> 
        Where <OrgID> and <LocalID> are separated by a
        colon (:), and where <OrgID> must include a
        copyrighted, trademarked, or otherwise unique name
        that is owned by the business entity that is
        creating or defining the InstanceID or that is a
        registered ID assigned to the business entity by a
        recognized global authority. (This requirement is
        similar to the <Schema Name>_<Class Name> structure
        of Schema class names.) In addition, to ensure
        uniqueness, <OrgID> must not contain a colon (:).
        When using this algorithm, the first colon to
        appear in InstanceID must appear between <OrgID>
        and <LocalID>. 
        <LocalID> is chosen by the business entity and
        should not be reused to identify different
        underlying (real-world) elements. If the above
        'preferred' algorithm is not used, the defining
        entity must assure that the resulting InstanceID is
        not reused across any InstanceIDs produced by this
        or other providers for the NameSpace of this
        instance. 
        For DMTF-defined instances, the 'preferred'
        algorithm must be used with the <OrgID> set to
        CIM."
    ::= { msvmEmulateEthernetPortDataEntry 12 }

msvmeepsdLimit OBJECT-TYPE
    SYNTAX     Gauge32
    MAX-ACCESS read-only
    STATUS     current
    DESCRIPTION
        "This property specifies the upper bound, or
        maximum amount of resource that will be granted for
        this allocation. For example, a system which
        supports memory paging may support setting the
        Limit of a Memory allocation below that of the
        VirtualQuantity, thus forcing paging to occur for
        this allocation."
    ::= { msvmEmulateEthernetPortDataEntry 13 }

msvmeepsdMappingBehavior OBJECT-TYPE
    SYNTAX     INTEGER {
        unknown(0),
        notSupported(1),
        dedicated(2),
        softAffinity(3),
        hardAffinity(4)
    }
    MAX-ACCESS read-only
    STATUS     current
    DESCRIPTION
        "Specifies how this resource maps to underlying
        resourcesIf the HostResource array contains any
        entries, this property reflects how the resource
        maps to those specific resources."
    ::= { msvmEmulateEthernetPortDataEntry 14 }

msvmeepsdOtherResourceType OBJECT-TYPE
    SYNTAX     WtcsDisplayString
    MAX-ACCESS read-only
    STATUS     current
    DESCRIPTION
        "A string that describes the resource type when a
        well defined value is not available and
        ResourceType has the value 'Other'."
    ::= { msvmEmulateEthernetPortDataEntry 15 }

msvmeepsdParent OBJECT-TYPE
    SYNTAX     WtcsDisplayString
    MAX-ACCESS read-only
    STATUS     current
    DESCRIPTION
        "The Parent of the resource.  For example, a
        controller for the current allocation"
    ::= { msvmEmulateEthernetPortDataEntry 16 }

msvmeepsdPoolID OBJECT-TYPE
    SYNTAX     WtcsDisplayString
    MAX-ACCESS read-only
    STATUS     current
    DESCRIPTION
        "This property specifies which ResourcePool the
        resource is currently allocated from, or which
        ResourcePool the resource will be allocated from
        when the allocation occurs."
    ::= { msvmEmulateEthernetPortDataEntry 17 }

msvmeepsdReservation OBJECT-TYPE
    SYNTAX     Gauge32
    MAX-ACCESS read-only
    STATUS     current
    DESCRIPTION
        "This property specifies the amount of resource
        guaranteed to be available for this allocation.  On
        system which support over-commitment of resources,
        this value is typically used for admission control
        to prevent an an allocation from being accepted
        thus preventing starvation."
    ::= { msvmEmulateEthernetPortDataEntry 18 }

msvmeepsdResourceSubType OBJECT-TYPE
    SYNTAX     WtcsDisplayString
    MAX-ACCESS read-only
    STATUS     current
    DESCRIPTION
        "A string describing an implementation specific
        sub-type for this resource.  For example, this may
        be used to distinguish different models of the same
        resource type."
    ::= { msvmEmulateEthernetPortDataEntry 19 }

msvmeepsdResourceType OBJECT-TYPE
    SYNTAX     INTEGER {
        other(1),
        computerSystem(2),
        processor(3),
        memory(4),
        ideController(5),
        parallelSCSIHBA(6),
        fcHBA(7),
        iSCSIHBA(8),
        ibHCA(9),
        ethernetAdapter(10),
        iOSlot(11),
        iODevice(12),
        floppyDrive(13),
        cdDrive(14),
        dvddrive(15),
        serialport(16),
        parallelport(17),
        usbController(18),
        graphicscontroller(19),
        storageExtent(20),
        disk(21),
        tape(22),
        otherstoragedevice(23),
        firewireController(24),
        partitionableUnit(25),
        basePartitionableUnit(26),
        powerSupply(27),
        coolingDevice(28),
        dmtfreserved(29)
    }
    MAX-ACCESS read-only
    STATUS     current
    DESCRIPTION
        "The type of resource this allocation setting
        represents."
    ::= { msvmEmulateEthernetPortDataEntry 20 }

msvmeepsdStaticMacAddress OBJECT-TYPE
    SYNTAX     TruthValue
    MAX-ACCESS read-only
    STATUS     current
    DESCRIPTION
        "Indicates whether the MAC address is static or
        dynamic."
    ::= { msvmEmulateEthernetPortDataEntry 21 }

msvmeepsdVirtualQuantity OBJECT-TYPE
    SYNTAX     Gauge32
    MAX-ACCESS read-only
    STATUS     current
    DESCRIPTION
        "This property specifies the quantity of resources
        presented to the consumer.  For example, when
        ResourceType=Processor,  this property would
        reflect the number of discrete Processors presented
        to the virtual computer system.  When
        ResourceType=Memory, this property could reflect
        the number of MB reported to the virtual computer
        system."
    ::= { msvmEmulateEthernetPortDataEntry 22 }

msvmeepsdVirtualSystemIdentifier OBJECT-TYPE
    SYNTAX     WtcsDisplayString
    MAX-ACCESS read-only
    STATUS     current
    DESCRIPTION
        "A freeform string array of identifiers of this
        resource presented to the virtual computer system's
        operating system. The indexes and values per index
        are defined on a per resource basis (that is, for
        each enumerated ResourceType value). This property
        is inherited from
        CIM_ResourceAllocationSettingData."
    ::= { msvmEmulateEthernetPortDataEntry 23 }

msvmeepsdWeight OBJECT-TYPE
    SYNTAX     Gauge32
    MAX-ACCESS read-only
    STATUS     current
    DESCRIPTION
        "This property specifies a relative priority for
        this allocation in relation to other allocations
        from the same ResourcePool.  This property has no
        unit of measure, and is only relevant when compared
        to other allocations vying for the same host
        resources."
    ::= { msvmEmulateEthernetPortDataEntry 24 }

msvmExternalEthernetPortTable OBJECT-TYPE
    SYNTAX     SEQUENCE OF MsvmExternalEthernetPort
    MAX-ACCESS not-accessible
    STATUS     current
    DESCRIPTION
        "This class represents an external Ethernet port
        (network adapter)."
    ::= { msvmNetworking 7 }

msvmExternalEthernetPortEntry OBJECT-TYPE
    SYNTAX     MsvmExternalEthernetPort
    MAX-ACCESS not-accessible
    STATUS     current
    DESCRIPTION
        "None"
    INDEX      { msvmxepIndex }
    ::= { msvmExternalEthernetPortTable 1 }

MsvmExternalEthernetPort ::= SEQUENCE {
    msvmxepIndex Integer32,
    msvmxepActiveMaxTransmissionUnit Gauge32,
    msvmxepAdditionalAvailability INTEGER,
    msvmxepAutoSense TruthValue,
    msvmxepAvailability INTEGER,
    msvmxepCapabilities INTEGER,
    msvmxepCapabilityDescriptions WtcsDisplayString,
    msvmxepCaption WtcsDisplayString,
    msvmxepCreationClassName WtcsDisplayString,
    msvmxepDescription WtcsDisplayString,
    msvmxepDeviceID WtcsDisplayString,
    msvmxepElementName WtcsDisplayString,
    msvmxepEnabledCapabilities INTEGER,
    msvmxepEnabledDefault INTEGER,
    msvmxepEnabledState INTEGER,
    msvmxepErrorCleared TruthValue,
    msvmxepErrorDescription WtcsDisplayString,
    msvmxepFullDuplex TruthValue,
    msvmxepHealthState INTEGER,
    msvmxepIdentifyingDescriptions WtcsDisplayString,
    msvmxepInstallDate DateAndTime,
    msvmxepIsBound TruthValue,
    msvmxepLastErrorCode Gauge32,
    msvmxepLinkTechnology INTEGER,
    msvmxepLocationIndicator INTEGER,
    msvmxepMaxDataSize Gauge32,
    msvmxepMaxQuiesceTime Gauge32,
    msvmxepMaxSpeed Gauge32,
    msvmxepName WtcsDisplayString,
    msvmxepNetworkAddresses WtcsDisplayString,
    msvmxepOperationalStatus INTEGER,
    msvmxepOtherEnabledCapabilities WtcsDisplayString,
    msvmxepOtherEnabledState WtcsDisplayString,
    msvmxepOtherIdentifyingInfo WtcsDisplayString,
    msvmxepOtherLinkTechnology WtcsDisplayString,
    msvmxepOtherNetworkPortType WtcsDisplayString,
    msvmxepOtherPortType WtcsDisplayString,
    msvmxepPermanentAddress WtcsDisplayString,
    msvmxepPortNumber Integer32,
    msvmxepPortType INTEGER,
    msvmxepPowerManagementCapability INTEGER,
    msvmxepPowerManagementSupported TruthValue,
    msvmxepPowerOnHours Gauge32,
    msvmxepRequestedSpeed Gauge32,
    msvmxepRequestedState INTEGER,
    msvmxepSpeed Gauge32,
    msvmxepStatus WtcsDisplayString,
    msvmxepStatusDescriptions WtcsDisplayString,
    msvmxepStatusInfo INTEGER,
    msvmxepSupportMaxTransmissionUnt Gauge32,
    msvmxepSystemCreationClassName WtcsDisplayString,
    msvmxepSystemName WtcsDisplayString,
    msvmxepTimeOfLastStateChange DateAndTime,
    msvmxepTotalPowerOnHours Gauge32,
    msvmxepUsageRestriction INTEGER
}

msvmxepIndex OBJECT-TYPE
    SYNTAX     Integer32 (1..2147483647)
    MAX-ACCESS read-only
    STATUS     current
    DESCRIPTION
        "The value of this object uniquely identifies the
        instance entry for this class."
    ::= { msvmExternalEthernetPortEntry 1 }

msvmxepActiveMaxTransmissionUnit OBJECT-TYPE
    SYNTAX     Gauge32
    UNITS "Bytes"
    MAX-ACCESS read-only
    STATUS     current
    DESCRIPTION
        "The active or negotiated maximum transmission unit
        (MTU) that can be supported."
    ::= { msvmExternalEthernetPortEntry 2 }

msvmxepAdditionalAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Additional availability and status of the Device
        in addition to that specified in the Availability
        property. The Availability property denotes the
        primary status and availability of the Device. In
        some cases, this property will not be sufficient to
        denote the complete status of the Device. In those
        cases, the AdditionalAvailability property can be
        used to provide further information. For example,
        the primary Availability of a device might be 'Off
        line' (value=8) or in a low-power state
        (AdditionalAvailability value=14), or the Device
        could be running Diagnostics
        (AdditionalAvailability value=5, 'In Test')."
    ::= { msvmExternalEthernetPortEntry 3 }

msvmxepAutoSense OBJECT-TYPE
    SYNTAX     TruthValue
    MAX-ACCESS read-only
    STATUS     current
    DESCRIPTION
        "A Boolean that indicates whether the NetworkPort
        is capable of automatically determining the speed
        or other communications characteristics of the
        attached network media."
    ::= { msvmExternalEthernetPortEntry 4 }

msvmxepAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Note: The use of this property has been
        deprecated. 
        Deprecated description: The primary availability
        and status of the Device. (Additional status
        information can be specified using the Additional
        Availability array property.) For example, the
        Availability property indicates that the Device is
        running and has full power (value=3), or is in a
        warning (4), test (5), degraded (10) or power save
        state (values 13-15 and 17). The Power Save states
        are defined as follows: Value 13 ('Power Save -
        Unknown') indicates that the Device is known to be
        in a power save mode, but its exact status in this
        mode is unknown; value 14 ('Power Save - Low Power
        Mode') indicates that the Device is in a power save
        state but still functioning, and might exhibit
        degraded performance; value 15 ('Power Save -
        Standby') indicates that the Device is not
        functioning but could be brought to full power
        'quickly'; and value 17 ('Power Save - Warning')
        indicates that the Device is in a warning state,
        but is also in a power save mode."
    ::= { msvmExternalEthernetPortEntry 5 }

msvmxepCapabilities OBJECT-TYPE
    SYNTAX     INTEGER {
        unknown(0),
        other(1),
        alertOnLan(2),
        wakeOnLan(3),
        failOver(4),
        loadBalancing(5)
    }
    MAX-ACCESS read-only
    STATUS     current
    DESCRIPTION
        "Capabilities of the EthernetPort. For example, the
        Device might support AlertOnLan, WakeOnLan, Load
        Balancing, or FailOver. If failover or load
        balancing capabilities are listed, a SpareGroup
        (failover) or ExtraCapacityGroup (load balancing)
        should also be defined to completely describe the
        capability."
    ::= { msvmExternalEthernetPortEntry 6 }

msvmxepCapabilityDescriptions OBJECT-TYPE
    SYNTAX     WtcsDisplayString
    MAX-ACCESS read-only
    STATUS     current
    DESCRIPTION
        "An array of free-form strings that provides more
        detailed explanations for any of the EthernetPort
        features that are indicated in the Capabilities
        array. Note, each entry of this array is related to
        the entry in the Capabilities array that is located
        at the same index."
    ::= { msvmExternalEthernetPortEntry 7 }

msvmxepCaption OBJECT-TYPE
    SYNTAX     WtcsDisplayString (SIZE (0..64))
    MAX-ACCESS read-only
    STATUS     current
    DESCRIPTION
        "The Caption property is a short textual
        description (one- line string) of the object."
    ::= { msvmExternalEthernetPortEntry 8 }

msvmxepCreationClassName OBJECT-TYPE
    SYNTAX     WtcsDisplayString (SIZE (0..256))
    MAX-ACCESS read-only
    STATUS     current
    DESCRIPTION
        "CreationClassName indicates the name of the class
        or the subclass used in the creation of an
        instance. When used with the other key properties
        of this class, this property allows all instances
        of this class and its subclasses to be uniquely
        identified."
    ::= { msvmExternalEthernetPortEntry 9 }

msvmxepDescription OBJECT-TYPE
    SYNTAX     WtcsDisplayString
    MAX-ACCESS read-only
    STATUS     current
    DESCRIPTION
        "The Description property provides a textual
        description of the object."
    ::= { msvmExternalEthernetPortEntry 10 }

msvmxepDeviceID OBJECT-TYPE
    SYNTAX     WtcsDisplayString (SIZE (0..64))
    MAX-ACCESS read-only
    STATUS     current
    DESCRIPTION
        "An address or other identifying information used
        to uniquely name the LogicalDevice."
    ::= { msvmExternalEthernetPortEntry 11 }

msvmxepElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmExternalEthernetPortEntry 12 }

msvmxepEnabledCapabilities OBJECT-TYPE
    SYNTAX     INTEGER {
        unknown(0),
        other(1),
        alertOnLan(2),
        wakeOnLan(3),
        failOver(4),
        loadBalancing(5)
    }
    MAX-ACCESS read-only
    STATUS     current
    DESCRIPTION
        "Specifies which capabilities are enabled from the
        list of all supported ones, which are defined in
        the Capabilities array."
    ::= { msvmExternalEthernetPortEntry 13 }

msvmxepEnabledDefault OBJECT-TYPE
    SYNTAX     INTEGER {
        enabled(2),
        disabled(3),
        notApplicable(5),
        enabledbutOffline(6),
        noDefault(7)
    }
    MAX-ACCESS read-only
    STATUS     current
    DESCRIPTION
        "An enumerated value indicating an administrator's
        default or startup configuration for the Enabled
        State of an element. By default, the element is
        'Enabled' (value=2)."
    ::= { msvmExternalEthernetPortEntry 14 }

msvmxepEnabledState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "EnabledState is an integer enumeration that
        indicates the enabled and disabled states of an
        element. It can also indicate the transitions
        between these requested states. For example,
        shutting down (value=4) and starting (value=10) are
        transient states between enabled and disabled. The
        following text briefly summarizes the various
        enabled and disabled states: 
        Enabled (2) indicates that the element is or could
        be executing commands, will process any queued
        commands, and queues new requests. 
        Disabled (3) indicates that the element will not
        execute commands and will drop any new requests. 
        Shutting Down (4) indicates that the element is in
        the process of going to a Disabled state. 
        Not Applicable (5) indicates the element does not
        support being enabled or disabled. 
        Enabled but Offline (6) indicates that the element
        might be completing commands, and will drop any new
        requests. 
        Test (7) indicates that the element is in a test
        state. 
        Deferred (8) indicates that the element might be
        completing commands, but will queue any new
        requests. 
        Quiesce (9) indicates that the element is enabled
        but in a restricted mode. The behavior of the
        element is similar to the Enabled state, but it
        processes only a restricted set of commands. All
        other requests are queued. 
        Starting (10) indicates that the element is in the
        process of going to an Enabled state. New requests
        are queued."
    ::= { msvmExternalEthernetPortEntry 15 }

msvmxepErrorCleared OBJECT-TYPE
    SYNTAX     TruthValue
    MAX-ACCESS read-only
    STATUS     current
    DESCRIPTION
        "Note: The use of this method is deprecated. 
        Deprecated description: ErrorCleared is a Boolean
        property that indicates that the error reported in
        LastErrorCode is now cleared."
    ::= { msvmExternalEthernetPortEntry 16 }

msvmxepErrorDescription OBJECT-TYPE
    SYNTAX     WtcsDisplayString
    MAX-ACCESS read-only
    STATUS     current
    DESCRIPTION
        "Note: The use of this method is deprecated. 
        Deprecated description: ErrorDescription is a
        free-form string that supplies more information
        about the error recorded in LastErrorCode and
        information on any corrective actions that can be
        taken."
    ::= { msvmExternalEthernetPortEntry 17 }

msvmxepFullDuplex OBJECT-TYPE
    SYNTAX     TruthValue
    MAX-ACCESS read-only
    STATUS     current
    DESCRIPTION
        "Boolean that indicates that the port is operating
        in full duplex mode."
    ::= { msvmExternalEthernetPortEntry 18 }

msvmxepHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmExternalEthernetPortEntry 19 }

msvmxepIdentifyingDescriptions OBJECT-TYPE
    SYNTAX     WtcsDisplayString
    MAX-ACCESS read-only
    STATUS     current
    DESCRIPTION
        "An array of free-form strings providing
        explanations and details behind the entries in the
        OtherIdentifyingInfo array. Note that each entry of
        this array is related to the entry in
        OtherIdentifyingInfo that is located at the same
        index."
    ::= { msvmExternalEthernetPortEntry 20 }

msvmxepInstallDate OBJECT-TYPE
    SYNTAX     DateAndTime
    MAX-ACCESS read-only
    STATUS     current
    DESCRIPTION
        "A datetime value that indicates when the object
        was installed. Lack of a value does not indicate
        that the object is not installed."
    ::= { msvmExternalEthernetPortEntry 21 }

msvmxepIsBound OBJECT-TYPE
    SYNTAX     TruthValue
    MAX-ACCESS read-only
    STATUS     current
    DESCRIPTION
        "If this property is true, then this Ethernet port
        can be connected to the switches and thus can
        provide connectivity to virtual machine. If this
        property is false, then this Ethernet is not being
        used by the virtual machine networking
        architecture. This property is inherited from
        CIM_EthernetPort."
    ::= { msvmExternalEthernetPortEntry 22 }

msvmxepLastErrorCode OBJECT-TYPE
    SYNTAX     Gauge32
    MAX-ACCESS read-only
    STATUS     current
    DESCRIPTION
        "Note: The use of this method is deprecated. 
        Deprecated description: LastErrorCode captures the
        last error code reported by the LogicalDevice."
    ::= { msvmExternalEthernetPortEntry 23 }

msvmxepLinkTechnology OBJECT-TYPE
    SYNTAX     INTEGER {
        unknown(0),
        other(1),
        ethernet(2),
        ib(3),
        fc(4),
        fddi(5),
        atm(6),
        tokenRing(7),
        frameRelay(8),
        infrared(9),
        blueTooth(10),
        wirelessLAN(11)
    }
    MAX-ACCESS read-only
    STATUS     current
    DESCRIPTION
        "An enumeration of the types of links. When set to
        1 ('Other'), the related property
        OtherLinkTechnology contains a string description
        of the type of link."
    ::= { msvmExternalEthernetPortEntry 24 }

msvmxepLocationIndicator OBJECT-TYPE
    SYNTAX     INTEGER {
        unknown(0),
        on(2),
        off(3),
        notSupported(4)
    }
    MAX-ACCESS read-only
    STATUS     current
    DESCRIPTION
        "An integer that reflects the state of an indicator
        (e.g., LED) that is part of a device. Reading the
        value gives the current state. Writing the value
        with 'On'/'Off' turns the indicator on/off, other
        values may not be written."
    ::= { msvmExternalEthernetPortEntry 25 }

msvmxepMaxDataSize OBJECT-TYPE
    SYNTAX     Gauge32
    MAX-ACCESS read-only
    STATUS     current
    DESCRIPTION
        "The maximum size of the INFO (non-MAC) field that
        will be received or transmitted."
    ::= { msvmExternalEthernetPortEntry 26 }

msvmxepMaxQuiesceTime OBJECT-TYPE
    SYNTAX     Gauge32
    UNITS "MilliSeconds"
    MAX-ACCESS read-only
    STATUS     current
    DESCRIPTION
        "Note: The use of this property has been
        deprecated. When evaluating the use of Quiesce, it
        was determined that this single property is not
        adequate for describing when a device will
        automatically exit a quiescent state. In fact, the
        most likely scenario for a device to exit a
        quiescent state was determined to be based on the
        number of outstanding requests queued rather than
        on a maximum time. This decision will be
        re-evaluated and repositioned later. 
        Deprecated description: Maximum time, in
        milliseconds, that a Device can run in a 'Quiesced'
        state. The state is defined in its Availability and
        AdditionalAvailability properties, where 'Quiesced'
        is conveyed by the value 21. What occurs at the end
        of the time limit is device-specific. The Device
        can unquiesce, can be offline, or can take other
        actions. A value of 0 indicates that a Device can
        remain quiesced indefinitely."
    ::= { msvmExternalEthernetPortEntry 27 }

msvmxepMaxSpeed OBJECT-TYPE
    SYNTAX     Gauge32
    UNITS "Bits per Second"
    MAX-ACCESS read-only
    STATUS     current
    DESCRIPTION
        "The maximum bandwidth of the Port in Bits per
        Second."
    ::= { msvmExternalEthernetPortEntry 28 }

msvmxepName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmExternalEthernetPortEntry 29 }

msvmxepNetworkAddresses OBJECT-TYPE
    SYNTAX     WtcsDisplayString (SIZE (0..64))
    MAX-ACCESS read-only
    STATUS     current
    DESCRIPTION
        "An array of strings that indicates the network
        addresses for the port."
    ::= { msvmExternalEthernetPortEntry 30 }

msvmxepOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmExternalEthernetPortEntry 31 }

msvmxepOtherEnabledCapabilities OBJECT-TYPE
    SYNTAX     WtcsDisplayString
    MAX-ACCESS read-only
    STATUS     current
    DESCRIPTION
        "An array of free-form strings that provides more
        detailed explanations for any of the enabled
        capabilities that are specified as 'Other'."
    ::= { msvmExternalEthernetPortEntry 32 }

msvmxepOtherEnabledState OBJECT-TYPE
    SYNTAX     WtcsDisplayString
    MAX-ACCESS read-only
    STATUS     current
    DESCRIPTION
        "A string that describes the enabled or disabled
        state of the element when the EnabledState property
        is set to 1 ('Other'). This property must be set to
        null when EnabledState is any value other than 1."
    ::= { msvmExternalEthernetPortEntry 33 }

msvmxepOtherIdentifyingInfo OBJECT-TYPE
    SYNTAX     WtcsDisplayString (SIZE (0..256))
    MAX-ACCESS read-only
    STATUS     current
    DESCRIPTION
        "OtherIdentifyingInfo captures data, in addition to
        DeviceID information, that could be used to
        identify a LogicalDevice. For example, you could
        use this property to hold the operating system's
        user-friendly name for the Device."
    ::= { msvmExternalEthernetPortEntry 34 }

msvmxepOtherLinkTechnology OBJECT-TYPE
    SYNTAX     WtcsDisplayString
    MAX-ACCESS read-only
    STATUS     current
    DESCRIPTION
        "A string value that describes LinkTechnology when
        it is set to 1, 'Other'."
    ::= { msvmExternalEthernetPortEntry 35 }

msvmxepOtherNetworkPortType OBJECT-TYPE
    SYNTAX     WtcsDisplayString
    MAX-ACCESS read-only
    STATUS     current
    DESCRIPTION
        "Note: The use of this property is deprecated in
        lieu of CIM_LogicalPort.PortType. 
        Deprecated description: The type of module, when
        PortType is set to 1 ('Other'.)"
    ::= { msvmExternalEthernetPortEntry 36 }

msvmxepOtherPortType OBJECT-TYPE
    SYNTAX     WtcsDisplayString
    MAX-ACCESS read-only
    STATUS     current
    DESCRIPTION
        "Describes the type of module, when PortType is set
        to 1 ('Other')."
    ::= { msvmExternalEthernetPortEntry 37 }

msvmxepPermanentAddress OBJECT-TYPE
    SYNTAX     WtcsDisplayString (SIZE (0..64))
    MAX-ACCESS read-only
    STATUS     current
    DESCRIPTION
        "PermanentAddress defines the network address that
        is hardcoded into a port. This 'hardcoded' address
        can be changed using a firmware upgrade or a
        software configuration. When this change is made,
        the field should be updated at the same time.
        PermanentAddress should be left blank if no
        'hardcoded' address exists for the NetworkAdapter."
    ::= { msvmExternalEthernetPortEntry 38 }

msvmxepPortNumber OBJECT-TYPE
    SYNTAX     Integer32
    MAX-ACCESS read-only
    STATUS     current
    DESCRIPTION
        "NetworkPorts are often numbered relative to either
        a logical module or a network element."
    ::= { msvmExternalEthernetPortEntry 39 }

msvmxepPortType OBJECT-TYPE
    SYNTAX     INTEGER {
        unknown(0),
        other(1),
        notApplicable(2)
    }
    MAX-ACCESS read-only
    STATUS     current
    DESCRIPTION
        "PortType is defined to force consistent naming of
        the 'type' property in subclasses and to guarantee
        unique enum values for all instances of
        NetworkPort. When set to 1 ('Other'), related
        property OtherPortType contains a string
        description of the type of port. A range of values,
        DMTF_Reserved, has been defined that allows
        subclasses to override and define their specific
        types of ports."
    ::= { msvmExternalEthernetPortEntry 40 }

msvmxepPowerManagementCapability OBJECT-TYPE
    SYNTAX     INTEGER {
        unknown(0),
        notSupported(1),
        disabled(2),
        enabled(3),
        powerSavingModesEnteredAutomatic(4),
        powerStateSettable(5),
        powerCyclingSupported(6),
        timedPowerOnSupported(7)
    }
    MAX-ACCESS read-only
    STATUS     current
    DESCRIPTION
        "Note: The use of this property has been
        deprecated. Instead, use the PowerCapabilites
        property in an associated
        PowerManagementCapabilities class. Deprecated
        description: An enumerated array describing the
        power management capabilities of the Device."
    ::= { msvmExternalEthernetPortEntry 41 }

msvmxepPowerManagementSupported OBJECT-TYPE
    SYNTAX     TruthValue
    MAX-ACCESS read-only
    STATUS     current
    DESCRIPTION
        "Note: The use of this property has been
        deprecated. Instead, the existence of an associated
        PowerManagementCapabilities class (associated using
        the ElementCapabilities relationship) indicates
        that power management is supported. Deprecated
        description: Boolean that indicates that the Device
        can use power management."
    ::= { msvmExternalEthernetPortEntry 42 }

msvmxepPowerOnHours OBJECT-TYPE
    SYNTAX     Gauge32
    UNITS "Hours"
    MAX-ACCESS read-only
    STATUS     current
    DESCRIPTION
        "Note: The use of this method is deprecated. 
        Deprecated description: The number of consecutive
        hours that this Device has been powered on since
        its last power cycle."
    ::= { msvmExternalEthernetPortEntry 43 }

msvmxepRequestedSpeed OBJECT-TYPE
    SYNTAX     Gauge32
    UNITS "Bits per Second"
    MAX-ACCESS read-only
    STATUS     current
    DESCRIPTION
        "The requested bandwidth of the Port in Bits per
        Second. The actual bandwidth is reported in
        LogicalPort.Speed."
    ::= { msvmExternalEthernetPortEntry 44 }

msvmxepRequestedState OBJECT-TYPE
    SYNTAX     INTEGER {
        enabled(2),
        disabled(3),
        shutDown(4),
        noChange(5),
        offline(6),
        test(7),
        deferred(8),
        quiesce(9),
        reboot(10),
        reset(11),
        notApplicable(12)
    }
    MAX-ACCESS read-only
    STATUS     current
    DESCRIPTION
        "RequestedState is an integer enumeration that
        indicates the last requested or desired state for
        the element. The actual state of the element is
        represented by EnabledState. This property is
        provided to compare the last requested and current
        enabled or disabled states. Note that when
        EnabledState is set to 5 ('Not Applicable'), then
        this property has no meaning. By default, the
        RequestedState of the element is 5 ('No Change').
        Refer to the EnabledState property description for
        explanations of the values in the RequestedState
        enumeration. 
        
        It should be noted that there are two new values in
        RequestedState that build on the statuses of
        EnabledState. These are 'Reboot' (10) and 'Reset'
        (11). Reboot refers to doing a 'Shut Down' and then
        moving to an 'Enabled' state. Reset indicates that
        the element is first 'Disabled' and then 'Enabled'.
        The distinction between requesting 'Shut Down' and
        'Disabled' should also be noted. Shut Down requests
        an orderly transition to the Disabled state, and
        might involve removing power, to completely erase
        any existing state. The Disabled state requests an
        immediate disabling of the element, such that it
        will not execute or accept any commands or
        processing requests. 
        
        This property is set as the result of a method
        invocation (such as Start or StopService on
        CIM_Service), or can be overridden and defined as
        WRITEable in a subclass. The method approach is
        considered superior to a WRITEable property,
        because it allows an explicit invocation of the
        operation and the return of a result code. 
        
        A particular instance of EnabledLogicalElement
        might not support RequestedStateChange. If this
        occurs, the value 12 ('Not Applicable') is used."
    ::= { msvmExternalEthernetPortEntry 45 }

msvmxepSpeed OBJECT-TYPE
    SYNTAX     Gauge32
    UNITS "Bits per Second"
    MAX-ACCESS read-only
    STATUS     current
    DESCRIPTION
        "The bandwidth of the Port in Bits per Second."
    ::= { msvmExternalEthernetPortEntry 46 }

msvmxepStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmExternalEthernetPortEntry 47 }

msvmxepStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmExternalEthernetPortEntry 48 }

msvmxepStatusInfo OBJECT-TYPE
    SYNTAX     INTEGER {
        other(1),
        unknown(2),
        enabled(3),
        disabled(4),
        notApplicable(5)
    }
    MAX-ACCESS read-only
    STATUS     current
    DESCRIPTION
        "Note: The use of this method is deprecated in lieu
        of a more clearly named property (EnabledState)
        that is inherited from ManagedSystemElement and
        that has additional enumerated values. 
        Deprecated description: The StatusInfo property
        indicates whether the Logical Device is in an
        enabled state (value=3), disabled state (value=4),
        some other state (value=1), or an unknown state
        (value=2). If this property does not apply to the
        LogicalDevice, the value 5 ('Not Applicable')
        should be used. If a Device is
        ('Enabled')(value=3), it has been powered up and is
        configured and operational. The Device might or
        might not be functionally active, depending on
        whether its Availability (or
        AdditionalAvailability) indicates that it is
        ('Running/Full Power')(value=3) or ('Off line')
        (value=8). In an enabled but offline mode, a Device
        might be performing out-of-band requests, such as
        running Diagnostics. If StatusInfo is ('Disabled')
        (value=4), a Device can only be 'enabled' or
        powered off. In a personal computer environment,
        ('Disabled') means that the driver of the device is
        not available in the stack. In other environments,
        a Device can be disabled by removing its
        configuration file. A disabled device is physically
        present in a System and consuming resources, but it
        cannot be communicated with until a driver is
        loaded, a configuration file is loaded, or some
        other 'enabling' activity has occurred."
    ::= { msvmExternalEthernetPortEntry 49 }

msvmxepSupportMaxTransmissionUnt OBJECT-TYPE
    SYNTAX     Gauge32
    UNITS "Bytes"
    MAX-ACCESS read-only
    STATUS     current
    DESCRIPTION
        "The maximum transmission unit (MTU) that can be
        supported."
    ::= { msvmExternalEthernetPortEntry 50 }

msvmxepSystemCreationClassName OBJECT-TYPE
    SYNTAX     WtcsDisplayString (SIZE (0..256))
    MAX-ACCESS read-only
    STATUS     current
    DESCRIPTION
        "The CreationClassName of the scoping system."
    ::= { msvmExternalEthernetPortEntry 51 }

msvmxepSystemName OBJECT-TYPE
    SYNTAX     WtcsDisplayString (SIZE (0..256))
    MAX-ACCESS read-only
    STATUS     current
    DESCRIPTION
        "The System Name of the scoping system."
    ::= { msvmExternalEthernetPortEntry 52 }

msvmxepTimeOfLastStateChange OBJECT-TYPE
    SYNTAX     DateAndTime
    MAX-ACCESS read-only
    STATUS     current
    DESCRIPTION
        "The date or time when the EnabledState of the
        element last changed. If the state of the element
        has not changed and this property is populated,
        then it must be set to a 0 interval value. If a
        state change was requested, but rejected or not yet
        processed, the property must not be updated."
    ::= { msvmExternalEthernetPortEntry 53 }

msvmxepTotalPowerOnHours OBJECT-TYPE
    SYNTAX     Gauge32
    UNITS "Hours"
    MAX-ACCESS read-only
    STATUS     current
    DESCRIPTION
        "Note: The use of this method is deprecated. 
        Deprecated description: The total number of hours
        that this Device has been powered on."
    ::= { msvmExternalEthernetPortEntry 54 }

msvmxepUsageRestriction OBJECT-TYPE
    SYNTAX     INTEGER {
        unknown(0),
        frontendonly(2),
        backendonly(3),
        notrestricted(4)
    }
    MAX-ACCESS read-only
    STATUS     current
    DESCRIPTION
        "In some circumstances, a LogicalPort might be
        identifiable as a front end or back end port. An
        example of this situation would be a storage array
        that might have back end ports to communicate with
        disk drives and front end ports to communicate with
        hosts. If there is no restriction on the use of the
        port, then the value should be set to 'not
        restricted'."
    ::= { msvmExternalEthernetPortEntry 55 }

msvmGblEthernetPortSAPImplTable OBJECT-TYPE
    SYNTAX     SEQUENCE OF MsvmGlobalEthernetPortSAPImpl
    MAX-ACCESS not-accessible
    STATUS     current
    DESCRIPTION
        "This association connects a LAN endpoint to a
        global Ethernet port (either an external or
        internal Ethernet port)."
    ::= { msvmNetworking 8 }

msvmGblEthernetPortSAPImplEntry OBJECT-TYPE
    SYNTAX     MsvmGlobalEthernetPortSAPImpl
    MAX-ACCESS not-accessible
    STATUS     current
    DESCRIPTION
        "None"
    INDEX      { msvmgepsiIndex }
    ::= { msvmGblEthernetPortSAPImplTable 1 }

MsvmGlobalEthernetPortSAPImpl ::= SEQUENCE {
    msvmgepsiIndex Integer32,
    msvmgepsiAntecedent WtcsDisplayString,
    msvmgepsiDependent WtcsDisplayString
}

msvmgepsiIndex OBJECT-TYPE
    SYNTAX     Integer32 (1..2147483647)
    MAX-ACCESS read-only
    STATUS     current
    DESCRIPTION
        "The value of this object uniquely identifies the
        instance entry for this class."
    ::= { msvmGblEthernetPortSAPImplEntry 1 }

msvmgepsiAntecedent OBJECT-TYPE
    SYNTAX     WtcsDisplayString
    MAX-ACCESS read-only
    STATUS     current
    DESCRIPTION
        "Antecedent represents the independent object in
        this association."
    ::= { msvmGblEthernetPortSAPImplEntry 2 }

msvmgepsiDependent OBJECT-TYPE
    SYNTAX     WtcsDisplayString
    MAX-ACCESS read-only
    STATUS     current
    DESCRIPTION
        "Dependent represents the object that is dependent
        on the Antecedent."
    ::= { msvmGblEthernetPortSAPImplEntry 3 }

msvmInternalEthernetPortTable OBJECT-TYPE
    SYNTAX     SEQUENCE OF MsvmInternalEthernetPort
    MAX-ACCESS not-accessible
    STATUS     current
    DESCRIPTION
        "This class represents an internal Ethernet port
        (network adapter)."
    ::= { msvmNetworking 9 }

msvmInternalEthernetPortEntry OBJECT-TYPE
    SYNTAX     MsvmInternalEthernetPort
    MAX-ACCESS not-accessible
    STATUS     current
    DESCRIPTION
        "None"
    INDEX      { msvmiepIndex }
    ::= { msvmInternalEthernetPortTable 1 }

MsvmInternalEthernetPort ::= SEQUENCE {
    msvmiepIndex Integer32,
    msvmiepActiveMaxTransmissionUnit Gauge32,
    msvmiepAdditionalAvailability INTEGER,
    msvmiepAutoSense TruthValue,
    msvmiepAvailability INTEGER,
    msvmiepCapabilities INTEGER,
    msvmiepCapabilityDescriptions WtcsDisplayString,
    msvmiepCaption WtcsDisplayString,
    msvmiepCreationClassName WtcsDisplayString,
    msvmiepDescription WtcsDisplayString,
    msvmiepDeviceID WtcsDisplayString,
    msvmiepElementName WtcsDisplayString,
    msvmiepEnabledCapabilities INTEGER,
    msvmiepEnabledDefault INTEGER,
    msvmiepEnabledState INTEGER,
    msvmiepErrorCleared TruthValue,
    msvmiepErrorDescription WtcsDisplayString,
    msvmiepFullDuplex TruthValue,
    msvmiepHealthState INTEGER,
    msvmiepIdentifyingDescriptions WtcsDisplayString,
    msvmiepInstallDate DateAndTime,
    msvmiepLastErrorCode Gauge32,
    msvmiepLinkTechnology INTEGER,
    msvmiepLocationIndicator INTEGER,
    msvmiepMaxDataSize Gauge32,
    msvmiepMaxQuiesceTime Gauge32,
    msvmiepMaxSpeed Gauge32,
    msvmiepName WtcsDisplayString,
    msvmiepNetworkAddresses WtcsDisplayString,
    msvmiepOperationalStatus INTEGER,
    msvmiepOtherEnabledCapabilities WtcsDisplayString,
    msvmiepOtherEnabledState WtcsDisplayString,
    msvmiepOtherIdentifyingInfo WtcsDisplayString,
    msvmiepOtherLinkTechnology WtcsDisplayString,
    msvmiepOtherNetworkPortType WtcsDisplayString,
    msvmiepOtherPortType WtcsDisplayString,
    msvmiepPermanentAddress WtcsDisplayString,
    msvmiepPortNumber Integer32,
    msvmiepPortType INTEGER,
    msvmiepPowerManagementCapability INTEGER,
    msvmiepPowerManagementSupported TruthValue,
    msvmiepPowerOnHours Gauge32,
    msvmiepRequestedSpeed Gauge32,
    msvmiepRequestedState INTEGER,
    msvmiepSpeed Gauge32,
    msvmiepStatus WtcsDisplayString,
    msvmiepStatusDescriptions WtcsDisplayString,
    msvmiepStatusInfo INTEGER,
    msvmiepSupportMaxTransmissionUnt Gauge32,
    msvmiepSystemCreationClassName WtcsDisplayString,
    msvmiepSystemName WtcsDisplayString,
    msvmiepTimeOfLastStateChange DateAndTime,
    msvmiepTotalPowerOnHours Gauge32,
    msvmiepUsageRestriction INTEGER
}

msvmiepIndex OBJECT-TYPE
    SYNTAX     Integer32 (1..2147483647)
    MAX-ACCESS read-only
    STATUS     current
    DESCRIPTION
        "The value of this object uniquely identifies the
        instance entry for this class."
    ::= { msvmInternalEthernetPortEntry 1 }

msvmiepActiveMaxTransmissionUnit OBJECT-TYPE
    SYNTAX     Gauge32
    UNITS "Bytes"
    MAX-ACCESS read-only
    STATUS     current
    DESCRIPTION
        "The active or negotiated maximum transmission unit
        (MTU) that can be supported."
    ::= { msvmInternalEthernetPortEntry 2 }

msvmiepAdditionalAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Additional availability and status of the Device
        in addition to that specified in the Availability
        property. The Availability property denotes the
        primary status and availability of the Device. In
        some cases, this property will not be sufficient to
        denote the complete status of the Device. In those
        cases, the AdditionalAvailability property can be
        used to provide further information. For example,
        the primary Availability of a device might be 'Off
        line' (value=8) or in a low-power state
        (AdditionalAvailability value=14), or the Device
        could be running Diagnostics
        (AdditionalAvailability value=5, 'In Test')."
    ::= { msvmInternalEthernetPortEntry 3 }

msvmiepAutoSense OBJECT-TYPE
    SYNTAX     TruthValue
    MAX-ACCESS read-only
    STATUS     current
    DESCRIPTION
        "A Boolean that indicates whether the NetworkPort
        is capable of automatically determining the speed
        or other communications characteristics of the
        attached network media."
    ::= { msvmInternalEthernetPortEntry 4 }

msvmiepAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Note: The use of this property has been
        deprecated. 
        Deprecated description: The primary availability
        and status of the Device. (Additional status
        information can be specified using the Additional
        Availability array property.) For example, the
        Availability property indicates that the Device is
        running and has full power (value=3), or is in a
        warning (4), test (5), degraded (10) or power save
        state (values 13-15 and 17). The Power Save states
        are defined as follows: Value 13 ('Power Save -
        Unknown') indicates that the Device is known to be
        in a power save mode, but its exact status in this
        mode is unknown; value 14 ('Power Save - Low Power
        Mode') indicates that the Device is in a power save
        state but still functioning, and might exhibit
        degraded performance; value 15 ('Power Save -
        Standby') indicates that the Device is not
        functioning but could be brought to full power
        'quickly'; and value 17 ('Power Save - Warning')
        indicates that the Device is in a warning state,
        but is also in a power save mode."
    ::= { msvmInternalEthernetPortEntry 5 }

msvmiepCapabilities OBJECT-TYPE
    SYNTAX     INTEGER {
        unknown(0),
        other(1),
        alertOnLan(2),
        wakeOnLan(3),
        failOver(4),
        loadBalancing(5)
    }
    MAX-ACCESS read-only
    STATUS     current
    DESCRIPTION
        "Capabilities of the EthernetPort. For example, the
        Device might support AlertOnLan, WakeOnLan, Load
        Balancing, or FailOver. If failover or load
        balancing capabilities are listed, a SpareGroup
        (failover) or ExtraCapacityGroup (load balancing)
        should also be defined to completely describe the
        capability."
    ::= { msvmInternalEthernetPortEntry 6 }

msvmiepCapabilityDescriptions OBJECT-TYPE
    SYNTAX     WtcsDisplayString
    MAX-ACCESS read-only
    STATUS     current
    DESCRIPTION
        "An array of free-form strings that provides more
        detailed explanations for any of the EthernetPort
        features that are indicated in the Capabilities
        array. Note, each entry of this array is related to
        the entry in the Capabilities array that is located
        at the same index."
    ::= { msvmInternalEthernetPortEntry 7 }

msvmiepCaption OBJECT-TYPE
    SYNTAX     WtcsDisplayString (SIZE (0..64))
    MAX-ACCESS read-only
    STATUS     current
    DESCRIPTION
        "The Caption property is a short textual
        description (one- line string) of the object."
    ::= { msvmInternalEthernetPortEntry 8 }

msvmiepCreationClassName OBJECT-TYPE
    SYNTAX     WtcsDisplayString (SIZE (0..256))
    MAX-ACCESS read-only
    STATUS     current
    DESCRIPTION
        "CreationClassName indicates the name of the class
        or the subclass used in the creation of an
        instance. When used with the other key properties
        of this class, this property allows all instances
        of this class and its subclasses to be uniquely
        identified."
    ::= { msvmInternalEthernetPortEntry 9 }

msvmiepDescription OBJECT-TYPE
    SYNTAX     WtcsDisplayString
    MAX-ACCESS read-only
    STATUS     current
    DESCRIPTION
        "The Description property provides a textual
        description of the object."
    ::= { msvmInternalEthernetPortEntry 10 }

msvmiepDeviceID OBJECT-TYPE
    SYNTAX     WtcsDisplayString (SIZE (0..64))
    MAX-ACCESS read-only
    STATUS     current
    DESCRIPTION
        "An address or other identifying information used
        to uniquely name the LogicalDevice."
    ::= { msvmInternalEthernetPortEntry 11 }

msvmiepElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmInternalEthernetPortEntry 12 }

msvmiepEnabledCapabilities OBJECT-TYPE
    SYNTAX     INTEGER {
        unknown(0),
        other(1),
        alertOnLan(2),
        wakeOnLan(3),
        failOver(4),
        loadBalancing(5)
    }
    MAX-ACCESS read-only
    STATUS     current
    DESCRIPTION
        "Specifies which capabilities are enabled from the
        list of all supported ones, which are defined in
        the Capabilities array."
    ::= { msvmInternalEthernetPortEntry 13 }

msvmiepEnabledDefault OBJECT-TYPE
    SYNTAX     INTEGER {
        enabled(2),
        disabled(3),
        notApplicable(5),
        enabledbutOffline(6),
        noDefault(7)
    }
    MAX-ACCESS read-only
    STATUS     current
    DESCRIPTION
        "An enumerated value indicating an administrator's
        default or startup configuration for the Enabled
        State of an element. By default, the element is
        'Enabled' (value=2)."
    ::= { msvmInternalEthernetPortEntry 14 }

msvmiepEnabledState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "EnabledState is an integer enumeration that
        indicates the enabled and disabled states of an
        element. It can also indicate the transitions
        between these requested states. For example,
        shutting down (value=4) and starting (value=10) are
        transient states between enabled and disabled. The
        following text briefly summarizes the various
        enabled and disabled states: 
        Enabled (2) indicates that the element is or could
        be executing commands, will process any queued
        commands, and queues new requests. 
        Disabled (3) indicates that the element will not
        execute commands and will drop any new requests. 
        Shutting Down (4) indicates that the element is in
        the process of going to a Disabled state. 
        Not Applicable (5) indicates the element does not
        support being enabled or disabled. 
        Enabled but Offline (6) indicates that the element
        might be completing commands, and will drop any new
        requests. 
        Test (7) indicates that the element is in a test
        state. 
        Deferred (8) indicates that the element might be
        completing commands, but will queue any new
        requests. 
        Quiesce (9) indicates that the element is enabled
        but in a restricted mode. The behavior of the
        element is similar to the Enabled state, but it
        processes only a restricted set of commands. All
        other requests are queued. 
        Starting (10) indicates that the element is in the
        process of going to an Enabled state. New requests
        are queued."
    ::= { msvmInternalEthernetPortEntry 15 }

msvmiepErrorCleared OBJECT-TYPE
    SYNTAX     TruthValue
    MAX-ACCESS read-only
    STATUS     current
    DESCRIPTION
        "Note: The use of this method is deprecated. 
        Deprecated description: ErrorCleared is a Boolean
        property that indicates that the error reported in
        LastErrorCode is now cleared."
    ::= { msvmInternalEthernetPortEntry 16 }

msvmiepErrorDescription OBJECT-TYPE
    SYNTAX     WtcsDisplayString
    MAX-ACCESS read-only
    STATUS     current
    DESCRIPTION
        "Note: The use of this method is deprecated. 
        Deprecated description: ErrorDescription is a
        free-form string that supplies more information
        about the error recorded in LastErrorCode and
        information on any corrective actions that can be
        taken."
    ::= { msvmInternalEthernetPortEntry 17 }

msvmiepFullDuplex OBJECT-TYPE
    SYNTAX     TruthValue
    MAX-ACCESS read-only
    STATUS     current
    DESCRIPTION
        "Boolean that indicates that the port is operating
        in full duplex mode."
    ::= { msvmInternalEthernetPortEntry 18 }

msvmiepHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmInternalEthernetPortEntry 19 }

msvmiepIdentifyingDescriptions OBJECT-TYPE
    SYNTAX     WtcsDisplayString
    MAX-ACCESS read-only
    STATUS     current
    DESCRIPTION
        "An array of free-form strings providing
        explanations and details behind the entries in the
        OtherIdentifyingInfo array. Note that each entry of
        this array is related to the entry in
        OtherIdentifyingInfo that is located at the same
        index."
    ::= { msvmInternalEthernetPortEntry 20 }

msvmiepInstallDate OBJECT-TYPE
    SYNTAX     DateAndTime
    MAX-ACCESS read-only
    STATUS     current
    DESCRIPTION
        "A datetime value that indicates when the object
        was installed. Lack of a value does not indicate
        that the object is not installed."
    ::= { msvmInternalEthernetPortEntry 21 }

msvmiepLastErrorCode OBJECT-TYPE
    SYNTAX     Gauge32
    MAX-ACCESS read-only
    STATUS     current
    DESCRIPTION
        "Note: The use of this method is deprecated. 
        Deprecated description: LastErrorCode captures the
        last error code reported by the LogicalDevice."
    ::= { msvmInternalEthernetPortEntry 22 }

msvmiepLinkTechnology OBJECT-TYPE
    SYNTAX     INTEGER {
        unknown(0),
        other(1),
        ethernet(2),
        ib(3),
        fc(4),
        fddi(5),
        atm(6),
        tokenRing(7),
        frameRelay(8),
        infrared(9),
        blueTooth(10),
        wirelessLAN(11)
    }
    MAX-ACCESS read-only
    STATUS     current
    DESCRIPTION
        "An enumeration of the types of links. When set to
        1 ('Other'), the related property
        OtherLinkTechnology contains a string description
        of the type of link."
    ::= { msvmInternalEthernetPortEntry 23 }

msvmiepLocationIndicator OBJECT-TYPE
    SYNTAX     INTEGER {
        unknown(0),
        on(2),
        off(3),
        notSupported(4)
    }
    MAX-ACCESS read-only
    STATUS     current
    DESCRIPTION
        "An integer that reflects the state of an indicator
        (e.g., LED) that is part of a device. Reading the
        value gives the current state. Writing the value
        with 'On'/'Off' turns the indicator on/off, other
        values may not be written."
    ::= { msvmInternalEthernetPortEntry 24 }

msvmiepMaxDataSize OBJECT-TYPE
    SYNTAX     Gauge32
    MAX-ACCESS read-only
    STATUS     current
    DESCRIPTION
        "The maximum size of the INFO (non-MAC) field that
        will be received or transmitted."
    ::= { msvmInternalEthernetPortEntry 25 }

msvmiepMaxQuiesceTime OBJECT-TYPE
    SYNTAX     Gauge32
    UNITS "MilliSeconds"
    MAX-ACCESS read-only
    STATUS     current
    DESCRIPTION
        "Note: The use of this property has been
        deprecated. When evaluating the use of Quiesce, it
        was determined that this single property is not
        adequate for describing when a device will
        automatically exit a quiescent state. In fact, the
        most likely scenario for a device to exit a
        quiescent state was determined to be based on the
        number of outstanding requests queued rather than
        on a maximum time. This decision will be
        re-evaluated and repositioned later. 
        Deprecated description: Maximum time, in
        milliseconds, that a Device can run in a 'Quiesced'
        state. The state is defined in its Availability and
        AdditionalAvailability properties, where 'Quiesced'
        is conveyed by the value 21. What occurs at the end
        of the time limit is device-specific. The Device
        can unquiesce, can be offline, or can take other
        actions. A value of 0 indicates that a Device can
        remain quiesced indefinitely."
    ::= { msvmInternalEthernetPortEntry 26 }

msvmiepMaxSpeed OBJECT-TYPE
    SYNTAX     Gauge32
    UNITS "Bits per Second"
    MAX-ACCESS read-only
    STATUS     current
    DESCRIPTION
        "The maximum bandwidth of the Port in Bits per
        Second."
    ::= { msvmInternalEthernetPortEntry 27 }

msvmiepName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmInternalEthernetPortEntry 28 }

msvmiepNetworkAddresses OBJECT-TYPE
    SYNTAX     WtcsDisplayString (SIZE (0..64))
    MAX-ACCESS read-only
    STATUS     current
    DESCRIPTION
        "An array of strings that indicates the network
        addresses for the port."
    ::= { msvmInternalEthernetPortEntry 29 }

msvmiepOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmInternalEthernetPortEntry 30 }

msvmiepOtherEnabledCapabilities OBJECT-TYPE
    SYNTAX     WtcsDisplayString
    MAX-ACCESS read-only
    STATUS     current
    DESCRIPTION
        "An array of free-form strings that provides more
        detailed explanations for any of the enabled
        capabilities that are specified as 'Other'."
    ::= { msvmInternalEthernetPortEntry 31 }

msvmiepOtherEnabledState OBJECT-TYPE
    SYNTAX     WtcsDisplayString
    MAX-ACCESS read-only
    STATUS     current
    DESCRIPTION
        "A string that describes the enabled or disabled
        state of the element when the EnabledState property
        is set to 1 ('Other'). This property must be set to
        null when EnabledState is any value other than 1."
    ::= { msvmInternalEthernetPortEntry 32 }

msvmiepOtherIdentifyingInfo OBJECT-TYPE
    SYNTAX     WtcsDisplayString (SIZE (0..256))
    MAX-ACCESS read-only
    STATUS     current
    DESCRIPTION
        "OtherIdentifyingInfo captures data, in addition to
        DeviceID information, that could be used to
        identify a LogicalDevice. For example, you could
        use this property to hold the operating system's
        user-friendly name for the Device."
    ::= { msvmInternalEthernetPortEntry 33 }

msvmiepOtherLinkTechnology OBJECT-TYPE
    SYNTAX     WtcsDisplayString
    MAX-ACCESS read-only
    STATUS     current
    DESCRIPTION
        "A string value that describes LinkTechnology when
        it is set to 1, 'Other'."
    ::= { msvmInternalEthernetPortEntry 34 }

msvmiepOtherNetworkPortType OBJECT-TYPE
    SYNTAX     WtcsDisplayString
    MAX-ACCESS read-only
    STATUS     current
    DESCRIPTION
        "Note: The use of this property is deprecated in
        lieu of CIM_LogicalPort.PortType. 
        Deprecated description: The type of module, when
        PortType is set to 1 ('Other'.)"
    ::= { msvmInternalEthernetPortEntry 35 }

msvmiepOtherPortType OBJECT-TYPE
    SYNTAX     WtcsDisplayString
    MAX-ACCESS read-only
    STATUS     current
    DESCRIPTION
        "Describes the type of module, when PortType is set
        to 1 ('Other')."
    ::= { msvmInternalEthernetPortEntry 36 }

msvmiepPermanentAddress OBJECT-TYPE
    SYNTAX     WtcsDisplayString (SIZE (0..64))
    MAX-ACCESS read-only
    STATUS     current
    DESCRIPTION
        "PermanentAddress defines the network address that
        is hardcoded into a port. This 'hardcoded' address
        can be changed using a firmware upgrade or a
        software configuration. When this change is made,
        the field should be updated at the same time.
        PermanentAddress should be left blank if no
        'hardcoded' address exists for the NetworkAdapter."
    ::= { msvmInternalEthernetPortEntry 37 }

msvmiepPortNumber OBJECT-TYPE
    SYNTAX     Integer32
    MAX-ACCESS read-only
    STATUS     current
    DESCRIPTION
        "NetworkPorts are often numbered relative to either
        a logical module or a network element."
    ::= { msvmInternalEthernetPortEntry 38 }

msvmiepPortType OBJECT-TYPE
    SYNTAX     INTEGER {
        unknown(0),
        other(1),
        notApplicable(2)
    }
    MAX-ACCESS read-only
    STATUS     current
    DESCRIPTION
        "PortType is defined to force consistent naming of
        the 'type' property in subclasses and to guarantee
        unique enum values for all instances of
        NetworkPort. When set to 1 ('Other'), related
        property OtherPortType contains a string
        description of the type of port. A range of values,
        DMTF_Reserved, has been defined that allows
        subclasses to override and define their specific
        types of ports."
    ::= { msvmInternalEthernetPortEntry 39 }

msvmiepPowerManagementCapability OBJECT-TYPE
    SYNTAX     INTEGER {
        unknown(0),
        notSupported(1),
        disabled(2),
        enabled(3),
        powerSavingModesEnteredAutomatic(4),
        powerStateSettable(5),
        powerCyclingSupported(6),
        timedPowerOnSupported(7)
    }
    MAX-ACCESS read-only
    STATUS     current
    DESCRIPTION
        "Note: The use of this property has been
        deprecated. Instead, use the PowerCapabilites
        property in an associated
        PowerManagementCapabilities class. Deprecated
        description: An enumerated array describing the
        power management capabilities of the Device."
    ::= { msvmInternalEthernetPortEntry 40 }

msvmiepPowerManagementSupported OBJECT-TYPE
    SYNTAX     TruthValue
    MAX-ACCESS read-only
    STATUS     current
    DESCRIPTION
        "Note: The use of this property has been
        deprecated. Instead, the existence of an associated
        PowerManagementCapabilities class (associated using
        the ElementCapabilities relationship) indicates
        that power management is supported. Deprecated
        description: Boolean that indicates that the Device
        can use power management."
    ::= { msvmInternalEthernetPortEntry 41 }

msvmiepPowerOnHours OBJECT-TYPE
    SYNTAX     Gauge32
    UNITS "Hours"
    MAX-ACCESS read-only
    STATUS     current
    DESCRIPTION
        "Note: The use of this method is deprecated. 
        Deprecated description: The number of consecutive
        hours that this Device has been powered on since
        its last power cycle."
    ::= { msvmInternalEthernetPortEntry 42 }

msvmiepRequestedSpeed OBJECT-TYPE
    SYNTAX     Gauge32
    UNITS "Bits per Second"
    MAX-ACCESS read-only
    STATUS     current
    DESCRIPTION
        "The requested bandwidth of the Port in Bits per
        Second. The actual bandwidth is reported in
        LogicalPort.Speed."
    ::= { msvmInternalEthernetPortEntry 43 }

msvmiepRequestedState OBJECT-TYPE
    SYNTAX     INTEGER {
        enabled(2),
        disabled(3),
        shutDown(4),
        noChange(5),
        offline(6),
        test(7),
        deferred(8),
        quiesce(9),
        reboot(10),
        reset(11),
        notApplicable(12)
    }
    MAX-ACCESS read-only
    STATUS     current
    DESCRIPTION
        "RequestedState is an integer enumeration that
        indicates the last requested or desired state for
        the element. The actual state of the element is
        represented by EnabledState. This property is
        provided to compare the last requested and current
        enabled or disabled states. Note that when
        EnabledState is set to 5 ('Not Applicable'), then
        this property has no meaning. By default, the
        RequestedState of the element is 5 ('No Change').
        Refer to the EnabledState property description for
        explanations of the values in the RequestedState
        enumeration. 
        
        It should be noted that there are two new values in
        RequestedState that build on the statuses of
        EnabledState. These are 'Reboot' (10) and 'Reset'
        (11). Reboot refers to doing a 'Shut Down' and then
        moving to an 'Enabled' state. Reset indicates that
        the element is first 'Disabled' and then 'Enabled'.
        The distinction between requesting 'Shut Down' and
        'Disabled' should also be noted. Shut Down requests
        an orderly transition to the Disabled state, and
        might involve removing power, to completely erase
        any existing state. The Disabled state requests an
        immediate disabling of the element, such that it
        will not execute or accept any commands or
        processing requests. 
        
        This property is set as the result of a method
        invocation (such as Start or StopService on
        CIM_Service), or can be overridden and defined as
        WRITEable in a subclass. The method approach is
        considered superior to a WRITEable property,
        because it allows an explicit invocation of the
        operation and the return of a result code. 
        
        A particular instance of EnabledLogicalElement
        might not support RequestedStateChange. If this
        occurs, the value 12 ('Not Applicable') is used."
    ::= { msvmInternalEthernetPortEntry 44 }

msvmiepSpeed OBJECT-TYPE
    SYNTAX     Gauge32
    UNITS "Bits per Second"
    MAX-ACCESS read-only
    STATUS     current
    DESCRIPTION
        "The bandwidth of the Port in Bits per Second."
    ::= { msvmInternalEthernetPortEntry 45 }

msvmiepStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmInternalEthernetPortEntry 46 }

msvmiepStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmInternalEthernetPortEntry 47 }

msvmiepStatusInfo OBJECT-TYPE
    SYNTAX     INTEGER {
        other(1),
        unknown(2),
        enabled(3),
        disabled(4),
        notApplicable(5)
    }
    MAX-ACCESS read-only
    STATUS     current
    DESCRIPTION
        "Note: The use of this method is deprecated in lieu
        of a more clearly named property (EnabledState)
        that is inherited from ManagedSystemElement and
        that has additional enumerated values. 
        Deprecated description: The StatusInfo property
        indicates whether the Logical Device is in an
        enabled state (value=3), disabled state (value=4),
        some other state (value=1), or an unknown state
        (value=2). If this property does not apply to the
        LogicalDevice, the value 5 ('Not Applicable')
        should be used. If a Device is
        ('Enabled')(value=3), it has been powered up and is
        configured and operational. The Device might or
        might not be functionally active, depending on
        whether its Availability (or
        AdditionalAvailability) indicates that it is
        ('Running/Full Power')(value=3) or ('Off line')
        (value=8). In an enabled but offline mode, a Device
        might be performing out-of-band requests, such as
        running Diagnostics. If StatusInfo is ('Disabled')
        (value=4), a Device can only be 'enabled' or
        powered off. In a personal computer environment,
        ('Disabled') means that the driver of the device is
        not available in the stack. In other environments,
        a Device can be disabled by removing its
        configuration file. A disabled device is physically
        present in a System and consuming resources, but it
        cannot be communicated with until a driver is
        loaded, a configuration file is loaded, or some
        other 'enabling' activity has occurred."
    ::= { msvmInternalEthernetPortEntry 48 }

msvmiepSupportMaxTransmissionUnt OBJECT-TYPE
    SYNTAX     Gauge32
    UNITS "Bytes"
    MAX-ACCESS read-only
    STATUS     current
    DESCRIPTION
        "The maximum transmission unit (MTU) that can be
        supported."
    ::= { msvmInternalEthernetPortEntry 49 }

msvmiepSystemCreationClassName OBJECT-TYPE
    SYNTAX     WtcsDisplayString (SIZE (0..256))
    MAX-ACCESS read-only
    STATUS     current
    DESCRIPTION
        "The CreationClassName of the scoping system."
    ::= { msvmInternalEthernetPortEntry 50 }

msvmiepSystemName OBJECT-TYPE
    SYNTAX     WtcsDisplayString (SIZE (0..256))
    MAX-ACCESS read-only
    STATUS     current
    DESCRIPTION
        "The System Name of the scoping system."
    ::= { msvmInternalEthernetPortEntry 51 }

msvmiepTimeOfLastStateChange OBJECT-TYPE
    SYNTAX     DateAndTime
    MAX-ACCESS read-only
    STATUS     current
    DESCRIPTION
        "The date or time when the EnabledState of the
        element last changed. If the state of the element
        has not changed and this property is populated,
        then it must be set to a 0 interval value. If a
        state change was requested, but rejected or not yet
        processed, the property must not be updated."
    ::= { msvmInternalEthernetPortEntry 52 }

msvmiepTotalPowerOnHours OBJECT-TYPE
    SYNTAX     Gauge32
    UNITS "Hours"
    MAX-ACCESS read-only
    STATUS     current
    DESCRIPTION
        "Note: The use of this method is deprecated. 
        Deprecated description: The total number of hours
        that this Device has been powered on."
    ::= { msvmInternalEthernetPortEntry 53 }

msvmiepUsageRestriction OBJECT-TYPE
    SYNTAX     INTEGER {
        unknown(0),
        frontendonly(2),
        backendonly(3),
        notrestricted(4)
    }
    MAX-ACCESS read-only
    STATUS     current
    DESCRIPTION
        "In some circumstances, a LogicalPort might be
        identifiable as a front end or back end port. An
        example of this situation would be a storage array
        that might have back end ports to communicate with
        disk drives and front end ports to communicate with
        hosts. If there is no restriction on the use of the
        port, then the value should be set to 'not
        restricted'."
    ::= { msvmInternalEthernetPortEntry 54 }

msvmLANEndpointTable OBJECT-TYPE
    SYNTAX     SEQUENCE OF MsvmLANEndpoint
    MAX-ACCESS not-accessible
    STATUS     current
    DESCRIPTION
        "Represents the logical connection point for a
        network adapter. When the LAN endpoint is connected
        to a switch port, the network adapter connected to
        the LAN endpoint has network connectivity."
    ::= { msvmNetworking 10 }

msvmLANEndpointEntry OBJECT-TYPE
    SYNTAX     MsvmLANEndpoint
    MAX-ACCESS not-accessible
    STATUS     current
    DESCRIPTION
        "None"
    INDEX      { msvmleIndex }
    ::= { msvmLANEndpointTable 1 }

MsvmLANEndpoint ::= SEQUENCE {
    msvmleIndex Integer32,
    msvmleAliasAddresses WtcsDisplayString,
    msvmleBroadcastResetSupported TruthValue,
    msvmleCaption WtcsDisplayString,
    msvmleConnected TruthValue,
    msvmleCreationClassName WtcsDisplayString,
    msvmleDescription WtcsDisplayString,
    msvmleElementName WtcsDisplayString,
    msvmleEnabledDefault INTEGER,
    msvmleEnabledState INTEGER,
    msvmleGroupAddresses WtcsDisplayString,
    msvmleHealthState INTEGER,
    msvmleInstallDate DateAndTime,
    msvmleLANID WtcsDisplayString,
    msvmleLANType INTEGER,
    msvmleMACAddress WtcsDisplayString,
    msvmleMaxDataSize Gauge32,
    msvmleName WtcsDisplayString,
    msvmleNameFormat WtcsDisplayString,
    msvmleOperationalStatus INTEGER,
    msvmleOtherEnabledState WtcsDisplayString,
    msvmleOtherLANType WtcsDisplayString,
    msvmleOtherTypeDescription WtcsDisplayString,
    msvmleProtocolIFType Integer32,
    msvmleProtocolType INTEGER,
    msvmleRequestedState INTEGER,
    msvmleStatus WtcsDisplayString,
    msvmleStatusDescriptions WtcsDisplayString,
    msvmleSystemCreationClassName WtcsDisplayString,
    msvmleSystemName WtcsDisplayString,
    msvmleTimeOfLastStateChange DateAndTime
}

msvmleIndex OBJECT-TYPE
    SYNTAX     Integer32 (1..2147483647)
    MAX-ACCESS read-only
    STATUS     current
    DESCRIPTION
        "The value of this object uniquely identifies the
        instance entry for this class."
    ::= { msvmLANEndpointEntry 1 }

msvmleAliasAddresses OBJECT-TYPE
    SYNTAX     WtcsDisplayString
    MAX-ACCESS read-only
    STATUS     current
    DESCRIPTION
        "Other unicast addresses that may be used to
        communicate with the LANEndpoint."
    ::= { msvmLANEndpointEntry 2 }

msvmleBroadcastResetSupported OBJECT-TYPE
    SYNTAX     TruthValue
    MAX-ACCESS read-only
    STATUS     current
    DESCRIPTION
        "A boolean indicating whether the instrumentation
        supports the BroadcastReset method."
    ::= { msvmLANEndpointEntry 3 }

msvmleCaption OBJECT-TYPE
    SYNTAX     WtcsDisplayString (SIZE (0..64))
    MAX-ACCESS read-only
    STATUS     current
    DESCRIPTION
        "The Caption property is a short textual
        description (one- line string) of the object."
    ::= { msvmLANEndpointEntry 4 }

msvmleConnected OBJECT-TYPE
    SYNTAX     TruthValue
    MAX-ACCESS read-only
    STATUS     current
    DESCRIPTION
        "This property is inherited from CIM_LANEndPoint
        and is always set to True if connected to a switch
        port."
    ::= { msvmLANEndpointEntry 5 }

msvmleCreationClassName OBJECT-TYPE
    SYNTAX     WtcsDisplayString (SIZE (0..256))
    MAX-ACCESS read-only
    STATUS     current
    DESCRIPTION
        "CreationClassName indicates the name of the class
        or the subclass used in the creation of an
        instance. When used with the other key properties
        of this class, this property allows all instances
        of this class and its subclasses to be uniquely
        identified."
    ::= { msvmLANEndpointEntry 6 }

msvmleDescription OBJECT-TYPE
    SYNTAX     WtcsDisplayString
    MAX-ACCESS read-only
    STATUS     current
    DESCRIPTION
        "The Description property provides a textual
        description of the object."
    ::= { msvmLANEndpointEntry 7 }

msvmleElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmLANEndpointEntry 8 }

msvmleEnabledDefault OBJECT-TYPE
    SYNTAX     INTEGER {
        enabled(2),
        disabled(3),
        notApplicable(5),
        enabledbutOffline(6),
        noDefault(7)
    }
    MAX-ACCESS read-only
    STATUS     current
    DESCRIPTION
        "An enumerated value indicating an administrator's
        default or startup configuration for the Enabled
        State of an element. By default, the element is
        'Enabled' (value=2)."
    ::= { msvmLANEndpointEntry 9 }

msvmleEnabledState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "EnabledState is an integer enumeration that
        indicates the enabled and disabled states of an
        element. It can also indicate the transitions
        between these requested states. For example,
        shutting down (value=4) and starting (value=10) are
        transient states between enabled and disabled. The
        following text briefly summarizes the various
        enabled and disabled states: 
        Enabled (2) indicates that the element is or could
        be executing commands, will process any queued
        commands, and queues new requests. 
        Disabled (3) indicates that the element will not
        execute commands and will drop any new requests. 
        Shutting Down (4) indicates that the element is in
        the process of going to a Disabled state. 
        Not Applicable (5) indicates the element does not
        support being enabled or disabled. 
        Enabled but Offline (6) indicates that the element
        might be completing commands, and will drop any new
        requests. 
        Test (7) indicates that the element is in a test
        state. 
        Deferred (8) indicates that the element might be
        completing commands, but will queue any new
        requests. 
        Quiesce (9) indicates that the element is enabled
        but in a restricted mode. The behavior of the
        element is similar to the Enabled state, but it
        processes only a restricted set of commands. All
        other requests are queued. 
        Starting (10) indicates that the element is in the
        process of going to an Enabled state. New requests
        are queued."
    ::= { msvmLANEndpointEntry 10 }

msvmleGroupAddresses OBJECT-TYPE
    SYNTAX     WtcsDisplayString
    MAX-ACCESS read-only
    STATUS     current
    DESCRIPTION
        "Multicast addresses to which the LANEndpoint
        listens."
    ::= { msvmLANEndpointEntry 11 }

msvmleHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmLANEndpointEntry 12 }

msvmleInstallDate OBJECT-TYPE
    SYNTAX     DateAndTime
    MAX-ACCESS read-only
    STATUS     current
    DESCRIPTION
        "A datetime value that indicates when the object
        was installed. Lack of a value does not indicate
        that the object is not installed."
    ::= { msvmLANEndpointEntry 13 }

msvmleLANID OBJECT-TYPE
    SYNTAX     WtcsDisplayString
    MAX-ACCESS read-only
    STATUS     current
    DESCRIPTION
        "A label or identifier for the LAN Segment to which
        the Endpoint is connected. If the Endpoint is not
        currently active/connected or this information is
        not known, then LANID is NULL."
    ::= { msvmLANEndpointEntry 14 }

msvmleLANType OBJECT-TYPE
    SYNTAX     INTEGER {
        unknown(0),
        other(1),
        ethernet(2),
        tokenRing(3),
        fddi(4)
    }
    MAX-ACCESS read-only
    STATUS     current
    DESCRIPTION
        "An indication of the kind of technology used on
        the LAN. This property is deprecated in lieu of
        ProtocolType, which is an enumeration inherited
        from ProtocolEndpoint and which includes the Values
        specified here."
    ::= { msvmLANEndpointEntry 15 }

msvmleMACAddress OBJECT-TYPE
    SYNTAX     WtcsDisplayString (SIZE (0..12))
    MAX-ACCESS read-only
    STATUS     current
    DESCRIPTION
        "The principal unicast address used in
        communication with the LANEndpoint. The MAC address
        is formatted as twelve hexadecimal digits (e.g.,
        '010203040506'), with each pair representing one of
        the six octets of the MAC address in 'canonical'
        bit order according to RFC 2469."
    ::= { msvmLANEndpointEntry 16 }

msvmleMaxDataSize OBJECT-TYPE
    SYNTAX     Gauge32
    UNITS "Bits"
    MAX-ACCESS read-only
    STATUS     current
    DESCRIPTION
        "The largest information field that may be sent or
        received by the LANEndpoint."
    ::= { msvmLANEndpointEntry 17 }

msvmleName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmLANEndpointEntry 18 }

msvmleNameFormat OBJECT-TYPE
    SYNTAX     WtcsDisplayString (SIZE (0..256))
    MAX-ACCESS read-only
    STATUS     current
    DESCRIPTION
        "NameFormat contains the naming heuristic that is
        selected to ensure that the value of the Name
        property is unique. For example, you might choose
        to prepend the name of the port or interface with
        the Type of ProtocolEndpoint (for example, IPv4) of
        this instance followed by an underscore."
    ::= { msvmLANEndpointEntry 19 }

msvmleOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmLANEndpointEntry 20 }

msvmleOtherEnabledState OBJECT-TYPE
    SYNTAX     WtcsDisplayString
    MAX-ACCESS read-only
    STATUS     current
    DESCRIPTION
        "A string that describes the enabled or disabled
        state of the element when the EnabledState property
        is set to 1 ('Other'). This property must be set to
        null when EnabledState is any value other than 1."
    ::= { msvmLANEndpointEntry 21 }

msvmleOtherLANType OBJECT-TYPE
    SYNTAX     WtcsDisplayString
    MAX-ACCESS read-only
    STATUS     current
    DESCRIPTION
        "A free-form string that describes the type of
        technology used on the LAN when the value of the
        LANType property is equal to 1 (i.e., 'Other').
        This property is deprecated since its purpose
        overlaps with OtherTypeDescription, which which is
        inherited from ProtocolEndpoint."
    ::= { msvmLANEndpointEntry 22 }

msvmleOtherTypeDescription OBJECT-TYPE
    SYNTAX     WtcsDisplayString (SIZE (0..64))
    MAX-ACCESS read-only
    STATUS     current
    DESCRIPTION
        "A string that describes the type of
        ProtocolEndpoint when the Type property of this
        class (or any of its subclasses) is set to 1
        (Other). This property should be set to null when
        the Type property is any value other than 1."
    ::= { msvmLANEndpointEntry 23 }

msvmleProtocolIFType OBJECT-TYPE
    SYNTAX     Integer32
    MAX-ACCESS read-only
    STATUS     current
    DESCRIPTION
        "ProtocolIFType is an enumeration that is
        synchronized with the IANA ifType MIB. The ifType
        MIB is maintained at the URL,
        http://www.iana.org/assignments/ianaiftype-mib.
        Also, additional values defined by the DMTF are
        included. The property is used to categorize and
        classify instances of the ProtocolEndpoint class.
        Note that if the ProtocolIFType is set to 1
        (Other), then the type information should be
        provided in the OtherTypeDescription string
        property."
    ::= { msvmLANEndpointEntry 24 }

msvmleProtocolType OBJECT-TYPE
    SYNTAX     INTEGER {
        unknown(0),
        other(1),
        ipv4(2),
        ipv6(3),
        ipx(4),
        appleTalk(5),
        decnet(6),
        sna(7),
        conp(8),
        clnp(9),
        vines(10),
        xns(11),
        atm(12),
        frameRelay(13),
        ethernet(14),
        tokenRing(15),
        fddi(16),
        infiniband(17),
        fibreChannel(18),
        isdnBRIEndpoint(19),
        isdnBChannelEndpoint(20),
        isdnDChannelEndpoint(21),
        ipv4v6(22),
        bgp(23),
        ospf(24),
        mpls(25),
        udp(26),
        tcp(27)
    }
    MAX-ACCESS read-only
    STATUS     current
    DESCRIPTION
        "Note: This property is deprecated in lieu of the
        ProtocolIFType enumeration. This deprecation was
        done to have better alignment between the IF-MIB of
        the IETF and this CIM class. 
        Deprecated description: ProtocolType is an
        enumeration that provides information to categorize
        and classify different instances of this class. For
        most instances, information in this enumeration and
        the definition of the subclass overlap. However,
        there are several cases where a specific subclass
        of ProtocolEndpoint is not required (for example,
        there is no Fibre Channel subclass of
        ProtocolEndpoint). Therefore, this property is
        needed to define the type of Endpoint."
    ::= { msvmLANEndpointEntry 25 }

msvmleRequestedState OBJECT-TYPE
    SYNTAX     INTEGER {
        enabled(2),
        disabled(3),
        shutDown(4),
        noChange(5),
        offline(6),
        test(7),
        deferred(8),
        quiesce(9),
        reboot(10),
        reset(11),
        notApplicable(12)
    }
    MAX-ACCESS read-only
    STATUS     current
    DESCRIPTION
        "RequestedState is an integer enumeration that
        indicates the last requested or desired state for
        the element. The actual state of the element is
        represented by EnabledState. This property is
        provided to compare the last requested and current
        enabled or disabled states. Note that when
        EnabledState is set to 5 ('Not Applicable'), then
        this property has no meaning. By default, the
        RequestedState of the element is 5 ('No Change').
        Refer to the EnabledState property description for
        explanations of the values in the RequestedState
        enumeration. 
        
        It should be noted that there are two new values in
        RequestedState that build on the statuses of
        EnabledState. These are 'Reboot' (10) and 'Reset'
        (11). Reboot refers to doing a 'Shut Down' and then
        moving to an 'Enabled' state. Reset indicates that
        the element is first 'Disabled' and then 'Enabled'.
        The distinction between requesting 'Shut Down' and
        'Disabled' should also be noted. Shut Down requests
        an orderly transition to the Disabled state, and
        might involve removing power, to completely erase
        any existing state. The Disabled state requests an
        immediate disabling of the element, such that it
        will not execute or accept any commands or
        processing requests. 
        
        This property is set as the result of a method
        invocation (such as Start or StopService on
        CIM_Service), or can be overridden and defined as
        WRITEable in a subclass. The method approach is
        considered superior to a WRITEable property,
        because it allows an explicit invocation of the
        operation and the return of a result code. 
        
        A particular instance of EnabledLogicalElement
        might not support RequestedStateChange. If this
        occurs, the value 12 ('Not Applicable') is used."
    ::= { msvmLANEndpointEntry 26 }

msvmleStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmLANEndpointEntry 27 }

msvmleStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmLANEndpointEntry 28 }

msvmleSystemCreationClassName OBJECT-TYPE
    SYNTAX     WtcsDisplayString (SIZE (0..256))
    MAX-ACCESS read-only
    STATUS     current
    DESCRIPTION
        "The CreationClassName of the scoping System."
    ::= { msvmLANEndpointEntry 29 }

msvmleSystemName OBJECT-TYPE
    SYNTAX     WtcsDisplayString (SIZE (0..256))
    MAX-ACCESS read-only
    STATUS     current
    DESCRIPTION
        "The Name of the scoping System."
    ::= { msvmLANEndpointEntry 30 }

msvmleTimeOfLastStateChange OBJECT-TYPE
    SYNTAX     DateAndTime
    MAX-ACCESS read-only
    STATUS     current
    DESCRIPTION
        "The date or time when the EnabledState of the
        element last changed. If the state of the element
        has not changed and this property is populated,
        then it must be set to a 0 interval value. If a
        state change was requested, but rejected or not yet
        processed, the property must not be updated."
    ::= { msvmLANEndpointEntry 31 }

msvmNetworkElementSetDataTable OBJECT-TYPE
    SYNTAX     SEQUENCE OF MsvmNetworkElementSettingData
    MAX-ACCESS not-accessible
    STATUS     current
    DESCRIPTION
        "The Msvm_NetworkElementSettingData association
        class logically connects the virtual system with
        the various LAN endpoints scoped by the virtual
        system."
    ::= { msvmNetworking 11 }

msvmNetworkElementSetDataEntry OBJECT-TYPE
    SYNTAX     MsvmNetworkElementSettingData
    MAX-ACCESS not-accessible
    STATUS     current
    DESCRIPTION
        "None"
    INDEX      { msvmnesdIndex }
    ::= { msvmNetworkElementSetDataTable 1 }

MsvmNetworkElementSettingData ::= SEQUENCE {
    msvmnesdIndex Integer32,
    msvmnesdIsCurrent INTEGER,
    msvmnesdIsDefault INTEGER,
    msvmnesdIsMaximum INTEGER,
    msvmnesdIsMinimum INTEGER,
    msvmnesdIsNext INTEGER,
    msvmnesdManagedElement WtcsDisplayString,
    msvmnesdSettingData WtcsDisplayString
}

msvmnesdIndex OBJECT-TYPE
    SYNTAX     Integer32 (1..2147483647)
    MAX-ACCESS read-only
    STATUS     current
    DESCRIPTION
        "The value of this object uniquely identifies the
        instance entry for this class."
    ::= { msvmNetworkElementSetDataEntry 1 }

msvmnesdIsCurrent OBJECT-TYPE
    SYNTAX     INTEGER {
        unknown(0),
        isCurrent(1),
        isNotCurrent(2)
    }
    MAX-ACCESS read-only
    STATUS     current
    DESCRIPTION
        "An enumerated integer that indicates that the
        referenced setting is currently being used in the
        operation of the element or that this information
        is unknown. 
        For a given ManagedElement and all instances of a
        SettingData subclass, there shall be at most one
        instance of ElementSettingData which references the
        ManagedElement and an instance of the SettingData
        sub-class where there is a specified non-null,
        non-key property of the SettingData sub-class, and
        the IsMaximum property on the referencing
        ElementSettingData instance has a value of 'Is
        Maximum' or the IsMinimum property on the
        referencing ElementSettingData instance has a value
        of 'Is Minimum' and the IsCurrent property on the
        referencing ElementSettingData instance has a value
        of 'Is Current'. There shall be at most one
        instance of ElementSettingData which references a
        ManagedElement and an instance of a SettingData
        sub-class where the IsCurrent property has a value
        of 'Is Current' and the IsMinimum property does not
        have a value of 'Is Minimum' and the IsMaximum
        property does not have a value of 'Is Maximum'."
    ::= { msvmNetworkElementSetDataEntry 2 }

msvmnesdIsDefault OBJECT-TYPE
    SYNTAX     INTEGER {
        unknown(0),
        isDefault(1),
        isNotDefault(2)
    }
    MAX-ACCESS read-only
    STATUS     current
    DESCRIPTION
        "An enumerated integer that indicates that the
        referenced setting is a default setting for the
        element or that this information is unknown."
    ::= { msvmNetworkElementSetDataEntry 3 }

msvmnesdIsMaximum OBJECT-TYPE
    SYNTAX     INTEGER {
        unknown(0),
        notApplicable(1),
        isMaximum(2),
        isNotMaximum(3)
    }
    MAX-ACCESS read-only
    STATUS     current
    DESCRIPTION
        "This property affects the interpretation of all
        non-null, non-enumerated, non-binary, numeric,
        non-key properties of the associated SettingData
        instance. All other properties of the associated
        SettingData instance are not affected by this
        property. 
        Note: It is assumed that the semantics of each
        property of this set are designed to be compared
        mathematically. 
        When IsMaximum = 'Is Maxiumum', this property
        indicates that the affected property values
        specified in the associated SettingData instance
        shall define maximum setting values. 
        When IsMaximum = 'Is Not Maxiumum', this property
        indicates that the affected property values
        specified in the associated SettingData instance
        shall not define maximum setting values. 
        When IsMaximum = 'Unknown', this property indicates
        that the affected property values specified in the
        associated SettingData instance may correspond to
        maximum setting values. 
        When IsMaximum = 'Not Applicable', this property
        indicates that the affected property values
        specified in the associated SettingData instance
        shall not be interpreted with respect to whether
        each defines a maximum."
    ::= { msvmNetworkElementSetDataEntry 4 }

msvmnesdIsMinimum OBJECT-TYPE
    SYNTAX     INTEGER {
        unknown(0),
        notApplicable(1),
        isMinimum(2),
        isNotMinimum(3)
    }
    MAX-ACCESS read-only
    STATUS     current
    DESCRIPTION
        "This property affects the interpretation of all
        non-null, non-enumerated, non-binary, numeric,
        non-key properties of the associated SettingData
        instance. All other properties of the associated
        SettingData instance are not affected by this
        property. 
        Note: It is assumed that the semantics of each
        property of this set are designed to be compared
        mathematically. 
        When IsMinimum = 'Is Miniumum', this property
        indicates that the affected property values
        specified in the associated SettingData instance
        shall define minimum setting values. 
        When IsMinimum = 'Is Not Miniumum', this property
        indicates that the affected property values
        specified in the associated SettingData instance
        shall not define minimum setting values. 
        When IsMinimum = 'Unknown', this property indicates
        that the affected property values specified in the
        associated SettingData instance may correspond to
        minimum setting values. 
        When IsMinimum = 'Not Applicable', this property
        indicates that the affected property values
        specified in the associated SettingData instance
        shall not be interpreted with respect to whether
        each defines a minimum."
    ::= { msvmNetworkElementSetDataEntry 5 }

msvmnesdIsNext OBJECT-TYPE
    SYNTAX     INTEGER {
        unknown(0),
        isNext(1),
        isNotNext(2),
        isNextForSingleUse(3)
    }
    MAX-ACCESS read-only
    STATUS     current
    DESCRIPTION
        "An enumerated integer indicating whether or not
        the referenced setting is the next setting to be
        applied. For example, the application could take
        place on a re-initialization, reset,
        reconfiguration request. This could be a permanent
        setting, or a setting used only one time, as
        indicated by the flag. If it is a permanent setting
        then the setting is applied every time the managed
        element reinitializes, until this flag is manually
        reset. However, if it is single use, then the flag
        is automatically cleared after the settings are
        applied. Also note that if this flag is specified
        (i.e. set to value other than 'Unknown'), then this
        takes precedence over any SettingData that may have
        been specified as Default. For example: If the
        managed element is a computer system, and the value
        of this flag is 'Is Next', then the setting will be
        effective next time the system resets. And, unless
        this flag is changed, it will persist for
        subsequent system resets. However, if this flag is
        set to 'Is Next For Single Use', then this setting
        will only be used once and the flag would be reset
        after that to 'Is Not Next'. So, in the above
        example, if the system reboots in a quick
        succession, the setting will not be used at the
        second reboot."
    ::= { msvmNetworkElementSetDataEntry 6 }

msvmnesdManagedElement OBJECT-TYPE
    SYNTAX     WtcsDisplayString
    MAX-ACCESS read-only
    STATUS     current
    DESCRIPTION
        "The managed element."
    ::= { msvmNetworkElementSetDataEntry 7 }

msvmnesdSettingData OBJECT-TYPE
    SYNTAX     WtcsDisplayString
    MAX-ACCESS read-only
    STATUS     current
    DESCRIPTION
        "The SettingData object that is associated with the
        element."
    ::= { msvmNetworkElementSetDataEntry 8 }

msvmNetworkJobTable OBJECT-TYPE
    SYNTAX     SEQUENCE OF MsvmNetworkJob
    MAX-ACCESS not-accessible
    STATUS     current
    DESCRIPTION
        "This class represents a network operation job
        created by the Network VSP WMI management service."
    ::= { msvmNetworking 12 }

msvmNetworkJobEntry OBJECT-TYPE
    SYNTAX     MsvmNetworkJob
    MAX-ACCESS not-accessible
    STATUS     current
    DESCRIPTION
        "None"
    INDEX      { msvmnjIndex }
    ::= { msvmNetworkJobTable 1 }

MsvmNetworkJob ::= SEQUENCE {
    msvmnjIndex Integer32,
    msvmnjCaption WtcsDisplayString,
    msvmnjCreateInternalEthernetPort WtcsDisplayString,
    msvmnjDeleteOnCompletion TruthValue,
    msvmnjDescription WtcsDisplayString,
    msvmnjElapsedTime DateAndTime,
    msvmnjElementName WtcsDisplayString,
    msvmnjErrorCode Integer32,
    msvmnjErrorDescription WtcsDisplayString,
    msvmnjErrorSummaryDescription WtcsDisplayString,
    msvmnjHealthState INTEGER,
    msvmnjHresult Gauge32,
    msvmnjInstallDate DateAndTime,
    msvmnjInstanceID WtcsDisplayString,
    msvmnjJobRunTimes Gauge32,
    msvmnjJobState INTEGER,
    msvmnjJobStatus WtcsDisplayString,
    msvmnjLocalOrUtcTime INTEGER,
    msvmnjName WtcsDisplayString,
    msvmnjNetworkJobType INTEGER,
    msvmnjNotify WtcsDisplayString,
    msvmnjOperationalStatus INTEGER,
    msvmnjOtherRecoveryAction WtcsDisplayString,
    msvmnjOwner WtcsDisplayString,
    msvmnjPercentComplete Integer32,
    msvmnjPriority Gauge32,
    msvmnjRecoveryAction INTEGER,
    msvmnjRunDay Integer32,
    msvmnjRunDayOfWeek Integer32,
    msvmnjRunMonth INTEGER,
    msvmnjRunStartInterval DateAndTime,
    msvmnjScheduledStartTime DateAndTime,
    msvmnjStartTime DateAndTime,
    msvmnjStatus WtcsDisplayString,
    msvmnjStatusDescriptions WtcsDisplayString,
    msvmnjTimeBeforeRemoval DateAndTime,
    msvmnjTimeOfLastStateChange DateAndTime,
    msvmnjTimeSubmitted DateAndTime,
    msvmnjUntilTime DateAndTime
}

msvmnjIndex OBJECT-TYPE
    SYNTAX     Integer32 (1..2147483647)
    MAX-ACCESS read-only
    STATUS     current
    DESCRIPTION
        "The value of this object uniquely identifies the
        instance entry for this class."
    ::= { msvmNetworkJobEntry 1 }

msvmnjCaption OBJECT-TYPE
    SYNTAX     WtcsDisplayString (SIZE (0..64))
    MAX-ACCESS read-only
    STATUS     current
    DESCRIPTION
        "The Caption property is a short textual
        description (one- line string) of the object."
    ::= { msvmNetworkJobEntry 2 }

msvmnjCreateInternalEthernetPort OBJECT-TYPE
    SYNTAX     WtcsDisplayString
    MAX-ACCESS read-only
    STATUS     current
    DESCRIPTION
        "The NvspWmiJobTypeSetupSwitch job will create a
        Msvm_InternalEthernetPort as a part of the job.
        This property can be used to find the reference to
        the created Ethernet port."
    ::= { msvmNetworkJobEntry 3 }

msvmnjDeleteOnCompletion OBJECT-TYPE
    SYNTAX     TruthValue
    MAX-ACCESS read-only
    STATUS     current
    DESCRIPTION
        "Indicates whether or not the job should be
        automatically deleted upon completion. Note that
        the 'completion' of a recurring job is defined by
        its JobRunTimes or UntilTime properties, or when
        the Job is terminated by manual intervention. If
        this property is set to false and the job
        completes, then the extrinsic method DeleteInstance
        must be used to delete the job instead of updating
        this property."
    ::= { msvmNetworkJobEntry 4 }

msvmnjDescription OBJECT-TYPE
    SYNTAX     WtcsDisplayString
    MAX-ACCESS read-only
    STATUS     current
    DESCRIPTION
        "The Description property provides a textual
        description of the object."
    ::= { msvmNetworkJobEntry 5 }

msvmnjElapsedTime OBJECT-TYPE
    SYNTAX     DateAndTime
    MAX-ACCESS read-only
    STATUS     current
    DESCRIPTION
        "The time interval that the Job has been executing
        or the total execution time if the Job is complete.
        Note that this property is also present in the
        JobProcessingStatistics class. This class is
        necessary to capture the processing information for
        recurring Jobs, because only the 'last' run time
        can be stored in this single-valued property."
    ::= { msvmNetworkJobEntry 6 }

msvmnjElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmNetworkJobEntry 7 }

msvmnjErrorCode OBJECT-TYPE
    SYNTAX     Integer32
    MAX-ACCESS read-only
    STATUS     current
    DESCRIPTION
        "A vendor-specific error code. The value must be
        set to zero if the Job completed without error.
        Note that this property is also present in the
        JobProcessingStatistics class. This class is
        necessary to capture the processing information for
        recurring Jobs, because only the 'last' run error
        can be stored in this single-valued property."
    ::= { msvmNetworkJobEntry 8 }

msvmnjErrorDescription OBJECT-TYPE
    SYNTAX     WtcsDisplayString
    MAX-ACCESS read-only
    STATUS     current
    DESCRIPTION
        "A free-form string that contains the vendor error
        description. Note that this property is also
        present in the JobProcessingStatistics class. This
        class is necessary to capture the processing
        information for recurring Jobs, because only the
        'last' run error can be stored in this
        single-valued property."
    ::= { msvmNetworkJobEntry 9 }

msvmnjErrorSummaryDescription OBJECT-TYPE
    SYNTAX     WtcsDisplayString
    MAX-ACCESS read-only
    STATUS     current
    DESCRIPTION
        "A free-form string that contains the vendor
        summary error description. Note that this property
        is also present in the JobProcessingStatistics
        class. This class is necessary to capture the
        processing information for recurring Jobs, because
        only the 'last' run error can be stored in this
        single-valued property."
    ::= { msvmNetworkJobEntry 10 }

msvmnjHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmNetworkJobEntry 11 }

msvmnjHresult OBJECT-TYPE
    SYNTAX     Gauge32
    MAX-ACCESS read-only
    STATUS     current
    DESCRIPTION
        "The completion status of the job."
    ::= { msvmNetworkJobEntry 12 }

msvmnjInstallDate OBJECT-TYPE
    SYNTAX     DateAndTime
    MAX-ACCESS read-only
    STATUS     current
    DESCRIPTION
        "A datetime value that indicates when the object
        was installed. Lack of a value does not indicate
        that the object is not installed."
    ::= { msvmNetworkJobEntry 13 }

msvmnjInstanceID OBJECT-TYPE
    SYNTAX     WtcsDisplayString
    MAX-ACCESS read-only
    STATUS     current
    DESCRIPTION
        "Within the scope of the instantiating Namespace,
        InstanceID opaquely and uniquely identifies an
        instance of this class. In order to ensure
        uniqueness within the NameSpace, the value of
        InstanceID SHOULD be constructed using the
        following 'preferred' algorithm: 
        <OrgID>:<LocalID> 
        Where <OrgID> and <LocalID> are separated by a
        colon ':', and where <OrgID> must include a
        copyrighted, trademarked or otherwise unique name
        that is owned by the business entity that is
        creating or defining the InstanceID, or that is a
        registered ID that is assigned to the business
        entity by a recognized global authority. (This
        requirement is similar to the <Schema Name>_<Class
        Name> structure of Schema class names.) In
        addition, to ensure uniqueness <OrgID> must not
        contain a colon (':'). When using this algorithm,
        the first colon to appear in InstanceID must appear
        between <OrgID> and <LocalID>. 
        <LocalID> is chosen by the business entity and
        should not be re-used to identify different
        underlying (real-world) elements. If the above
        'preferred' algorithm is not used, the defining
        entity must assure that the resulting InstanceID is
        not re-used across any InstanceIDs produced by this
        or other providers for the NameSpace of this
        instance. 
        For DMTF defined instances, the 'preferred'
        algorithm must be used with the <OrgID> set to
        'CIM'."
    ::= { msvmNetworkJobEntry 14 }

msvmnjJobRunTimes OBJECT-TYPE
    SYNTAX     Gauge32
    MAX-ACCESS read-only
    STATUS     current
    DESCRIPTION
        "The number of times that the Job should be run. A
        value of 1 indicates that the Job is not recurring,
        while any non-zero value indicates a limit to the
        number of times that the Job will recur. Zero
        indicates that there is no limit to the number of
        times that the Job can be processed, but that it is
        terminated either after the UntilTime or by manual
        intervention. By default, a Job is processed once."
    ::= { msvmNetworkJobEntry 15 }

msvmnjJobState OBJECT-TYPE
    SYNTAX     INTEGER {
        new(2),
        starting(3),
        running(4),
        suspended(5),
        shuttingDown(6),
        completed(7),
        terminated(8),
        killed(9),
        exception(10),
        service(11)
    }
    MAX-ACCESS read-only
    STATUS     current
    DESCRIPTION
        "JobState is an integer enumeration that indicates
        the operational state of a Job. It can also
        indicate transitions between these states, for
        example, 'Shutting Down' and 'Starting'. Following
        is a brief description of the states: 
        New (2) indicates that the job has never been
        started. 
        Starting (3) indicates that the job is moving from
        the 'New', 'Suspended', or 'Service' states into
        the 'Running' state. 
        Running (4) indicates that the Job is running. 
        Suspended (5) indicates that the Job is stopped,
        but can be restarted in a seamless manner. 
        Shutting Down (6) indicates that the job is moving
        to a 'Completed', 'Terminated', or 'Killed' state. 
        Completed (7) indicates that the job has completed
        normally. 
        Terminated (8) indicates that the job has been
        stopped by a 'Terminate' state change request. The
        job and all its underlying processes are ended and
        can be restarted (this is job-specific) only as a
        new job. 
        Killed (9) indicates that the job has been stopped
        by a 'Kill' state change request. Underlying
        processes might have been left running, and cleanup
        might be required to free up resources. 
        Exception (10) indicates that the Job is in an
        abnormal state that might be indicative of an error
        condition. Actual status might be displayed though
        job-specific objects. 
        Service (11) indicates that the Job is in a
        vendor-specific state that supports problem
        discovery, or resolution, or both."
    ::= { msvmNetworkJobEntry 16 }

msvmnjJobStatus OBJECT-TYPE
    SYNTAX     WtcsDisplayString
    MAX-ACCESS read-only
    STATUS     current
    DESCRIPTION
        "A free-form string that represents the status of
        the job. The primary status is reflected in the
        inherited OperationalStatus property. JobStatus
        provides additional, implementation-specific
        details."
    ::= { msvmNetworkJobEntry 17 }

msvmnjLocalOrUtcTime OBJECT-TYPE
    SYNTAX     INTEGER {
        localTime(1),
        utcTime(2)
    }
    MAX-ACCESS read-only
    STATUS     current
    DESCRIPTION
        "This property indicates whether the times
        represented in the RunStartInterval and UntilTime
        properties represent local times or UTC times. Time
        values are synchronized worldwide by using the
        enumeration value 2, 'UTC Time'."
    ::= { msvmNetworkJobEntry 18 }

msvmnjName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmNetworkJobEntry 19 }

msvmnjNetworkJobType OBJECT-TYPE
    SYNTAX     INTEGER {
        nvspWmiJobTypeInvalid(0),
        nvspWmiJobTypeSetupSwitch(1),
        nvspWmiJobTypeTeardownSwitch(2)
    }
    MAX-ACCESS read-only
    STATUS     current
    DESCRIPTION
        "The type of job."
    ::= { msvmNetworkJobEntry 20 }

msvmnjNotify OBJECT-TYPE
    SYNTAX     WtcsDisplayString
    MAX-ACCESS read-only
    STATUS     current
    DESCRIPTION
        "The User who is to be notified upon the Job
        completion or failure."
    ::= { msvmNetworkJobEntry 21 }

msvmnjOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmNetworkJobEntry 22 }

msvmnjOtherRecoveryAction OBJECT-TYPE
    SYNTAX     WtcsDisplayString
    MAX-ACCESS read-only
    STATUS     current
    DESCRIPTION
        "A string describing the recovery action when the
        RecoveryAction property of the instance is 1
        ('Other')."
    ::= { msvmNetworkJobEntry 23 }

msvmnjOwner OBJECT-TYPE
    SYNTAX     WtcsDisplayString
    MAX-ACCESS read-only
    STATUS     current
    DESCRIPTION
        "The User that submitted the Job, or the Service or
        method name that caused the job to be created."
    ::= { msvmNetworkJobEntry 24 }

msvmnjPercentComplete OBJECT-TYPE
    SYNTAX     Integer32
    UNITS "Percent"
    MAX-ACCESS read-only
    STATUS     current
    DESCRIPTION
        "The percentage of the job that has completed at
        the time that this value is requested. Note that
        this property is also present in the
        JobProcessingStatistics class. This class is
        necessary to capture the processing information for
        recurring Jobs, because only the 'last' run data
        can be stored in this single-valued property. 
        Note that the value 101 is undefined and will be
        not be allowed in the next major revision of the
        specification."
    ::= { msvmNetworkJobEntry 25 }

msvmnjPriority OBJECT-TYPE
    SYNTAX     Gauge32
    MAX-ACCESS read-only
    STATUS     current
    DESCRIPTION
        "Indicates the urgency or importance of execution
        of the Job. The lower the number, the higher the
        priority. Note that this property is also present
        in the JobProcessingStatistics class. This class is
        necessary to capture the setting information that
        would influence the results of a job."
    ::= { msvmNetworkJobEntry 26 }

msvmnjRecoveryAction OBJECT-TYPE
    SYNTAX     INTEGER {
        unknown(0),
        other(1),
        doNotContinue(2),
        continueWithNextJob(3),
        rerunJob(4),
        runRecoveryJob(5)
    }
    MAX-ACCESS read-only
    STATUS     current
    DESCRIPTION
        "Describes the recovery action to be taken for an
        unsuccessfully run Job. The possible values are: 
        0 = 'Unknown', meaning it is unknown as to what
        recovery action to take 
        1 = 'Other', indicating that the recovery action
        will be specified in the OtherRecoveryAction
        property 
        2 = 'Do Not Continue', meaning stop the execution
        of the job and appropriately update its status 
        3 = 'Continue With Next Job', meaning continue with
        the next job in the queue 
        4 = 'Re-run Job', indicating that the job should be
        re-run 
        5 = 'Run Recovery Job', meaning run the Job
        associated using the RecoveryJob relationship. Note
        that the recovery Job must already be in the queue
        from which it will run."
    ::= { msvmNetworkJobEntry 27 }

msvmnjRunDay OBJECT-TYPE
    SYNTAX     Integer32
    MAX-ACCESS read-only
    STATUS     current
    DESCRIPTION
        "The day in the month on which the Job should be
        processed. There are two different interpretations
        for this property, depending on the value of
        DayOfWeek. In one case, RunDay defines the
        day-in-month on which the Job is processed. This
        interpretation is used when the DayOfWeek is 0. A
        positive or negative integer indicates whether the
        RunDay should be calculated from the beginning or
        end of the month. For example, 5 indicates the
        fifth day in the RunMonth and -1 indicates the last
        day in the RunMonth. 
        
        When RunDayOfWeek is not 0, RunDay is the
        day-in-month on which the Job is processed, defined
        in conjunction with RunDayOfWeek. For example, if
        RunDay is 15 and RunDayOfWeek is Saturday, then the
        Job is processed on the first Saturday on or after
        the 15th day in the RunMonth (for example, the
        third Saturday in the month). If RunDay is 20 and
        RunDayOfWeek is -Saturday, then this indicates the
        first Saturday on or before the 20th day in the
        RunMonth. If RunDay is -1 and RunDayOfWeek is
        -Sunday, then this indicates the last Sunday in the
        RunMonth."
    ::= { msvmNetworkJobEntry 28 }

msvmnjRunDayOfWeek OBJECT-TYPE
    SYNTAX     Integer32
    MAX-ACCESS read-only
    STATUS     current
    DESCRIPTION
        "A positive or negative integer used in conjunction
        with RunDay to indicate the day of the week on
        which the Job is processed. RunDayOfWeek is set to
        0 to indicate an exact day of the month, such as
        March 1. A positive integer (representing Sunday,
        Monday, ..., Saturday) means that the day of week
        is found on or after the specified RunDay. A
        negative integer (representing -Sunday, -Monday,
        ..., -Saturday) means that the day of week is found
        on or BEFORE the RunDay."
    ::= { msvmNetworkJobEntry 29 }

msvmnjRunMonth OBJECT-TYPE
    SYNTAX     INTEGER {
        january(0),
        february(1),
        march(2),
        april(3),
        may(4),
        june(5),
        july(6),
        august(7),
        september(8),
        october(9),
        november(10),
        december(11)
    }
    MAX-ACCESS read-only
    STATUS     current
    DESCRIPTION
        "The month during which the Job should be
        processed. Specify 0 for January, 1 for February,
        and so on."
    ::= { msvmNetworkJobEntry 30 }

msvmnjRunStartInterval OBJECT-TYPE
    SYNTAX     DateAndTime
    MAX-ACCESS read-only
    STATUS     current
    DESCRIPTION
        "The time interval after midnight when the Job
        should be processed. For example, 
        00000000020000.000000:000 
        indicates that the Job should be run on or after
        two o'clock, local time or UTC time (distinguished
        using the LocalOrUtcTime property."
    ::= { msvmNetworkJobEntry 31 }

msvmnjScheduledStartTime OBJECT-TYPE
    SYNTAX     DateAndTime
    MAX-ACCESS read-only
    STATUS     current
    DESCRIPTION
        "The time that the current Job is scheduled to
        start. This time can be represented by the actual
        date and time, or an interval relative to the time
        that this property is requested. A value of all
        zeroes indicates that the Job is already executing.
        The property is deprecated in lieu of the more
        expressive scheduling properties, RunMonth, RunDay,
        RunDayOfWeek, and RunStartInterval."
    ::= { msvmNetworkJobEntry 32 }

msvmnjStartTime OBJECT-TYPE
    SYNTAX     DateAndTime
    MAX-ACCESS read-only
    STATUS     current
    DESCRIPTION
        "The time that the Job was actually started. This
        time can be represented by an actual date and time,
        or by an interval relative to the time that this
        property is requested. Note that this property is
        also present in the JobProcessingStatistics class.
        This class is necessary to capture the processing
        information for recurring Jobs, because only the
        'last' run time can be stored in this single-valued
        property."
    ::= { msvmNetworkJobEntry 33 }

msvmnjStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmNetworkJobEntry 34 }

msvmnjStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmNetworkJobEntry 35 }

msvmnjTimeBeforeRemoval OBJECT-TYPE
    SYNTAX     DateAndTime
    MAX-ACCESS read-only
    STATUS     current
    DESCRIPTION
        "The amount of time that the Job is retained after
        it has finished executing, either succeeding or
        failing in that execution. The job must remain in
        existence for some period of time regardless of the
        value of the DeleteOnCompletion property. 
        The default is five minutes."
    ::= { msvmNetworkJobEntry 36 }

msvmnjTimeOfLastStateChange OBJECT-TYPE
    SYNTAX     DateAndTime
    MAX-ACCESS read-only
    STATUS     current
    DESCRIPTION
        "The date or time when the state of the Job last
        changed. If the state of the Job has not changed
        and this property is populated, then it must be set
        to a 0 interval value. If a state change was
        requested, but rejected or not yet processed, the
        property must not be updated."
    ::= { msvmNetworkJobEntry 37 }

msvmnjTimeSubmitted OBJECT-TYPE
    SYNTAX     DateAndTime
    MAX-ACCESS read-only
    STATUS     current
    DESCRIPTION
        "The time that the Job was submitted to execute. A
        value of all zeroes indicates that the owning
        element is not capable of reporting a date and
        time. Therefore, the ScheduledStartTime and
        StartTime are reported as intervals relative to the
        time their values are requested."
    ::= { msvmNetworkJobEntry 38 }

msvmnjUntilTime OBJECT-TYPE
    SYNTAX     DateAndTime
    MAX-ACCESS read-only
    STATUS     current
    DESCRIPTION
        "The time after which the Job is invalid or should
        be stopped. This time can be represented by an
        actual date and time, or by an interval relative to
        the time that this property is requested. A value
        of all nines indicates that the Job can run
        indefinitely."
    ::= { msvmNetworkJobEntry 39 }

msvmSwitchesAmongTable OBJECT-TYPE
    SYNTAX     SEQUENCE OF MsvmSwitchesAmong
    MAX-ACCESS not-accessible
    STATUS     current
    DESCRIPTION
        "Associates a switch service with a switch port."
    ::= { msvmNetworking 13 }

msvmSwitchesAmongEntry OBJECT-TYPE
    SYNTAX     MsvmSwitchesAmong
    MAX-ACCESS not-accessible
    STATUS     current
    DESCRIPTION
        "None"
    INDEX      { msvmsaIndex }
    ::= { msvmSwitchesAmongTable 1 }

MsvmSwitchesAmong ::= SEQUENCE {
    msvmsaIndex Integer32,
    msvmsaAntecedent WtcsDisplayString,
    msvmsaDependent WtcsDisplayString
}

msvmsaIndex OBJECT-TYPE
    SYNTAX     Integer32 (1..2147483647)
    MAX-ACCESS read-only
    STATUS     current
    DESCRIPTION
        "The value of this object uniquely identifies the
        instance entry for this class."
    ::= { msvmSwitchesAmongEntry 1 }

msvmsaAntecedent OBJECT-TYPE
    SYNTAX     WtcsDisplayString
    MAX-ACCESS read-only
    STATUS     current
    DESCRIPTION
        "Antecedent represents the independent object in
        this association."
    ::= { msvmSwitchesAmongEntry 2 }

msvmsaDependent OBJECT-TYPE
    SYNTAX     WtcsDisplayString
    MAX-ACCESS read-only
    STATUS     current
    DESCRIPTION
        "Dependent represents the object that is dependent
        on the Antecedent."
    ::= { msvmSwitchesAmongEntry 3 }

msvmSwitchPortTable OBJECT-TYPE
    SYNTAX     SEQUENCE OF MsvmSwitchPort
    MAX-ACCESS not-accessible
    STATUS     current
    DESCRIPTION
        "Represents a port on the switch."
    ::= { msvmNetworking 14 }

msvmSwitchPortEntry OBJECT-TYPE
    SYNTAX     MsvmSwitchPort
    MAX-ACCESS not-accessible
    STATUS     current
    DESCRIPTION
        "None"
    INDEX      { msvmspIndex }
    ::= { msvmSwitchPortTable 1 }

MsvmSwitchPort ::= SEQUENCE {
    msvmspIndex Integer32,
    msvmspBroadcastResetSupported TruthValue,
    msvmspCaption WtcsDisplayString,
    msvmspCreationClassName WtcsDisplayString,
    msvmspDescription WtcsDisplayString,
    msvmspElementName WtcsDisplayString,
    msvmspEnabledDefault INTEGER,
    msvmspEnabledState INTEGER,
    msvmspHealthState INTEGER,
    msvmspInstallDate DateAndTime,
    msvmspName WtcsDisplayString,
    msvmspNameFormat WtcsDisplayString,
    msvmspOperationalStatus INTEGER,
    msvmspOtherEnabledState WtcsDisplayString,
    msvmspOtherTypeDescription WtcsDisplayString,
    msvmspPortNumber Integer32,
    msvmspProtocolIFType Integer32,
    msvmspProtocolType INTEGER,
    msvmspRequestedState INTEGER,
    msvmspScopeOfResidence WtcsDisplayString,
    msvmspStatus WtcsDisplayString,
    msvmspStatusDescriptions WtcsDisplayString,
    msvmspSystemCreationClassName WtcsDisplayString,
    msvmspSystemName WtcsDisplayString,
    msvmspTimeOfLastStateChange DateAndTime
}

msvmspIndex OBJECT-TYPE
    SYNTAX     Integer32 (1..2147483647)
    MAX-ACCESS read-only
    STATUS     current
    DESCRIPTION
        "The value of this object uniquely identifies the
        instance entry for this class."
    ::= { msvmSwitchPortEntry 1 }

msvmspBroadcastResetSupported OBJECT-TYPE
    SYNTAX     TruthValue
    MAX-ACCESS read-only
    STATUS     current
    DESCRIPTION
        "A boolean indicating whether the instrumentation
        supports the BroadcastReset method."
    ::= { msvmSwitchPortEntry 2 }

msvmspCaption OBJECT-TYPE
    SYNTAX     WtcsDisplayString (SIZE (0..64))
    MAX-ACCESS read-only
    STATUS     current
    DESCRIPTION
        "The Caption property is a short textual
        description (one- line string) of the object."
    ::= { msvmSwitchPortEntry 3 }

msvmspCreationClassName OBJECT-TYPE
    SYNTAX     WtcsDisplayString (SIZE (0..256))
    MAX-ACCESS read-only
    STATUS     current
    DESCRIPTION
        "CreationClassName indicates the name of the class
        or the subclass used in the creation of an
        instance. When used with the other key properties
        of this class, this property allows all instances
        of this class and its subclasses to be uniquely
        identified."
    ::= { msvmSwitchPortEntry 4 }

msvmspDescription OBJECT-TYPE
    SYNTAX     WtcsDisplayString
    MAX-ACCESS read-only
    STATUS     current
    DESCRIPTION
        "The Description property provides a textual
        description of the object."
    ::= { msvmSwitchPortEntry 5 }

msvmspElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmSwitchPortEntry 6 }

msvmspEnabledDefault OBJECT-TYPE
    SYNTAX     INTEGER {
        enabled(2),
        disabled(3),
        notApplicable(5),
        enabledbutOffline(6),
        noDefault(7)
    }
    MAX-ACCESS read-only
    STATUS     current
    DESCRIPTION
        "An enumerated value indicating an administrator's
        default or startup configuration for the Enabled
        State of an element. By default, the element is
        'Enabled' (value=2)."
    ::= { msvmSwitchPortEntry 7 }

msvmspEnabledState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "EnabledState is an integer enumeration that
        indicates the enabled and disabled states of an
        element. It can also indicate the transitions
        between these requested states. For example,
        shutting down (value=4) and starting (value=10) are
        transient states between enabled and disabled. The
        following text briefly summarizes the various
        enabled and disabled states: 
        Enabled (2) indicates that the element is or could
        be executing commands, will process any queued
        commands, and queues new requests. 
        Disabled (3) indicates that the element will not
        execute commands and will drop any new requests. 
        Shutting Down (4) indicates that the element is in
        the process of going to a Disabled state. 
        Not Applicable (5) indicates the element does not
        support being enabled or disabled. 
        Enabled but Offline (6) indicates that the element
        might be completing commands, and will drop any new
        requests. 
        Test (7) indicates that the element is in a test
        state. 
        Deferred (8) indicates that the element might be
        completing commands, but will queue any new
        requests. 
        Quiesce (9) indicates that the element is enabled
        but in a restricted mode. The behavior of the
        element is similar to the Enabled state, but it
        processes only a restricted set of commands. All
        other requests are queued. 
        Starting (10) indicates that the element is in the
        process of going to an Enabled state. New requests
        are queued."
    ::= { msvmSwitchPortEntry 8 }

msvmspHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmSwitchPortEntry 9 }

msvmspInstallDate OBJECT-TYPE
    SYNTAX     DateAndTime
    MAX-ACCESS read-only
    STATUS     current
    DESCRIPTION
        "A datetime value that indicates when the object
        was installed. Lack of a value does not indicate
        that the object is not installed."
    ::= { msvmSwitchPortEntry 10 }

msvmspName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmSwitchPortEntry 11 }

msvmspNameFormat OBJECT-TYPE
    SYNTAX     WtcsDisplayString (SIZE (0..256))
    MAX-ACCESS read-only
    STATUS     current
    DESCRIPTION
        "NameFormat contains the naming heuristic that is
        selected to ensure that the value of the Name
        property is unique. For example, you might choose
        to prepend the name of the port or interface with
        the Type of ProtocolEndpoint (for example, IPv4) of
        this instance followed by an underscore."
    ::= { msvmSwitchPortEntry 12 }

msvmspOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmSwitchPortEntry 13 }

msvmspOtherEnabledState OBJECT-TYPE
    SYNTAX     WtcsDisplayString
    MAX-ACCESS read-only
    STATUS     current
    DESCRIPTION
        "A string that describes the enabled or disabled
        state of the element when the EnabledState property
        is set to 1 ('Other'). This property must be set to
        null when EnabledState is any value other than 1."
    ::= { msvmSwitchPortEntry 14 }

msvmspOtherTypeDescription OBJECT-TYPE
    SYNTAX     WtcsDisplayString (SIZE (0..64))
    MAX-ACCESS read-only
    STATUS     current
    DESCRIPTION
        "A string that describes the type of
        ProtocolEndpoint when the Type property of this
        class (or any of its subclasses) is set to 1
        (Other). This property should be set to null when
        the Type property is any value other than 1."
    ::= { msvmSwitchPortEntry 15 }

msvmspPortNumber OBJECT-TYPE
    SYNTAX     Integer32
    MAX-ACCESS read-only
    STATUS     current
    DESCRIPTION
        "Numeric identifier for a switch port."
    ::= { msvmSwitchPortEntry 16 }

msvmspProtocolIFType OBJECT-TYPE
    SYNTAX     Integer32
    MAX-ACCESS read-only
    STATUS     current
    DESCRIPTION
        "ProtocolIFType is an enumeration that is
        synchronized with the IANA ifType MIB. The ifType
        MIB is maintained at the URL,
        http://www.iana.org/assignments/ianaiftype-mib.
        Also, additional values defined by the DMTF are
        included. The property is used to categorize and
        classify instances of the ProtocolEndpoint class.
        Note that if the ProtocolIFType is set to 1
        (Other), then the type information should be
        provided in the OtherTypeDescription string
        property."
    ::= { msvmSwitchPortEntry 17 }

msvmspProtocolType OBJECT-TYPE
    SYNTAX     INTEGER {
        unknown(0),
        other(1),
        ipv4(2),
        ipv6(3),
        ipx(4),
        appleTalk(5),
        decnet(6),
        sna(7),
        conp(8),
        clnp(9),
        vines(10),
        xns(11),
        atm(12),
        frameRelay(13),
        ethernet(14),
        tokenRing(15),
        fddi(16),
        infiniband(17),
        fibreChannel(18),
        isdnBRIEndpoint(19),
        isdnBChannelEndpoint(20),
        isdnDChannelEndpoint(21),
        ipv4v6(22),
        bgp(23),
        ospf(24),
        mpls(25),
        udp(26),
        tcp(27)
    }
    MAX-ACCESS read-only
    STATUS     current
    DESCRIPTION
        "Note: This property is deprecated in lieu of the
        ProtocolIFType enumeration. This deprecation was
        done to have better alignment between the IF-MIB of
        the IETF and this CIM class. 
        Deprecated description: ProtocolType is an
        enumeration that provides information to categorize
        and classify different instances of this class. For
        most instances, information in this enumeration and
        the definition of the subclass overlap. However,
        there are several cases where a specific subclass
        of ProtocolEndpoint is not required (for example,
        there is no Fibre Channel subclass of
        ProtocolEndpoint). Therefore, this property is
        needed to define the type of Endpoint."
    ::= { msvmSwitchPortEntry 18 }

msvmspRequestedState OBJECT-TYPE
    SYNTAX     INTEGER {
        enabled(2),
        disabled(3),
        shutDown(4),
        noChange(5),
        offline(6),
        test(7),
        deferred(8),
        quiesce(9),
        reboot(10),
        reset(11),
        notApplicable(12)
    }
    MAX-ACCESS read-only
    STATUS     current
    DESCRIPTION
        "RequestedState is an integer enumeration that
        indicates the last requested or desired state for
        the element. The actual state of the element is
        represented by EnabledState. This property is
        provided to compare the last requested and current
        enabled or disabled states. Note that when
        EnabledState is set to 5 ('Not Applicable'), then
        this property has no meaning. By default, the
        RequestedState of the element is 5 ('No Change').
        Refer to the EnabledState property description for
        explanations of the values in the RequestedState
        enumeration. 
        
        It should be noted that there are two new values in
        RequestedState that build on the statuses of
        EnabledState. These are 'Reboot' (10) and 'Reset'
        (11). Reboot refers to doing a 'Shut Down' and then
        moving to an 'Enabled' state. Reset indicates that
        the element is first 'Disabled' and then 'Enabled'.
        The distinction between requesting 'Shut Down' and
        'Disabled' should also be noted. Shut Down requests
        an orderly transition to the Disabled state, and
        might involve removing power, to completely erase
        any existing state. The Disabled state requests an
        immediate disabling of the element, such that it
        will not execute or accept any commands or
        processing requests. 
        
        This property is set as the result of a method
        invocation (such as Start or StopService on
        CIM_Service), or can be overridden and defined as
        WRITEable in a subclass. The method approach is
        considered superior to a WRITEable property,
        because it allows an explicit invocation of the
        operation and the return of a result code. 
        
        A particular instance of EnabledLogicalElement
        might not support RequestedStateChange. If this
        occurs, the value 12 ('Not Applicable') is used."
    ::= { msvmSwitchPortEntry 19 }

msvmspScopeOfResidence OBJECT-TYPE
    SYNTAX     WtcsDisplayString
    MAX-ACCESS read-only
    STATUS     current
    DESCRIPTION
        "The azman scope for the switch service. This scope
        will be used when performing access checks for the
        switch service. This property is inherited from
        CIM_SwitchPort."
    ::= { msvmSwitchPortEntry 20 }

msvmspStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmSwitchPortEntry 21 }

msvmspStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmSwitchPortEntry 22 }

msvmspSystemCreationClassName OBJECT-TYPE
    SYNTAX     WtcsDisplayString (SIZE (0..256))
    MAX-ACCESS read-only
    STATUS     current
    DESCRIPTION
        "The CreationClassName of the scoping System."
    ::= { msvmSwitchPortEntry 23 }

msvmspSystemName OBJECT-TYPE
    SYNTAX     WtcsDisplayString (SIZE (0..256))
    MAX-ACCESS read-only
    STATUS     current
    DESCRIPTION
        "The Name of the scoping System."
    ::= { msvmSwitchPortEntry 24 }

msvmspTimeOfLastStateChange OBJECT-TYPE
    SYNTAX     DateAndTime
    MAX-ACCESS read-only
    STATUS     current
    DESCRIPTION
        "The date or time when the EnabledState of the
        element last changed. If the state of the element
        has not changed and this property is populated,
        then it must be set to a 0 interval value. If a
        state change was requested, but rejected or not yet
        processed, the property must not be updated."
    ::= { msvmSwitchPortEntry 25 }

msvmSwitchPortDynamicFwdTable OBJECT-TYPE
    SYNTAX     SEQUENCE OF MsvmSwitchPortDynamicForwarding
    MAX-ACCESS not-accessible
    STATUS     current
    DESCRIPTION
        "Connects a switch port to a dynamic forward entry
        (learned MAC address). This is useful in finding
        all of the learned MAC addresses for a specified
        port."
    ::= { msvmNetworking 15 }

msvmSwitchPortDynamicFwdEntry OBJECT-TYPE
    SYNTAX     MsvmSwitchPortDynamicForwarding
    MAX-ACCESS not-accessible
    STATUS     current
    DESCRIPTION
        "None"
    INDEX      { msvmspdfIndex }
    ::= { msvmSwitchPortDynamicFwdTable 1 }

MsvmSwitchPortDynamicForwarding ::= SEQUENCE {
    msvmspdfIndex Integer32,
    msvmspdfAntecedent WtcsDisplayString,
    msvmspdfDependent WtcsDisplayString
}

msvmspdfIndex OBJECT-TYPE
    SYNTAX     Integer32 (1..2147483647)
    MAX-ACCESS read-only
    STATUS     current
    DESCRIPTION
        "The value of this object uniquely identifies the
        instance entry for this class."
    ::= { msvmSwitchPortDynamicFwdEntry 1 }

msvmspdfAntecedent OBJECT-TYPE
    SYNTAX     WtcsDisplayString
    MAX-ACCESS read-only
    STATUS     current
    DESCRIPTION
        "Antecedent represents the independent object in
        this association."
    ::= { msvmSwitchPortDynamicFwdEntry 2 }

msvmspdfDependent OBJECT-TYPE
    SYNTAX     WtcsDisplayString
    MAX-ACCESS read-only
    STATUS     current
    DESCRIPTION
        "Dependent represents the object that is dependent
        on the Antecedent."
    ::= { msvmSwitchPortDynamicFwdEntry 3 }

msvmSwitchServiceTable OBJECT-TYPE
    SYNTAX     SEQUENCE OF MsvmSwitchService
    MAX-ACCESS not-accessible
    STATUS     current
    DESCRIPTION
        "Represents a virtual switch."
    ::= { msvmNetworking 16 }

msvmSwitchServiceEntry OBJECT-TYPE
    SYNTAX     MsvmSwitchService
    MAX-ACCESS not-accessible
    STATUS     current
    DESCRIPTION
        "None"
    INDEX      { msvmssIndex }
    ::= { msvmSwitchServiceTable 1 }

MsvmSwitchService ::= SEQUENCE {
    msvmssIndex Integer32,
    msvmssBridgeAddress WtcsDisplayString,
    msvmssBridgeAddressType INTEGER,
    msvmssBridgeType INTEGER,
    msvmssCaption WtcsDisplayString,
    msvmssCreationClassName WtcsDisplayString,
    msvmssDescription WtcsDisplayString,
    msvmssElementName WtcsDisplayString,
    msvmssEnabledDefault INTEGER,
    msvmssEnabledState INTEGER,
    msvmssHealthState INTEGER,
    msvmssInstallDate DateAndTime,
    msvmssKeywords WtcsDisplayString,
    msvmssName WtcsDisplayString,
    msvmssNumLearnableAddresses Gauge32,
    msvmssNumPorts Integer32,
    msvmssOperationalStatus INTEGER,
    msvmssOtherEnabledState WtcsDisplayString,
    msvmssOtherProtocolType WtcsDisplayString,
    msvmssPrimaryOwnerContact WtcsDisplayString,
    msvmssPrimaryOwnerName WtcsDisplayString,
    msvmssProtocolType INTEGER,
    msvmssRequestedState INTEGER,
    msvmssScopeOfResidence WtcsDisplayString,
    msvmssServiceURL WtcsDisplayString,
    msvmssStartMode WtcsDisplayString,
    msvmssStarted TruthValue,
    msvmssStartupConditions WtcsDisplayString,
    msvmssStartupParameters WtcsDisplayString,
    msvmssStatus WtcsDisplayString,
    msvmssStatusDescriptions WtcsDisplayString,
    msvmssSystemCreationClassName WtcsDisplayString,
    msvmssSystemName WtcsDisplayString,
    msvmssTimeOfLastStateChange DateAndTime
}

msvmssIndex OBJECT-TYPE
    SYNTAX     Integer32 (1..2147483647)
    MAX-ACCESS read-only
    STATUS     current
    DESCRIPTION
        "The value of this object uniquely identifies the
        instance entry for this class."
    ::= { msvmSwitchServiceEntry 1 }

msvmssBridgeAddress OBJECT-TYPE
    SYNTAX     WtcsDisplayString (SIZE (0..32))
    MAX-ACCESS read-only
    STATUS     current
    DESCRIPTION
        "Address used by this SwitchService when it must be
        uniquely identified. For an ethernet bridge, the
        MAC Address serves as the BridgeAddress. When
        concatenated with a SpanningTreeService Priority, a
        unique bridge identifier results. The MAC address
        is formatted as twelve hexadecimal digits (e.g.,
        '010203040506'), with each pair representing one of
        the six octets of the MAC address in 'canonical'
        bit order according to RFC 2469. In other
        scenarios, like Ipv6, the address is formatted as
        'ffff:ffff:ffff:ffff'."
    ::= { msvmSwitchServiceEntry 2 }

msvmssBridgeAddressType OBJECT-TYPE
    SYNTAX     INTEGER {
        other(1),
        ipv4(2),
        ipv6(3),
        mac(4),
        macSpanningTreePriority(5)
    }
    MAX-ACCESS read-only
    STATUS     current
    DESCRIPTION
        "BridgeAddressType defines the type of addressing
        scheme used for this Bridge and its BridgeAddress
        property."
    ::= { msvmSwitchServiceEntry 3 }

msvmssBridgeType OBJECT-TYPE
    SYNTAX     INTEGER {
        unknown(1),
        transparentonly(2),
        sourceRouteonly(3),
        srt(4)
    }
    MAX-ACCESS read-only
    STATUS     current
    DESCRIPTION
        "Indicates what type of switching service can be
        performed."
    ::= { msvmSwitchServiceEntry 4 }

msvmssCaption OBJECT-TYPE
    SYNTAX     WtcsDisplayString (SIZE (0..64))
    MAX-ACCESS read-only
    STATUS     current
    DESCRIPTION
        "The Caption property is a short textual
        description (one- line string) of the object."
    ::= { msvmSwitchServiceEntry 5 }

msvmssCreationClassName OBJECT-TYPE
    SYNTAX     WtcsDisplayString (SIZE (0..256))
    MAX-ACCESS read-only
    STATUS     current
    DESCRIPTION
        "CreationClassName indicates the name of the class
        or the subclass that is used in the creation of an
        instance. When used with the other key properties
        of this class, this property allows all instances
        of this class and its subclasses to be uniquely
        identified."
    ::= { msvmSwitchServiceEntry 6 }

msvmssDescription OBJECT-TYPE
    SYNTAX     WtcsDisplayString
    MAX-ACCESS read-only
    STATUS     current
    DESCRIPTION
        "The Description property provides a textual
        description of the object."
    ::= { msvmSwitchServiceEntry 7 }

msvmssElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmSwitchServiceEntry 8 }

msvmssEnabledDefault OBJECT-TYPE
    SYNTAX     INTEGER {
        enabled(2),
        disabled(3),
        notApplicable(5),
        enabledbutOffline(6),
        noDefault(7)
    }
    MAX-ACCESS read-only
    STATUS     current
    DESCRIPTION
        "An enumerated value indicating an administrator's
        default or startup configuration for the Enabled
        State of an element. By default, the element is
        'Enabled' (value=2)."
    ::= { msvmSwitchServiceEntry 9 }

msvmssEnabledState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "EnabledState is an integer enumeration that
        indicates the enabled and disabled states of an
        element. It can also indicate the transitions
        between these requested states. For example,
        shutting down (value=4) and starting (value=10) are
        transient states between enabled and disabled. The
        following text briefly summarizes the various
        enabled and disabled states: 
        Enabled (2) indicates that the element is or could
        be executing commands, will process any queued
        commands, and queues new requests. 
        Disabled (3) indicates that the element will not
        execute commands and will drop any new requests. 
        Shutting Down (4) indicates that the element is in
        the process of going to a Disabled state. 
        Not Applicable (5) indicates the element does not
        support being enabled or disabled. 
        Enabled but Offline (6) indicates that the element
        might be completing commands, and will drop any new
        requests. 
        Test (7) indicates that the element is in a test
        state. 
        Deferred (8) indicates that the element might be
        completing commands, but will queue any new
        requests. 
        Quiesce (9) indicates that the element is enabled
        but in a restricted mode. The behavior of the
        element is similar to the Enabled state, but it
        processes only a restricted set of commands. All
        other requests are queued. 
        Starting (10) indicates that the element is in the
        process of going to an Enabled state. New requests
        are queued."
    ::= { msvmSwitchServiceEntry 10 }

msvmssHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmSwitchServiceEntry 11 }

msvmssInstallDate OBJECT-TYPE
    SYNTAX     DateAndTime
    MAX-ACCESS read-only
    STATUS     current
    DESCRIPTION
        "A datetime value that indicates when the object
        was installed. Lack of a value does not indicate
        that the object is not installed."
    ::= { msvmSwitchServiceEntry 12 }

msvmssKeywords OBJECT-TYPE
    SYNTAX     WtcsDisplayString
    MAX-ACCESS read-only
    STATUS     current
    DESCRIPTION
        "This is a free-form array of strings that provide
        descriptive words and phrases that can be used in
        queries. To-date, this property has not been
        implemented, since it is not standardized. Also, if
        this was a necessary query construct, then it would
        be required higher in the inheritance hierarchy.
        The latter has not proven necessary. Therefore, the
        property is deprecated."
    ::= { msvmSwitchServiceEntry 13 }

msvmssName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmSwitchServiceEntry 14 }

msvmssNumLearnableAddresses OBJECT-TYPE
    SYNTAX     Gauge32
    MAX-ACCESS read-only
    STATUS     current
    DESCRIPTION
        "The number of learnable addresses for this switch.
        This property is inherited from CIM_SwitchService."
    ::= { msvmSwitchServiceEntry 15 }

msvmssNumPorts OBJECT-TYPE
    SYNTAX     Integer32
    MAX-ACCESS read-only
    STATUS     current
    DESCRIPTION
        "The number of switch ports controlled by this
        switching service."
    ::= { msvmSwitchServiceEntry 16 }

msvmssOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmSwitchServiceEntry 17 }

msvmssOtherEnabledState OBJECT-TYPE
    SYNTAX     WtcsDisplayString
    MAX-ACCESS read-only
    STATUS     current
    DESCRIPTION
        "A string that describes the enabled or disabled
        state of the element when the EnabledState property
        is set to 1 ('Other'). This property must be set to
        null when EnabledState is any value other than 1."
    ::= { msvmSwitchServiceEntry 18 }

msvmssOtherProtocolType OBJECT-TYPE
    SYNTAX     WtcsDisplayString (SIZE (0..32))
    MAX-ACCESS read-only
    STATUS     current
    DESCRIPTION
        "This defines the type of protocol that is being
        forwarded when the value of the ProtocolType
        attribute is 1 (i.e., 'Other'). This provides for
        future extensibility."
    ::= { msvmSwitchServiceEntry 19 }

msvmssPrimaryOwnerContact OBJECT-TYPE
    SYNTAX     WtcsDisplayString (SIZE (0..256))
    MAX-ACCESS read-only
    STATUS     current
    DESCRIPTION
        "A string that provides information on how the
        primary owner of the Service can be reached (for
        example, phone number, e-mail address, and so on)."
    ::= { msvmSwitchServiceEntry 20 }

msvmssPrimaryOwnerName OBJECT-TYPE
    SYNTAX     WtcsDisplayString (SIZE (0..64))
    MAX-ACCESS read-only
    STATUS     current
    DESCRIPTION
        "The name of the primary owner for the service, if
        one is defined. The primary owner is the initial
        support contact for the Service."
    ::= { msvmSwitchServiceEntry 21 }

msvmssProtocolType OBJECT-TYPE
    SYNTAX     INTEGER {
        unknown(0),
        other(1),
        ipv4(2),
        ipv6(3),
        ipv4IPv6(4),
        ipx(5),
        appleTalk(6),
        decnet(7),
        sna(8),
        conp(9),
        clnp(10),
        vines(11),
        xns(12),
        atm(13),
        frameRelay(14),
        ethernet(15),
        tokenRing(16),
        fddi(17),
        infiniband(18),
        fibreChannel(19)
    }
    MAX-ACCESS read-only
    STATUS     current
    DESCRIPTION
        "This defines the type of protocol that is being
        forwarded."
    ::= { msvmSwitchServiceEntry 22 }

msvmssRequestedState OBJECT-TYPE
    SYNTAX     INTEGER {
        enabled(2),
        disabled(3),
        shutDown(4),
        noChange(5),
        offline(6),
        test(7),
        deferred(8),
        quiesce(9),
        reboot(10),
        reset(11),
        notApplicable(12)
    }
    MAX-ACCESS read-only
    STATUS     current
    DESCRIPTION
        "RequestedState is an integer enumeration that
        indicates the last requested or desired state for
        the element. The actual state of the element is
        represented by EnabledState. This property is
        provided to compare the last requested and current
        enabled or disabled states. Note that when
        EnabledState is set to 5 ('Not Applicable'), then
        this property has no meaning. By default, the
        RequestedState of the element is 5 ('No Change').
        Refer to the EnabledState property description for
        explanations of the values in the RequestedState
        enumeration. 
        
        It should be noted that there are two new values in
        RequestedState that build on the statuses of
        EnabledState. These are 'Reboot' (10) and 'Reset'
        (11). Reboot refers to doing a 'Shut Down' and then
        moving to an 'Enabled' state. Reset indicates that
        the element is first 'Disabled' and then 'Enabled'.
        The distinction between requesting 'Shut Down' and
        'Disabled' should also be noted. Shut Down requests
        an orderly transition to the Disabled state, and
        might involve removing power, to completely erase
        any existing state. The Disabled state requests an
        immediate disabling of the element, such that it
        will not execute or accept any commands or
        processing requests. 
        
        This property is set as the result of a method
        invocation (such as Start or StopService on
        CIM_Service), or can be overridden and defined as
        WRITEable in a subclass. The method approach is
        considered superior to a WRITEable property,
        because it allows an explicit invocation of the
        operation and the return of a result code. 
        
        A particular instance of EnabledLogicalElement
        might not support RequestedStateChange. If this
        occurs, the value 12 ('Not Applicable') is used."
    ::= { msvmSwitchServiceEntry 23 }

msvmssScopeOfResidence OBJECT-TYPE
    SYNTAX     WtcsDisplayString
    MAX-ACCESS read-only
    STATUS     current
    DESCRIPTION
        "The azman scope for the switch service. This
        property is inherited from CIM_SwitchService."
    ::= { msvmSwitchServiceEntry 24 }

msvmssServiceURL OBJECT-TYPE
    SYNTAX     WtcsDisplayString
    MAX-ACCESS read-only
    STATUS     current
    DESCRIPTION
        "This is a URL that provides the protocol, network
        location, and other service-specific information
        required in order to access the service. It is
        deprecated with the recommendation that
        ServiceAccessURI be instantiated instead. This new
        class correctly positions the semantics of the
        service access, and clarifies the format of the
        information."
    ::= { msvmSwitchServiceEntry 25 }

msvmssStartMode OBJECT-TYPE
    SYNTAX     WtcsDisplayString (SIZE (0..10))
    MAX-ACCESS read-only
    STATUS     current
    DESCRIPTION
        "Note: The use of this element is deprecated in
        lieu of the EnabledDefault property that is
        inherited from EnabledLogicalElement. The
        EnabledLogicalElement addresses the same semantics.
        The change to a uint16 data type was discussed when
        CIM V2.0 was defined. However, existing V1.0
        implementations used the string property. To remain
        compatible with those implementations, StartMode
        was grandfathered into the schema. Use of the
        deprecated qualifier allows the maintenance of the
        existing property but also permits an improved,
        clarified definition using EnabledDefault. 
        Deprecated description: StartMode is a string value
        that indicates whether the Service is automatically
        started by a System, an Operating System, and so
        on, or is started only upon request."
    ::= { msvmSwitchServiceEntry 26 }

msvmssStarted OBJECT-TYPE
    SYNTAX     TruthValue
    MAX-ACCESS read-only
    STATUS     current
    DESCRIPTION
        "Started is a Boolean that indicates whether the
        Service has been started (TRUE), or stopped
        (FALSE)."
    ::= { msvmSwitchServiceEntry 27 }

msvmssStartupConditions OBJECT-TYPE
    SYNTAX     WtcsDisplayString
    MAX-ACCESS read-only
    STATUS     current
    DESCRIPTION
        "This is a free-form array of strings that specify
        any specific pre-conditions that must be met in
        order for this service to start correctly. It was
        expected that subclasses would refine the inherited
        StartService() method to suit their specific needs.
        To-date, this refinement has not been necessary.
        Also, the property is not very useful, since it is
        not standardized. If this was a necessary
        construct, then it would be required higher in the
        inheritance hierarchy (on Service). The latter has
        not proven true. Therefore, the property is
        deprecated."
    ::= { msvmSwitchServiceEntry 28 }

msvmssStartupParameters OBJECT-TYPE
    SYNTAX     WtcsDisplayString
    MAX-ACCESS read-only
    STATUS     current
    DESCRIPTION
        "This is a free-form array of strings that specify
        any specific parameters that must be supplied to
        the StartService() method in order for this service
        to start correctly. It was expected that subclasses
        would refine the inherited StartService() methods
        to suit their specific needs. To-date, this
        refinement has not been necessary. If indeed the
        method were refined, then its parameters would more
        formally convey this information. Therefore, the
        property is deprecated."
    ::= { msvmSwitchServiceEntry 29 }

msvmssStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmSwitchServiceEntry 30 }

msvmssStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmSwitchServiceEntry 31 }

msvmssSystemCreationClassName OBJECT-TYPE
    SYNTAX     WtcsDisplayString (SIZE (0..256))
    MAX-ACCESS read-only
    STATUS     current
    DESCRIPTION
        "The CreationClassName of the scoping System."
    ::= { msvmSwitchServiceEntry 32 }

msvmssSystemName OBJECT-TYPE
    SYNTAX     WtcsDisplayString (SIZE (0..256))
    MAX-ACCESS read-only
    STATUS     current
    DESCRIPTION
        "The Name of the scoping System."
    ::= { msvmSwitchServiceEntry 33 }

msvmssTimeOfLastStateChange OBJECT-TYPE
    SYNTAX     DateAndTime
    MAX-ACCESS read-only
    STATUS     current
    DESCRIPTION
        "The date or time when the EnabledState of the
        element last changed. If the state of the element
        has not changed and this property is populated,
        then it must be set to a 0 interval value. If a
        state change was requested, but rejected or not yet
        processed, the property must not be updated."
    ::= { msvmSwitchServiceEntry 34 }

msvmSwitchServiceTrptBridgeTable OBJECT-TYPE
    SYNTAX     SEQUENCE OF MsvmSwitchSvcTransparentBridging
    MAX-ACCESS not-accessible
    STATUS     current
    DESCRIPTION
        "Connects a switch service to a transparent
        bridging service."
    ::= { msvmNetworking 17 }

msvmSwitchServiceTrptBridgeEntry OBJECT-TYPE
    SYNTAX     MsvmSwitchSvcTransparentBridging
    MAX-ACCESS not-accessible
    STATUS     current
    DESCRIPTION
        "None"
    INDEX      { msvmsstbIndex }
    ::= { msvmSwitchServiceTrptBridgeTable 1 }

MsvmSwitchSvcTransparentBridging ::= SEQUENCE {
    msvmsstbIndex Integer32,
    msvmsstbGroupComponent WtcsDisplayString,
    msvmsstbPartComponent WtcsDisplayString
}

msvmsstbIndex OBJECT-TYPE
    SYNTAX     Integer32 (1..2147483647)
    MAX-ACCESS read-only
    STATUS     current
    DESCRIPTION
        "The value of this object uniquely identifies the
        instance entry for this class."
    ::= { msvmSwitchServiceTrptBridgeEntry 1 }

msvmsstbGroupComponent OBJECT-TYPE
    SYNTAX     WtcsDisplayString
    MAX-ACCESS read-only
    STATUS     current
    DESCRIPTION
        "The parent element in the association."
    ::= { msvmSwitchServiceTrptBridgeEntry 2 }

msvmsstbPartComponent OBJECT-TYPE
    SYNTAX     WtcsDisplayString
    MAX-ACCESS read-only
    STATUS     current
    DESCRIPTION
        "The child element in the association."
    ::= { msvmSwitchServiceTrptBridgeEntry 3 }

msvmSyntheticEthernetPortTable OBJECT-TYPE
    SYNTAX     SEQUENCE OF MsvmSyntheticEthernetPort
    MAX-ACCESS not-accessible
    STATUS     current
    DESCRIPTION
        "Represents a synthetic Ethernet adapter."
    ::= { msvmNetworking 18 }

msvmSyntheticEthernetPortEntry OBJECT-TYPE
    SYNTAX     MsvmSyntheticEthernetPort
    MAX-ACCESS not-accessible
    STATUS     current
    DESCRIPTION
        "None"
    INDEX      { msvmsepIndex }
    ::= { msvmSyntheticEthernetPortTable 1 }

MsvmSyntheticEthernetPort ::= SEQUENCE {
    msvmsepIndex Integer32,
    msvmsepActiveMaxTransmissionUnit Gauge32,
    msvmsepAdditionalAvailability INTEGER,
    msvmsepAutoSense TruthValue,
    msvmsepAvailability INTEGER,
    msvmsepCapabilities INTEGER,
    msvmsepCapabilityDescriptions WtcsDisplayString,
    msvmsepCaption WtcsDisplayString,
    msvmsepCreationClassName WtcsDisplayString,
    msvmsepDescription WtcsDisplayString,
    msvmsepDeviceID WtcsDisplayString,
    msvmsepElementName WtcsDisplayString,
    msvmsepEnabledCapabilities INTEGER,
    msvmsepEnabledDefault INTEGER,
    msvmsepEnabledState INTEGER,
    msvmsepErrorCleared TruthValue,
    msvmsepErrorDescription WtcsDisplayString,
    msvmsepFullDuplex TruthValue,
    msvmsepHealthState INTEGER,
    msvmsepIdentifyingDescriptions WtcsDisplayString,
    msvmsepInstallDate DateAndTime,
    msvmsepLastErrorCode Gauge32,
    msvmsepLinkTechnology INTEGER,
    msvmsepLocationIndicator INTEGER,
    msvmsepMaxDataSize Gauge32,
    msvmsepMaxQuiesceTime Gauge32,
    msvmsepMaxSpeed Gauge32,
    msvmsepName WtcsDisplayString,
    msvmsepNetworkAddresses WtcsDisplayString,
    msvmsepOperationalStatus INTEGER,
    msvmsepOtherEnabledCapabilities WtcsDisplayString,
    msvmsepOtherEnabledState WtcsDisplayString,
    msvmsepOtherIdentifyingInfo WtcsDisplayString,
    msvmsepOtherLinkTechnology WtcsDisplayString,
    msvmsepOtherNetworkPortType WtcsDisplayString,
    msvmsepOtherPortType WtcsDisplayString,
    msvmsepPermanentAddress WtcsDisplayString,
    msvmsepPortNumber Integer32,
    msvmsepPortType INTEGER,
    msvmsepPowerManagementCapability INTEGER,
    msvmsepPowerManagementSupported TruthValue,
    msvmsepPowerOnHours Gauge32,
    msvmsepRequestedSpeed Gauge32,
    msvmsepRequestedState INTEGER,
    msvmsepSpeed Gauge32,
    msvmsepStatus WtcsDisplayString,
    msvmsepStatusDescriptions WtcsDisplayString,
    msvmsepStatusInfo INTEGER,
    msvmsepSupportedMaxTransmitUnit Gauge32,
    msvmsepSystemCreationClassName WtcsDisplayString,
    msvmsepSystemName WtcsDisplayString,
    msvmsepTimeOfLastStateChange DateAndTime,
    msvmsepTotalPowerOnHours Gauge32,
    msvmsepUsageRestriction INTEGER
}

msvmsepIndex OBJECT-TYPE
    SYNTAX     Integer32 (1..2147483647)
    MAX-ACCESS read-only
    STATUS     current
    DESCRIPTION
        "The value of this object uniquely identifies the
        instance entry for this class."
    ::= { msvmSyntheticEthernetPortEntry 1 }

msvmsepActiveMaxTransmissionUnit OBJECT-TYPE
    SYNTAX     Gauge32
    UNITS "Bytes"
    MAX-ACCESS read-only
    STATUS     current
    DESCRIPTION
        "The active or negotiated maximum transmission unit
        (MTU) that can be supported."
    ::= { msvmSyntheticEthernetPortEntry 2 }

msvmsepAdditionalAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Additional availability and status of the Device
        in addition to that specified in the Availability
        property. The Availability property denotes the
        primary status and availability of the Device. In
        some cases, this property will not be sufficient to
        denote the complete status of the Device. In those
        cases, the AdditionalAvailability property can be
        used to provide further information. For example,
        the primary Availability of a device might be 'Off
        line' (value=8) or in a low-power state
        (AdditionalAvailability value=14), or the Device
        could be running Diagnostics
        (AdditionalAvailability value=5, 'In Test')."
    ::= { msvmSyntheticEthernetPortEntry 3 }

msvmsepAutoSense OBJECT-TYPE
    SYNTAX     TruthValue
    MAX-ACCESS read-only
    STATUS     current
    DESCRIPTION
        "A Boolean that indicates whether the NetworkPort
        is capable of automatically determining the speed
        or other communications characteristics of the
        attached network media."
    ::= { msvmSyntheticEthernetPortEntry 4 }

msvmsepAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Note: The use of this property has been
        deprecated. 
        Deprecated description: The primary availability
        and status of the Device. (Additional status
        information can be specified using the Additional
        Availability array property.) For example, the
        Availability property indicates that the Device is
        running and has full power (value=3), or is in a
        warning (4), test (5), degraded (10) or power save
        state (values 13-15 and 17). The Power Save states
        are defined as follows: Value 13 ('Power Save -
        Unknown') indicates that the Device is known to be
        in a power save mode, but its exact status in this
        mode is unknown; value 14 ('Power Save - Low Power
        Mode') indicates that the Device is in a power save
        state but still functioning, and might exhibit
        degraded performance; value 15 ('Power Save -
        Standby') indicates that the Device is not
        functioning but could be brought to full power
        'quickly'; and value 17 ('Power Save - Warning')
        indicates that the Device is in a warning state,
        but is also in a power save mode."
    ::= { msvmSyntheticEthernetPortEntry 5 }

msvmsepCapabilities OBJECT-TYPE
    SYNTAX     INTEGER {
        unknown(0),
        other(1),
        alertOnLan(2),
        wakeOnLan(3),
        failOver(4),
        loadBalancing(5)
    }
    MAX-ACCESS read-only
    STATUS     current
    DESCRIPTION
        "Capabilities of the EthernetPort. For example, the
        Device might support AlertOnLan, WakeOnLan, Load
        Balancing, or FailOver. If failover or load
        balancing capabilities are listed, a SpareGroup
        (failover) or ExtraCapacityGroup (load balancing)
        should also be defined to completely describe the
        capability."
    ::= { msvmSyntheticEthernetPortEntry 6 }

msvmsepCapabilityDescriptions OBJECT-TYPE
    SYNTAX     WtcsDisplayString
    MAX-ACCESS read-only
    STATUS     current
    DESCRIPTION
        "An array of free-form strings that provides more
        detailed explanations for any of the EthernetPort
        features that are indicated in the Capabilities
        array. Note, each entry of this array is related to
        the entry in the Capabilities array that is located
        at the same index."
    ::= { msvmSyntheticEthernetPortEntry 7 }

msvmsepCaption OBJECT-TYPE
    SYNTAX     WtcsDisplayString (SIZE (0..64))
    MAX-ACCESS read-only
    STATUS     current
    DESCRIPTION
        "The Caption property is a short textual
        description (one- line string) of the object."
    ::= { msvmSyntheticEthernetPortEntry 8 }

msvmsepCreationClassName OBJECT-TYPE
    SYNTAX     WtcsDisplayString (SIZE (0..256))
    MAX-ACCESS read-only
    STATUS     current
    DESCRIPTION
        "CreationClassName indicates the name of the class
        or the subclass used in the creation of an
        instance. When used with the other key properties
        of this class, this property allows all instances
        of this class and its subclasses to be uniquely
        identified."
    ::= { msvmSyntheticEthernetPortEntry 9 }

msvmsepDescription OBJECT-TYPE
    SYNTAX     WtcsDisplayString
    MAX-ACCESS read-only
    STATUS     current
    DESCRIPTION
        "The Description property provides a textual
        description of the object."
    ::= { msvmSyntheticEthernetPortEntry 10 }

msvmsepDeviceID OBJECT-TYPE
    SYNTAX     WtcsDisplayString (SIZE (0..64))
    MAX-ACCESS read-only
    STATUS     current
    DESCRIPTION
        "An address or other identifying information used
        to uniquely name the LogicalDevice."
    ::= { msvmSyntheticEthernetPortEntry 11 }

msvmsepElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmSyntheticEthernetPortEntry 12 }

msvmsepEnabledCapabilities OBJECT-TYPE
    SYNTAX     INTEGER {
        unknown(0),
        other(1),
        alertOnLan(2),
        wakeOnLan(3),
        failOver(4),
        loadBalancing(5)
    }
    MAX-ACCESS read-only
    STATUS     current
    DESCRIPTION
        "Specifies which capabilities are enabled from the
        list of all supported ones, which are defined in
        the Capabilities array."
    ::= { msvmSyntheticEthernetPortEntry 13 }

msvmsepEnabledDefault OBJECT-TYPE
    SYNTAX     INTEGER {
        enabled(2),
        disabled(3),
        notApplicable(5),
        enabledbutOffline(6),
        noDefault(7)
    }
    MAX-ACCESS read-only
    STATUS     current
    DESCRIPTION
        "An enumerated value indicating an administrator's
        default or startup configuration for the Enabled
        State of an element. By default, the element is
        'Enabled' (value=2)."
    ::= { msvmSyntheticEthernetPortEntry 14 }

msvmsepEnabledState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "EnabledState is an integer enumeration that
        indicates the enabled and disabled states of an
        element. It can also indicate the transitions
        between these requested states. For example,
        shutting down (value=4) and starting (value=10) are
        transient states between enabled and disabled. The
        following text briefly summarizes the various
        enabled and disabled states: 
        Enabled (2) indicates that the element is or could
        be executing commands, will process any queued
        commands, and queues new requests. 
        Disabled (3) indicates that the element will not
        execute commands and will drop any new requests. 
        Shutting Down (4) indicates that the element is in
        the process of going to a Disabled state. 
        Not Applicable (5) indicates the element does not
        support being enabled or disabled. 
        Enabled but Offline (6) indicates that the element
        might be completing commands, and will drop any new
        requests. 
        Test (7) indicates that the element is in a test
        state. 
        Deferred (8) indicates that the element might be
        completing commands, but will queue any new
        requests. 
        Quiesce (9) indicates that the element is enabled
        but in a restricted mode. The behavior of the
        element is similar to the Enabled state, but it
        processes only a restricted set of commands. All
        other requests are queued. 
        Starting (10) indicates that the element is in the
        process of going to an Enabled state. New requests
        are queued."
    ::= { msvmSyntheticEthernetPortEntry 15 }

msvmsepErrorCleared OBJECT-TYPE
    SYNTAX     TruthValue
    MAX-ACCESS read-only
    STATUS     current
    DESCRIPTION
        "Note: The use of this method is deprecated. 
        Deprecated description: ErrorCleared is a Boolean
        property that indicates that the error reported in
        LastErrorCode is now cleared."
    ::= { msvmSyntheticEthernetPortEntry 16 }

msvmsepErrorDescription OBJECT-TYPE
    SYNTAX     WtcsDisplayString
    MAX-ACCESS read-only
    STATUS     current
    DESCRIPTION
        "Note: The use of this method is deprecated. 
        Deprecated description: ErrorDescription is a
        free-form string that supplies more information
        about the error recorded in LastErrorCode and
        information on any corrective actions that can be
        taken."
    ::= { msvmSyntheticEthernetPortEntry 17 }

msvmsepFullDuplex OBJECT-TYPE
    SYNTAX     TruthValue
    MAX-ACCESS read-only
    STATUS     current
    DESCRIPTION
        "Boolean that indicates that the port is operating
        in full duplex mode."
    ::= { msvmSyntheticEthernetPortEntry 18 }

msvmsepHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmSyntheticEthernetPortEntry 19 }

msvmsepIdentifyingDescriptions OBJECT-TYPE
    SYNTAX     WtcsDisplayString
    MAX-ACCESS read-only
    STATUS     current
    DESCRIPTION
        "An array of free-form strings providing
        explanations and details behind the entries in the
        OtherIdentifyingInfo array. Note that each entry of
        this array is related to the entry in
        OtherIdentifyingInfo that is located at the same
        index."
    ::= { msvmSyntheticEthernetPortEntry 20 }

msvmsepInstallDate OBJECT-TYPE
    SYNTAX     DateAndTime
    MAX-ACCESS read-only
    STATUS     current
    DESCRIPTION
        "A datetime value that indicates when the object
        was installed. Lack of a value does not indicate
        that the object is not installed."
    ::= { msvmSyntheticEthernetPortEntry 21 }

msvmsepLastErrorCode OBJECT-TYPE
    SYNTAX     Gauge32
    MAX-ACCESS read-only
    STATUS     current
    DESCRIPTION
        "Note: The use of this method is deprecated. 
        Deprecated description: LastErrorCode captures the
        last error code reported by the LogicalDevice."
    ::= { msvmSyntheticEthernetPortEntry 22 }

msvmsepLinkTechnology OBJECT-TYPE
    SYNTAX     INTEGER {
        unknown(0),
        other(1),
        ethernet(2),
        ib(3),
        fc(4),
        fddi(5),
        atm(6),
        tokenRing(7),
        frameRelay(8),
        infrared(9),
        blueTooth(10),
        wirelessLAN(11)
    }
    MAX-ACCESS read-only
    STATUS     current
    DESCRIPTION
        "An enumeration of the types of links. When set to
        1 ('Other'), the related property
        OtherLinkTechnology contains a string description
        of the type of link."
    ::= { msvmSyntheticEthernetPortEntry 23 }

msvmsepLocationIndicator OBJECT-TYPE
    SYNTAX     INTEGER {
        unknown(0),
        on(2),
        off(3),
        notSupported(4)
    }
    MAX-ACCESS read-only
    STATUS     current
    DESCRIPTION
        "An integer that reflects the state of an indicator
        (e.g., LED) that is part of a device. Reading the
        value gives the current state. Writing the value
        with 'On'/'Off' turns the indicator on/off, other
        values may not be written."
    ::= { msvmSyntheticEthernetPortEntry 24 }

msvmsepMaxDataSize OBJECT-TYPE
    SYNTAX     Gauge32
    MAX-ACCESS read-only
    STATUS     current
    DESCRIPTION
        "The maximum size of the INFO (non-MAC) field that
        will be received or transmitted."
    ::= { msvmSyntheticEthernetPortEntry 25 }

msvmsepMaxQuiesceTime OBJECT-TYPE
    SYNTAX     Gauge32
    UNITS "MilliSeconds"
    MAX-ACCESS read-only
    STATUS     current
    DESCRIPTION
        "Note: The use of this property has been
        deprecated. When evaluating the use of Quiesce, it
        was determined that this single property is not
        adequate for describing when a device will
        automatically exit a quiescent state. In fact, the
        most likely scenario for a device to exit a
        quiescent state was determined to be based on the
        number of outstanding requests queued rather than
        on a maximum time. This decision will be
        re-evaluated and repositioned later. 
        Deprecated description: Maximum time, in
        milliseconds, that a Device can run in a 'Quiesced'
        state. The state is defined in its Availability and
        AdditionalAvailability properties, where 'Quiesced'
        is conveyed by the value 21. What occurs at the end
        of the time limit is device-specific. The Device
        can unquiesce, can be offline, or can take other
        actions. A value of 0 indicates that a Device can
        remain quiesced indefinitely."
    ::= { msvmSyntheticEthernetPortEntry 26 }

msvmsepMaxSpeed OBJECT-TYPE
    SYNTAX     Gauge32
    UNITS "Bits per Second"
    MAX-ACCESS read-only
    STATUS     current
    DESCRIPTION
        "The maximum bandwidth of the Port in Bits per
        Second."
    ::= { msvmSyntheticEthernetPortEntry 27 }

msvmsepName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmSyntheticEthernetPortEntry 28 }

msvmsepNetworkAddresses OBJECT-TYPE
    SYNTAX     WtcsDisplayString (SIZE (0..64))
    MAX-ACCESS read-only
    STATUS     current
    DESCRIPTION
        "An array of strings that indicates the network
        addresses for the port."
    ::= { msvmSyntheticEthernetPortEntry 29 }

msvmsepOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmSyntheticEthernetPortEntry 30 }

msvmsepOtherEnabledCapabilities OBJECT-TYPE
    SYNTAX     WtcsDisplayString
    MAX-ACCESS read-only
    STATUS     current
    DESCRIPTION
        "An array of free-form strings that provides more
        detailed explanations for any of the enabled
        capabilities that are specified as 'Other'."
    ::= { msvmSyntheticEthernetPortEntry 31 }

msvmsepOtherEnabledState OBJECT-TYPE
    SYNTAX     WtcsDisplayString
    MAX-ACCESS read-only
    STATUS     current
    DESCRIPTION
        "A string that describes the enabled or disabled
        state of the element when the EnabledState property
        is set to 1 ('Other'). This property must be set to
        null when EnabledState is any value other than 1."
    ::= { msvmSyntheticEthernetPortEntry 32 }

msvmsepOtherIdentifyingInfo OBJECT-TYPE
    SYNTAX     WtcsDisplayString (SIZE (0..256))
    MAX-ACCESS read-only
    STATUS     current
    DESCRIPTION
        "OtherIdentifyingInfo captures data, in addition to
        DeviceID information, that could be used to
        identify a LogicalDevice. For example, you could
        use this property to hold the operating system's
        user-friendly name for the Device."
    ::= { msvmSyntheticEthernetPortEntry 33 }

msvmsepOtherLinkTechnology OBJECT-TYPE
    SYNTAX     WtcsDisplayString
    MAX-ACCESS read-only
    STATUS     current
    DESCRIPTION
        "A string value that describes LinkTechnology when
        it is set to 1, 'Other'."
    ::= { msvmSyntheticEthernetPortEntry 34 }

msvmsepOtherNetworkPortType OBJECT-TYPE
    SYNTAX     WtcsDisplayString
    MAX-ACCESS read-only
    STATUS     current
    DESCRIPTION
        "Note: The use of this property is deprecated in
        lieu of CIM_LogicalPort.PortType. 
        Deprecated description: The type of module, when
        PortType is set to 1 ('Other'.)"
    ::= { msvmSyntheticEthernetPortEntry 35 }

msvmsepOtherPortType OBJECT-TYPE
    SYNTAX     WtcsDisplayString
    MAX-ACCESS read-only
    STATUS     current
    DESCRIPTION
        "Describes the type of module, when PortType is set
        to 1 ('Other')."
    ::= { msvmSyntheticEthernetPortEntry 36 }

msvmsepPermanentAddress OBJECT-TYPE
    SYNTAX     WtcsDisplayString (SIZE (0..64))
    MAX-ACCESS read-only
    STATUS     current
    DESCRIPTION
        "PermanentAddress defines the network address that
        is hardcoded into a port. This 'hardcoded' address
        can be changed using a firmware upgrade or a
        software configuration. When this change is made,
        the field should be updated at the same time.
        PermanentAddress should be left blank if no
        'hardcoded' address exists for the NetworkAdapter."
    ::= { msvmSyntheticEthernetPortEntry 37 }

msvmsepPortNumber OBJECT-TYPE
    SYNTAX     Integer32
    MAX-ACCESS read-only
    STATUS     current
    DESCRIPTION
        "NetworkPorts are often numbered relative to either
        a logical module or a network element."
    ::= { msvmSyntheticEthernetPortEntry 38 }

msvmsepPortType OBJECT-TYPE
    SYNTAX     INTEGER {
        unknown(0),
        other(1),
        notApplicable(2)
    }
    MAX-ACCESS read-only
    STATUS     current
    DESCRIPTION
        "PortType is defined to force consistent naming of
        the 'type' property in subclasses and to guarantee
        unique enum values for all instances of
        NetworkPort. When set to 1 ('Other'), related
        property OtherPortType contains a string
        description of the type of port. A range of values,
        DMTF_Reserved, has been defined that allows
        subclasses to override and define their specific
        types of ports."
    ::= { msvmSyntheticEthernetPortEntry 39 }

msvmsepPowerManagementCapability OBJECT-TYPE
    SYNTAX     INTEGER {
        unknown(0),
        notSupported(1),
        disabled(2),
        enabled(3),
        powerSavingModesEnteredAutomatic(4),
        powerStateSettable(5),
        powerCyclingSupported(6),
        timedPowerOnSupported(7)
    }
    MAX-ACCESS read-only
    STATUS     current
    DESCRIPTION
        "Note: The use of this property has been
        deprecated. Instead, use the PowerCapabilites
        property in an associated
        PowerManagementCapabilities class. Deprecated
        description: An enumerated array describing the
        power management capabilities of the Device."
    ::= { msvmSyntheticEthernetPortEntry 40 }

msvmsepPowerManagementSupported OBJECT-TYPE
    SYNTAX     TruthValue
    MAX-ACCESS read-only
    STATUS     current
    DESCRIPTION
        "Note: The use of this property has been
        deprecated. Instead, the existence of an associated
        PowerManagementCapabilities class (associated using
        the ElementCapabilities relationship) indicates
        that power management is supported. Deprecated
        description: Boolean that indicates that the Device
        can use power management."
    ::= { msvmSyntheticEthernetPortEntry 41 }

msvmsepPowerOnHours OBJECT-TYPE
    SYNTAX     Gauge32
    UNITS "Hours"
    MAX-ACCESS read-only
    STATUS     current
    DESCRIPTION
        "Note: The use of this method is deprecated. 
        Deprecated description: The number of consecutive
        hours that this Device has been powered on since
        its last power cycle."
    ::= { msvmSyntheticEthernetPortEntry 42 }

msvmsepRequestedSpeed OBJECT-TYPE
    SYNTAX     Gauge32
    UNITS "Bits per Second"
    MAX-ACCESS read-only
    STATUS     current
    DESCRIPTION
        "The requested bandwidth of the Port in Bits per
        Second. The actual bandwidth is reported in
        LogicalPort.Speed."
    ::= { msvmSyntheticEthernetPortEntry 43 }

msvmsepRequestedState OBJECT-TYPE
    SYNTAX     INTEGER {
        enabled(2),
        disabled(3),
        shutDown(4),
        noChange(5),
        offline(6),
        test(7),
        deferred(8),
        quiesce(9),
        reboot(10),
        reset(11),
        notApplicable(12)
    }
    MAX-ACCESS read-only
    STATUS     current
    DESCRIPTION
        "RequestedState is an integer enumeration that
        indicates the last requested or desired state for
        the element. The actual state of the element is
        represented by EnabledState. This property is
        provided to compare the last requested and current
        enabled or disabled states. Note that when
        EnabledState is set to 5 ('Not Applicable'), then
        this property has no meaning. By default, the
        RequestedState of the element is 5 ('No Change').
        Refer to the EnabledState property description for
        explanations of the values in the RequestedState
        enumeration. 
        
        It should be noted that there are two new values in
        RequestedState that build on the statuses of
        EnabledState. These are 'Reboot' (10) and 'Reset'
        (11). Reboot refers to doing a 'Shut Down' and then
        moving to an 'Enabled' state. Reset indicates that
        the element is first 'Disabled' and then 'Enabled'.
        The distinction between requesting 'Shut Down' and
        'Disabled' should also be noted. Shut Down requests
        an orderly transition to the Disabled state, and
        might involve removing power, to completely erase
        any existing state. The Disabled state requests an
        immediate disabling of the element, such that it
        will not execute or accept any commands or
        processing requests. 
        
        This property is set as the result of a method
        invocation (such as Start or StopService on
        CIM_Service), or can be overridden and defined as
        WRITEable in a subclass. The method approach is
        considered superior to a WRITEable property,
        because it allows an explicit invocation of the
        operation and the return of a result code. 
        
        A particular instance of EnabledLogicalElement
        might not support RequestedStateChange. If this
        occurs, the value 12 ('Not Applicable') is used."
    ::= { msvmSyntheticEthernetPortEntry 44 }

msvmsepSpeed OBJECT-TYPE
    SYNTAX     Gauge32
    UNITS "Bits per Second"
    MAX-ACCESS read-only
    STATUS     current
    DESCRIPTION
        "The bandwidth of the Port in Bits per Second."
    ::= { msvmSyntheticEthernetPortEntry 45 }

msvmsepStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmSyntheticEthernetPortEntry 46 }

msvmsepStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmSyntheticEthernetPortEntry 47 }

msvmsepStatusInfo OBJECT-TYPE
    SYNTAX     INTEGER {
        other(1),
        unknown(2),
        enabled(3),
        disabled(4),
        notApplicable(5)
    }
    MAX-ACCESS read-only
    STATUS     current
    DESCRIPTION
        "Note: The use of this method is deprecated in lieu
        of a more clearly named property (EnabledState)
        that is inherited from ManagedSystemElement and
        that has additional enumerated values. 
        Deprecated description: The StatusInfo property
        indicates whether the Logical Device is in an
        enabled state (value=3), disabled state (value=4),
        some other state (value=1), or an unknown state
        (value=2). If this property does not apply to the
        LogicalDevice, the value 5 ('Not Applicable')
        should be used. If a Device is
        ('Enabled')(value=3), it has been powered up and is
        configured and operational. The Device might or
        might not be functionally active, depending on
        whether its Availability (or
        AdditionalAvailability) indicates that it is
        ('Running/Full Power')(value=3) or ('Off line')
        (value=8). In an enabled but offline mode, a Device
        might be performing out-of-band requests, such as
        running Diagnostics. If StatusInfo is ('Disabled')
        (value=4), a Device can only be 'enabled' or
        powered off. In a personal computer environment,
        ('Disabled') means that the driver of the device is
        not available in the stack. In other environments,
        a Device can be disabled by removing its
        configuration file. A disabled device is physically
        present in a System and consuming resources, but it
        cannot be communicated with until a driver is
        loaded, a configuration file is loaded, or some
        other 'enabling' activity has occurred."
    ::= { msvmSyntheticEthernetPortEntry 48 }

msvmsepSupportedMaxTransmitUnit OBJECT-TYPE
    SYNTAX     Gauge32
    UNITS "Bytes"
    MAX-ACCESS read-only
    STATUS     current
    DESCRIPTION
        "The maximum transmission unit (MTU) that can be
        supported."
    ::= { msvmSyntheticEthernetPortEntry 49 }

msvmsepSystemCreationClassName OBJECT-TYPE
    SYNTAX     WtcsDisplayString (SIZE (0..256))
    MAX-ACCESS read-only
    STATUS     current
    DESCRIPTION
        "The CreationClassName of the scoping system."
    ::= { msvmSyntheticEthernetPortEntry 50 }

msvmsepSystemName OBJECT-TYPE
    SYNTAX     WtcsDisplayString (SIZE (0..256))
    MAX-ACCESS read-only
    STATUS     current
    DESCRIPTION
        "The System Name of the scoping system."
    ::= { msvmSyntheticEthernetPortEntry 51 }

msvmsepTimeOfLastStateChange OBJECT-TYPE
    SYNTAX     DateAndTime
    MAX-ACCESS read-only
    STATUS     current
    DESCRIPTION
        "The date or time when the EnabledState of the
        element last changed. If the state of the element
        has not changed and this property is populated,
        then it must be set to a 0 interval value. If a
        state change was requested, but rejected or not yet
        processed, the property must not be updated."
    ::= { msvmSyntheticEthernetPortEntry 52 }

msvmsepTotalPowerOnHours OBJECT-TYPE
    SYNTAX     Gauge32
    UNITS "Hours"
    MAX-ACCESS read-only
    STATUS     current
    DESCRIPTION
        "Note: The use of this method is deprecated. 
        Deprecated description: The total number of hours
        that this Device has been powered on."
    ::= { msvmSyntheticEthernetPortEntry 53 }

msvmsepUsageRestriction OBJECT-TYPE
    SYNTAX     INTEGER {
        unknown(0),
        frontendonly(2),
        backendonly(3),
        notrestricted(4)
    }
    MAX-ACCESS read-only
    STATUS     current
    DESCRIPTION
        "In some circumstances, a LogicalPort might be
        identifiable as a front end or back end port. An
        example of this situation would be a storage array
        that might have back end ports to communicate with
        disk drives and front end ports to communicate with
        hosts. If there is no restriction on the use of the
        port, then the value should be set to 'not
        restricted'."
    ::= { msvmSyntheticEthernetPortEntry 54 }

msvmSyntheticEthernetPortDtTable OBJECT-TYPE
    SYNTAX     SEQUENCE OF MsvmSyntheticEthernetPortSetData
    MAX-ACCESS not-accessible
    STATUS     current
    DESCRIPTION
        "Represents the configured state of a synthetic
        Ethernet adapter."
    ::= { msvmNetworking 19 }

msvmSyntheticEthernetPortDtEntry OBJECT-TYPE
    SYNTAX     MsvmSyntheticEthernetPortSetData
    MAX-ACCESS not-accessible
    STATUS     current
    DESCRIPTION
        "None"
    INDEX      { msvmsepsdIndex }
    ::= { msvmSyntheticEthernetPortDtTable 1 }

MsvmSyntheticEthernetPortSetData ::= SEQUENCE {
    msvmsepsdIndex Integer32,
    msvmsepsdAddress WtcsDisplayString,
    msvmsepsdAllocationUnits WtcsDisplayString,
    msvmsepsdAutomaticAllocation TruthValue,
    msvmsepsdAutomaticDeallocation TruthValue,
    msvmsepsdCaption WtcsDisplayString,
    msvmsepsdConnection WtcsDisplayString,
    msvmsepsdResourceType INTEGER,
    msvmsepsdStaticMacAddress TruthValue,
    msvmsepsdVirtualQuantity Gauge32,
    msvmsepsdVirtualSystemIdentifier WtcsDisplayString,
    msvmsepsdWeight Gauge32
}

msvmsepsdIndex OBJECT-TYPE
    SYNTAX     Integer32 (1..2147483647)
    MAX-ACCESS read-only
    STATUS     current
    DESCRIPTION
        "The value of this object uniquely identifies the
        instance entry for this class."
    ::= { msvmSyntheticEthernetPortDtEntry 1 }

msvmsepsdAddress OBJECT-TYPE
    SYNTAX     WtcsDisplayString
    MAX-ACCESS read-only
    STATUS     current
    DESCRIPTION
        "The address of the resource.For example, the MAC
        address of a Ethernet port."
    ::= { msvmSyntheticEthernetPortDtEntry 2 }

msvmsepsdAllocationUnits OBJECT-TYPE
    SYNTAX     WtcsDisplayString
    MAX-ACCESS read-only
    STATUS     current
    DESCRIPTION
        "This property specifies the units of allocation
        used by the Reservation and Limit properties.  For
        example, when ResourceType=Processor,
        AllocationUnits may be set to MHZ. When
        ResourceType=Memory, AllocationUnits may be set to
        MB"
    ::= { msvmSyntheticEthernetPortDtEntry 3 }

msvmsepsdAutomaticAllocation OBJECT-TYPE
    SYNTAX     TruthValue
    MAX-ACCESS read-only
    STATUS     current
    DESCRIPTION
        "This property specifies if the resource will be
        automatically allocated.  For example when set to
        true, when the consuming virtual computer system is
        powered on, this resource would be allocated.  A
        value of false indicates the resource must be
        explicitly allocated.  For example, the setting may
        represent removable media (cdrom, floppy, etc.)
        where at power on time, the media isnot present. 
        An explicit operation is required to allocate the
        resource."
    ::= { msvmSyntheticEthernetPortDtEntry 4 }

msvmsepsdAutomaticDeallocation OBJECT-TYPE
    SYNTAX     TruthValue
    MAX-ACCESS read-only
    STATUS     current
    DESCRIPTION
        "This property specifies if the resource will be
        automatically de-allocated.  For example, when set
        to true, when the consuming virtual computer system
        is powered off, this resource would be
        de-allocated.  When set to false, the resource will
        remain allocated and must be explicitly
        de-allocated."
    ::= { msvmSyntheticEthernetPortDtEntry 5 }

msvmsepsdCaption OBJECT-TYPE
    SYNTAX     WtcsDisplayString (SIZE (0..64))
    MAX-ACCESS read-only
    STATUS     current
    DESCRIPTION
        "The Caption property is a short textual
        description (one- line string) of the object."
    ::= { msvmSyntheticEthernetPortDtEntry 6 }

msvmsepsdConnection OBJECT-TYPE
    SYNTAX     WtcsDisplayString
    MAX-ACCESS read-only
    STATUS     current
    DESCRIPTION
        "The thing to which this resource is connected. 
        For example, a named network or switch port."
    ::= { msvmSyntheticEthernetPortDtEntry 7 }

msvmsepsdResourceType OBJECT-TYPE
    SYNTAX     INTEGER {
        other(1),
        computerSystem(2),
        processor(3),
        memory(4),
        ideController(5),
        parallelSCSIHBA(6),
        fcHBA(7),
        iSCSIHBA(8),
        ibHCA(9),
        ethernetAdapter(10),
        iOSlot(11),
        iODevice(12),
        floppyDrive(13),
        cdDrive(14),
        dvddrive(15),
        serialport(16),
        parallelport(17),
        usbController(18),
        graphicscontroller(19),
        storageExtent(20),
        disk(21),
        tape(22),
        otherstoragedevice(23),
        firewireController(24),
        partitionableUnit(25),
        basePartitionableUnit(26),
        powerSupply(27),
        coolingDevice(28),
        dmtfreserved(29)
    }
    MAX-ACCESS read-only
    STATUS     current
    DESCRIPTION
        "The type of resource this allocation setting
        represents."
    ::= { msvmSyntheticEthernetPortDtEntry 20 }

msvmsepsdStaticMacAddress OBJECT-TYPE
    SYNTAX     TruthValue
    MAX-ACCESS read-only
    STATUS     current
    DESCRIPTION
        "Indicates whether the MAC address is static or
        dynamic."
    ::= { msvmSyntheticEthernetPortDtEntry 21 }

msvmsepsdVirtualQuantity OBJECT-TYPE
    SYNTAX     Gauge32
    MAX-ACCESS read-only
    STATUS     current
    DESCRIPTION
        "This property specifies the quantity of resources
        presented to the consumer.  For example, when
        ResourceType=Processor,  this property would
        reflect the number of discrete Processors presented
        to the virtual computer system.  When
        ResourceType=Memory, this property could reflect
        the number of MB reported to the virtual computer
        system."
    ::= { msvmSyntheticEthernetPortDtEntry 22 }

msvmsepsdVirtualSystemIdentifier OBJECT-TYPE
    SYNTAX     WtcsDisplayString
    MAX-ACCESS read-only
    STATUS     current
    DESCRIPTION
        "A freeform string array of identifiers of this
        resource presented to the virtual computer system's
        operating system. The indexes and values per index
        are defined on a per resource basis (that is, for
        each enumerated ResourceType value). This property
        is inherited from
        Msvm_SyntheticEthernetPortSettingData and is always
        set to '<GUID>'."
    ::= { msvmSyntheticEthernetPortDtEntry 23 }

msvmsepsdWeight OBJECT-TYPE
    SYNTAX     Gauge32
    MAX-ACCESS read-only
    STATUS     current
    DESCRIPTION
        "This property specifies a relative priority for
        this allocation in relation to other allocations
        from the same ResourcePool.  This property has no
        unit of measure, and is only relevant when compared
        to other allocations vying for the same host
        resources."
    ::= { msvmSyntheticEthernetPortDtEntry 24 }

msvmTransparentBridgeDynFwdTable OBJECT-TYPE
    SYNTAX     SEQUENCE OF MsvmTransparentBridgeDynamicFwd
    MAX-ACCESS not-accessible
    STATUS     current
    DESCRIPTION
        "Connects a transparent bridging service to a
        dynamic forward entry (learned MAC address)."
    ::= { msvmNetworking 20 }

msvmTransparentBridgeDynFwdEntry OBJECT-TYPE
    SYNTAX     MsvmTransparentBridgeDynamicFwd
    MAX-ACCESS not-accessible
    STATUS     current
    DESCRIPTION
        "None"
    INDEX      { msvmtbdfIndex }
    ::= { msvmTransparentBridgeDynFwdTable 1 }

MsvmTransparentBridgeDynamicFwd ::= SEQUENCE {
    msvmtbdfIndex Integer32,
    msvmtbdfAntecedent WtcsDisplayString,
    msvmtbdfDependent WtcsDisplayString
}

msvmtbdfIndex OBJECT-TYPE
    SYNTAX     Integer32 (1..2147483647)
    MAX-ACCESS read-only
    STATUS     current
    DESCRIPTION
        "The value of this object uniquely identifies the
        instance entry for this class."
    ::= { msvmTransparentBridgeDynFwdEntry 1 }

msvmtbdfAntecedent OBJECT-TYPE
    SYNTAX     WtcsDisplayString
    MAX-ACCESS read-only
    STATUS     current
    DESCRIPTION
        "Antecedent represents the independent object in
        this association."
    ::= { msvmTransparentBridgeDynFwdEntry 2 }

msvmtbdfDependent OBJECT-TYPE
    SYNTAX     WtcsDisplayString
    MAX-ACCESS read-only
    STATUS     current
    DESCRIPTION
        "Dependent represents the object that is dependent
        on the Antecedent."
    ::= { msvmTransparentBridgeDynFwdEntry 3 }

msvmTransparentBridgingSvcTable OBJECT-TYPE
    SYNTAX     SEQUENCE OF MsvmTransparentBridgingService
    MAX-ACCESS not-accessible
    STATUS     current
    DESCRIPTION
        "Serves as a placeholder for the service inside the
        switch that learns MAC addresses."
    ::= { msvmNetworking 21 }

msvmTransparentBridgingSvcEntry OBJECT-TYPE
    SYNTAX     MsvmTransparentBridgingService
    MAX-ACCESS not-accessible
    STATUS     current
    DESCRIPTION
        "None"
    INDEX      { msvmtbsIndex }
    ::= { msvmTransparentBridgingSvcTable 1 }

MsvmTransparentBridgingService ::= SEQUENCE {
    msvmtbsIndex Integer32,
    msvmtbsAgingTime Gauge32,
    msvmtbsCaption WtcsDisplayString,
    msvmtbsCreationClassName WtcsDisplayString,
    msvmtbsDescription WtcsDisplayString,
    msvmtbsElementName WtcsDisplayString,
    msvmtbsEnabledDefault INTEGER,
    msvmtbsEnabledState INTEGER,
    msvmtbsFID Gauge32,
    msvmtbsHealthState INTEGER,
    msvmtbsInstallDate DateAndTime,
    msvmtbsKeywords WtcsDisplayString,
    msvmtbsName WtcsDisplayString,
    msvmtbsOperationalStatus INTEGER,
    msvmtbsOtherEnabledState WtcsDisplayString,
    msvmtbsOtherProtocolType WtcsDisplayString,
    msvmtbsPrimaryOwnerContact WtcsDisplayString,
    msvmtbsPrimaryOwnerName WtcsDisplayString,
    msvmtbsProtocolType INTEGER,
    msvmtbsRequestedState INTEGER,
    msvmtbsServiceURL WtcsDisplayString,
    msvmtbsStartMode WtcsDisplayString,
    msvmtbsStarted TruthValue,
    msvmtbsStartupConditions WtcsDisplayString,
    msvmtbsStartupParameters WtcsDisplayString,
    msvmtbsStatus WtcsDisplayString,
    msvmtbsStatusDescriptions WtcsDisplayString,
    msvmtbsSystemCreationClassName WtcsDisplayString,
    msvmtbsSystemName WtcsDisplayString,
    msvmtbsTimeOfLastStateChange DateAndTime
}

msvmtbsIndex OBJECT-TYPE
    SYNTAX     Integer32 (1..2147483647)
    MAX-ACCESS read-only
    STATUS     current
    DESCRIPTION
        "The value of this object uniquely identifies the
        instance entry for this class."
    ::= { msvmTransparentBridgingSvcEntry 1 }

msvmtbsAgingTime OBJECT-TYPE
    SYNTAX     Gauge32
    UNITS "Seconds"
    MAX-ACCESS read-only
    STATUS     current
    DESCRIPTION
        "The timeout period in seconds for aging out
        dynamically learned forwarding information.
        802.1D-1990 recommends a default of 300 seconds."
    ::= { msvmTransparentBridgingSvcEntry 2 }

msvmtbsCaption OBJECT-TYPE
    SYNTAX     WtcsDisplayString (SIZE (0..64))
    MAX-ACCESS read-only
    STATUS     current
    DESCRIPTION
        "The Caption property is a short textual
        description (one- line string) of the object."
    ::= { msvmTransparentBridgingSvcEntry 3 }

msvmtbsCreationClassName OBJECT-TYPE
    SYNTAX     WtcsDisplayString (SIZE (0..256))
    MAX-ACCESS read-only
    STATUS     current
    DESCRIPTION
        "CreationClassName indicates the name of the class
        or the subclass that is used in the creation of an
        instance. When used with the other key properties
        of this class, this property allows all instances
        of this class and its subclasses to be uniquely
        identified."
    ::= { msvmTransparentBridgingSvcEntry 4 }

msvmtbsDescription OBJECT-TYPE
    SYNTAX     WtcsDisplayString
    MAX-ACCESS read-only
    STATUS     current
    DESCRIPTION
        "The Description property provides a textual
        description of the object."
    ::= { msvmTransparentBridgingSvcEntry 5 }

msvmtbsElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmTransparentBridgingSvcEntry 6 }

msvmtbsEnabledDefault OBJECT-TYPE
    SYNTAX     INTEGER {
        enabled(2),
        disabled(3),
        notApplicable(5),
        enabledbutOffline(6),
        noDefault(7)
    }
    MAX-ACCESS read-only
    STATUS     current
    DESCRIPTION
        "An enumerated value indicating an administrator's
        default or startup configuration for the Enabled
        State of an element. By default, the element is
        'Enabled' (value=2)."
    ::= { msvmTransparentBridgingSvcEntry 7 }

msvmtbsEnabledState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "EnabledState is an integer enumeration that
        indicates the enabled and disabled states of an
        element. It can also indicate the transitions
        between these requested states. For example,
        shutting down (value=4) and starting (value=10) are
        transient states between enabled and disabled. The
        following text briefly summarizes the various
        enabled and disabled states: 
        Enabled (2) indicates that the element is or could
        be executing commands, will process any queued
        commands, and queues new requests. 
        Disabled (3) indicates that the element will not
        execute commands and will drop any new requests. 
        Shutting Down (4) indicates that the element is in
        the process of going to a Disabled state. 
        Not Applicable (5) indicates the element does not
        support being enabled or disabled. 
        Enabled but Offline (6) indicates that the element
        might be completing commands, and will drop any new
        requests. 
        Test (7) indicates that the element is in a test
        state. 
        Deferred (8) indicates that the element might be
        completing commands, but will queue any new
        requests. 
        Quiesce (9) indicates that the element is enabled
        but in a restricted mode. The behavior of the
        element is similar to the Enabled state, but it
        processes only a restricted set of commands. All
        other requests are queued. 
        Starting (10) indicates that the element is in the
        process of going to an Enabled state. New requests
        are queued."
    ::= { msvmTransparentBridgingSvcEntry 8 }

msvmtbsFID OBJECT-TYPE
    SYNTAX     Gauge32
    MAX-ACCESS read-only
    STATUS     current
    DESCRIPTION
        "Filtering Database Identifier used by VLAN-aware
        switches that have more than one filtering
        database."
    ::= { msvmTransparentBridgingSvcEntry 9 }

msvmtbsHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmTransparentBridgingSvcEntry 10 }

msvmtbsInstallDate OBJECT-TYPE
    SYNTAX     DateAndTime
    MAX-ACCESS read-only
    STATUS     current
    DESCRIPTION
        "A datetime value that indicates when the object
        was installed. Lack of a value does not indicate
        that the object is not installed."
    ::= { msvmTransparentBridgingSvcEntry 11 }

msvmtbsKeywords OBJECT-TYPE
    SYNTAX     WtcsDisplayString
    MAX-ACCESS read-only
    STATUS     current
    DESCRIPTION
        "This is a free-form array of strings that provide
        descriptive words and phrases that can be used in
        queries. To-date, this property has not been
        implemented, since it is not standardized. Also, if
        this was a necessary query construct, then it would
        be required higher in the inheritance hierarchy.
        The latter has not proven necessary. Therefore, the
        property is deprecated."
    ::= { msvmTransparentBridgingSvcEntry 12 }

msvmtbsName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmTransparentBridgingSvcEntry 13 }

msvmtbsOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmTransparentBridgingSvcEntry 14 }

msvmtbsOtherEnabledState OBJECT-TYPE
    SYNTAX     WtcsDisplayString
    MAX-ACCESS read-only
    STATUS     current
    DESCRIPTION
        "A string that describes the enabled or disabled
        state of the element when the EnabledState property
        is set to 1 ('Other'). This property must be set to
        null when EnabledState is any value other than 1."
    ::= { msvmTransparentBridgingSvcEntry 15 }

msvmtbsOtherProtocolType OBJECT-TYPE
    SYNTAX     WtcsDisplayString (SIZE (0..32))
    MAX-ACCESS read-only
    STATUS     current
    DESCRIPTION
        "This defines the type of protocol that is being
        forwarded when the value of the ProtocolType
        attribute is 1 (i.e., 'Other'). This provides for
        future extensibility."
    ::= { msvmTransparentBridgingSvcEntry 16 }

msvmtbsPrimaryOwnerContact OBJECT-TYPE
    SYNTAX     WtcsDisplayString (SIZE (0..256))
    MAX-ACCESS read-only
    STATUS     current
    DESCRIPTION
        "A string that provides information on how the
        primary owner of the Service can be reached (for
        example, phone number, e-mail address, and so on)."
    ::= { msvmTransparentBridgingSvcEntry 17 }

msvmtbsPrimaryOwnerName OBJECT-TYPE
    SYNTAX     WtcsDisplayString (SIZE (0..64))
    MAX-ACCESS read-only
    STATUS     current
    DESCRIPTION
        "The name of the primary owner for the service, if
        one is defined. The primary owner is the initial
        support contact for the Service."
    ::= { msvmTransparentBridgingSvcEntry 18 }

msvmtbsProtocolType OBJECT-TYPE
    SYNTAX     INTEGER {
        unknown(0),
        other(1),
        ipv4(2),
        ipv6(3),
        ipv4IPv6(4),
        ipx(5),
        appleTalk(6),
        decnet(7),
        sna(8),
        conp(9),
        clnp(10),
        vines(11),
        xns(12),
        atm(13),
        frameRelay(14),
        ethernet(15),
        tokenRing(16),
        fddi(17),
        infiniband(18),
        fibreChannel(19)
    }
    MAX-ACCESS read-only
    STATUS     current
    DESCRIPTION
        "This defines the type of protocol that is being
        forwarded."
    ::= { msvmTransparentBridgingSvcEntry 19 }

msvmtbsRequestedState OBJECT-TYPE
    SYNTAX     INTEGER {
        enabled(2),
        disabled(3),
        shutDown(4),
        noChange(5),
        offline(6),
        test(7),
        deferred(8),
        quiesce(9),
        reboot(10),
        reset(11),
        notApplicable(12)
    }
    MAX-ACCESS read-only
    STATUS     current
    DESCRIPTION
        "RequestedState is an integer enumeration that
        indicates the last requested or desired state for
        the element. The actual state of the element is
        represented by EnabledState. This property is
        provided to compare the last requested and current
        enabled or disabled states. Note that when
        EnabledState is set to 5 ('Not Applicable'), then
        this property has no meaning. By default, the
        RequestedState of the element is 5 ('No Change').
        Refer to the EnabledState property description for
        explanations of the values in the RequestedState
        enumeration. 
        
        It should be noted that there are two new values in
        RequestedState that build on the statuses of
        EnabledState. These are 'Reboot' (10) and 'Reset'
        (11). Reboot refers to doing a 'Shut Down' and then
        moving to an 'Enabled' state. Reset indicates that
        the element is first 'Disabled' and then 'Enabled'.
        The distinction between requesting 'Shut Down' and
        'Disabled' should also be noted. Shut Down requests
        an orderly transition to the Disabled state, and
        might involve removing power, to completely erase
        any existing state. The Disabled state requests an
        immediate disabling of the element, such that it
        will not execute or accept any commands or
        processing requests. 
        
        This property is set as the result of a method
        invocation (such as Start or StopService on
        CIM_Service), or can be overridden and defined as
        WRITEable in a subclass. The method approach is
        considered superior to a WRITEable property,
        because it allows an explicit invocation of the
        operation and the return of a result code. 
        
        A particular instance of EnabledLogicalElement
        might not support RequestedStateChange. If this
        occurs, the value 12 ('Not Applicable') is used."
    ::= { msvmTransparentBridgingSvcEntry 20 }

msvmtbsServiceURL OBJECT-TYPE
    SYNTAX     WtcsDisplayString
    MAX-ACCESS read-only
    STATUS     current
    DESCRIPTION
        "This is a URL that provides the protocol, network
        location, and other service-specific information
        required in order to access the service. It is
        deprecated with the recommendation that
        ServiceAccessURI be instantiated instead. This new
        class correctly positions the semantics of the
        service access, and clarifies the format of the
        information."
    ::= { msvmTransparentBridgingSvcEntry 21 }

msvmtbsStartMode OBJECT-TYPE
    SYNTAX     WtcsDisplayString (SIZE (0..10))
    MAX-ACCESS read-only
    STATUS     current
    DESCRIPTION
        "Note: The use of this element is deprecated in
        lieu of the EnabledDefault property that is
        inherited from EnabledLogicalElement. The
        EnabledLogicalElement addresses the same semantics.
        The change to a uint16 data type was discussed when
        CIM V2.0 was defined. However, existing V1.0
        implementations used the string property. To remain
        compatible with those implementations, StartMode
        was grandfathered into the schema. Use of the
        deprecated qualifier allows the maintenance of the
        existing property but also permits an improved,
        clarified definition using EnabledDefault. 
        Deprecated description: StartMode is a string value
        that indicates whether the Service is automatically
        started by a System, an Operating System, and so
        on, or is started only upon request."
    ::= { msvmTransparentBridgingSvcEntry 22 }

msvmtbsStarted OBJECT-TYPE
    SYNTAX     TruthValue
    MAX-ACCESS read-only
    STATUS     current
    DESCRIPTION
        "Started is a Boolean that indicates whether the
        Service has been started (TRUE), or stopped
        (FALSE)."
    ::= { msvmTransparentBridgingSvcEntry 23 }

msvmtbsStartupConditions OBJECT-TYPE
    SYNTAX     WtcsDisplayString
    MAX-ACCESS read-only
    STATUS     current
    DESCRIPTION
        "This is a free-form array of strings that specify
        any specific pre-conditions that must be met in
        order for this service to start correctly. It was
        expected that subclasses would refine the inherited
        StartService() method to suit their specific needs.
        To-date, this refinement has not been necessary.
        Also, the property is not very useful, since it is
        not standardized. If this was a necessary
        construct, then it would be required higher in the
        inheritance hierarchy (on Service). The latter has
        not proven true. Therefore, the property is
        deprecated."
    ::= { msvmTransparentBridgingSvcEntry 24 }

msvmtbsStartupParameters OBJECT-TYPE
    SYNTAX     WtcsDisplayString
    MAX-ACCESS read-only
    STATUS     current
    DESCRIPTION
        "This is a free-form array of strings that specify
        any specific parameters that must be supplied to
        the StartService() method in order for this service
        to start correctly. It was expected that subclasses
        would refine the inherited StartService() methods
        to suit their specific needs. To-date, this
        refinement has not been necessary. If indeed the
        method were refined, then its parameters would more
        formally convey this information. Therefore, the
        property is deprecated."
    ::= { msvmTransparentBridgingSvcEntry 25 }

msvmtbsStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmTransparentBridgingSvcEntry 26 }

msvmtbsStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmTransparentBridgingSvcEntry 27 }

msvmtbsSystemCreationClassName OBJECT-TYPE
    SYNTAX     WtcsDisplayString (SIZE (0..256))
    MAX-ACCESS read-only
    STATUS     current
    DESCRIPTION
        "The CreationClassName of the scoping System."
    ::= { msvmTransparentBridgingSvcEntry 28 }

msvmtbsSystemName OBJECT-TYPE
    SYNTAX     WtcsDisplayString (SIZE (0..256))
    MAX-ACCESS read-only
    STATUS     current
    DESCRIPTION
        "The Name of the scoping System."
    ::= { msvmTransparentBridgingSvcEntry 29 }

msvmtbsTimeOfLastStateChange OBJECT-TYPE
    SYNTAX     DateAndTime
    MAX-ACCESS read-only
    STATUS     current
    DESCRIPTION
        "The date or time when the EnabledState of the
        element last changed. If the state of the element
        has not changed and this property is populated,
        then it must be set to a 0 interval value. If a
        state change was requested, but rejected or not yet
        processed, the property must not be updated."
    ::= { msvmTransparentBridgingSvcEntry 30 }

msvmVirtualSwitchMgtServiceTable OBJECT-TYPE
    SYNTAX     SEQUENCE OF MsvmVirtualSwitchMgtService
    MAX-ACCESS not-accessible
    STATUS     current
    DESCRIPTION
        "Controls the definition, modification, and
        destruction of global networking resources such as
        virtual switches, switch ports, and internal
        Ethernet ports."
    ::= { msvmNetworking 22 }

msvmVirtualSwitchMgtServiceEntry OBJECT-TYPE
    SYNTAX     MsvmVirtualSwitchMgtService
    MAX-ACCESS not-accessible
    STATUS     current
    DESCRIPTION
        "None"
    INDEX      { msvmvsmsIndex }
    ::= { msvmVirtualSwitchMgtServiceTable 1 }

MsvmVirtualSwitchMgtService ::= SEQUENCE {
    msvmvsmsIndex Integer32,
    msvmvsmsCaption WtcsDisplayString,
    msvmvsmsCreationClassName WtcsDisplayString,
    msvmvsmsDescription WtcsDisplayString,
    msvmvsmsElementName WtcsDisplayString,
    msvmvsmsEnabledDefault INTEGER,
    msvmvsmsEnabledState INTEGER,
    msvmvsmsHealthState INTEGER,
    msvmvsmsInstallDate DateAndTime,
    msvmvsmsName WtcsDisplayString,
    msvmvsmsOperationalStatus INTEGER,
    msvmvsmsOtherEnabledState WtcsDisplayString,
    msvmvsmsPrimaryOwnerContact WtcsDisplayString,
    msvmvsmsPrimaryOwnerName WtcsDisplayString,
    msvmvsmsRequestedState INTEGER,
    msvmvsmsStartMode WtcsDisplayString,
    msvmvsmsStarted TruthValue,
    msvmvsmsStatus WtcsDisplayString,
    msvmvsmsStatusDescriptions WtcsDisplayString,
    msvmvsmsSystemCreationClassName WtcsDisplayString,
    msvmvsmsSystemName WtcsDisplayString,
    msvmvsmsTimeOfLastStateChange DateAndTime
}

msvmvsmsIndex OBJECT-TYPE
    SYNTAX     Integer32 (1..2147483647)
    MAX-ACCESS read-only
    STATUS     current
    DESCRIPTION
        "The value of this object uniquely identifies the
        instance entry for this class."
    ::= { msvmVirtualSwitchMgtServiceEntry 1 }

msvmvsmsCaption OBJECT-TYPE
    SYNTAX     WtcsDisplayString (SIZE (0..64))
    MAX-ACCESS read-only
    STATUS     current
    DESCRIPTION
        "The Caption property is a short textual
        description (one- line string) of the object."
    ::= { msvmVirtualSwitchMgtServiceEntry 2 }

msvmvsmsCreationClassName OBJECT-TYPE
    SYNTAX     WtcsDisplayString (SIZE (0..256))
    MAX-ACCESS read-only
    STATUS     current
    DESCRIPTION
        "CreationClassName indicates the name of the class
        or the subclass that is used in the creation of an
        instance. When used with the other key properties
        of this class, this property allows all instances
        of this class and its subclasses to be uniquely
        identified."
    ::= { msvmVirtualSwitchMgtServiceEntry 3 }

msvmvsmsDescription OBJECT-TYPE
    SYNTAX     WtcsDisplayString
    MAX-ACCESS read-only
    STATUS     current
    DESCRIPTION
        "The Description property provides a textual
        description of the object."
    ::= { msvmVirtualSwitchMgtServiceEntry 4 }

msvmvsmsElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmVirtualSwitchMgtServiceEntry 5 }

msvmvsmsEnabledDefault OBJECT-TYPE
    SYNTAX     INTEGER {
        enabled(2),
        disabled(3),
        notApplicable(5),
        enabledbutOffline(6),
        noDefault(7)
    }
    MAX-ACCESS read-only
    STATUS     current
    DESCRIPTION
        "An enumerated value indicating an administrator's
        default or startup configuration for the Enabled
        State of an element. By default, the element is
        'Enabled' (value=2)."
    ::= { msvmVirtualSwitchMgtServiceEntry 6 }

msvmvsmsEnabledState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "EnabledState is an integer enumeration that
        indicates the enabled and disabled states of an
        element. It can also indicate the transitions
        between these requested states. For example,
        shutting down (value=4) and starting (value=10) are
        transient states between enabled and disabled. The
        following text briefly summarizes the various
        enabled and disabled states: 
        Enabled (2) indicates that the element is or could
        be executing commands, will process any queued
        commands, and queues new requests. 
        Disabled (3) indicates that the element will not
        execute commands and will drop any new requests. 
        Shutting Down (4) indicates that the element is in
        the process of going to a Disabled state. 
        Not Applicable (5) indicates the element does not
        support being enabled or disabled. 
        Enabled but Offline (6) indicates that the element
        might be completing commands, and will drop any new
        requests. 
        Test (7) indicates that the element is in a test
        state. 
        Deferred (8) indicates that the element might be
        completing commands, but will queue any new
        requests. 
        Quiesce (9) indicates that the element is enabled
        but in a restricted mode. The behavior of the
        element is similar to the Enabled state, but it
        processes only a restricted set of commands. All
        other requests are queued. 
        Starting (10) indicates that the element is in the
        process of going to an Enabled state. New requests
        are queued."
    ::= { msvmVirtualSwitchMgtServiceEntry 7 }

msvmvsmsHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmVirtualSwitchMgtServiceEntry 8 }

msvmvsmsInstallDate OBJECT-TYPE
    SYNTAX     DateAndTime
    MAX-ACCESS read-only
    STATUS     current
    DESCRIPTION
        "A datetime value that indicates when the object
        was installed. Lack of a value does not indicate
        that the object is not installed."
    ::= { msvmVirtualSwitchMgtServiceEntry 9 }

msvmvsmsName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmVirtualSwitchMgtServiceEntry 10 }

msvmvsmsOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmVirtualSwitchMgtServiceEntry 11 }

msvmvsmsOtherEnabledState OBJECT-TYPE
    SYNTAX     WtcsDisplayString
    MAX-ACCESS read-only
    STATUS     current
    DESCRIPTION
        "A string that describes the enabled or disabled
        state of the element when the EnabledState property
        is set to 1 ('Other'). This property must be set to
        null when EnabledState is any value other than 1."
    ::= { msvmVirtualSwitchMgtServiceEntry 12 }

msvmvsmsPrimaryOwnerContact OBJECT-TYPE
    SYNTAX     WtcsDisplayString (SIZE (0..256))
    MAX-ACCESS read-only
    STATUS     current
    DESCRIPTION
        "A string that provides information on how the
        primary owner of the Service can be reached (for
        example, phone number, e-mail address, and so on)."
    ::= { msvmVirtualSwitchMgtServiceEntry 13 }

msvmvsmsPrimaryOwnerName OBJECT-TYPE
    SYNTAX     WtcsDisplayString (SIZE (0..64))
    MAX-ACCESS read-only
    STATUS     current
    DESCRIPTION
        "The name of the primary owner for the service, if
        one is defined. The primary owner is the initial
        support contact for the Service."
    ::= { msvmVirtualSwitchMgtServiceEntry 14 }

msvmvsmsRequestedState OBJECT-TYPE
    SYNTAX     INTEGER {
        enabled(2),
        disabled(3),
        shutDown(4),
        noChange(5),
        offline(6),
        test(7),
        deferred(8),
        quiesce(9),
        reboot(10),
        reset(11),
        notApplicable(12)
    }
    MAX-ACCESS read-only
    STATUS     current
    DESCRIPTION
        "RequestedState is an integer enumeration that
        indicates the last requested or desired state for
        the element. The actual state of the element is
        represented by EnabledState. This property is
        provided to compare the last requested and current
        enabled or disabled states. Note that when
        EnabledState is set to 5 ('Not Applicable'), then
        this property has no meaning. By default, the
        RequestedState of the element is 5 ('No Change').
        Refer to the EnabledState property description for
        explanations of the values in the RequestedState
        enumeration. 
        
        It should be noted that there are two new values in
        RequestedState that build on the statuses of
        EnabledState. These are 'Reboot' (10) and 'Reset'
        (11). Reboot refers to doing a 'Shut Down' and then
        moving to an 'Enabled' state. Reset indicates that
        the element is first 'Disabled' and then 'Enabled'.
        The distinction between requesting 'Shut Down' and
        'Disabled' should also be noted. Shut Down requests
        an orderly transition to the Disabled state, and
        might involve removing power, to completely erase
        any existing state. The Disabled state requests an
        immediate disabling of the element, such that it
        will not execute or accept any commands or
        processing requests. 
        
        This property is set as the result of a method
        invocation (such as Start or StopService on
        CIM_Service), or can be overridden and defined as
        WRITEable in a subclass. The method approach is
        considered superior to a WRITEable property,
        because it allows an explicit invocation of the
        operation and the return of a result code. 
        
        A particular instance of EnabledLogicalElement
        might not support RequestedStateChange. If this
        occurs, the value 12 ('Not Applicable') is used."
    ::= { msvmVirtualSwitchMgtServiceEntry 15 }

msvmvsmsStartMode OBJECT-TYPE
    SYNTAX     WtcsDisplayString (SIZE (0..10))
    MAX-ACCESS read-only
    STATUS     current
    DESCRIPTION
        "Note: The use of this element is deprecated in
        lieu of the EnabledDefault property that is
        inherited from EnabledLogicalElement. The
        EnabledLogicalElement addresses the same semantics.
        The change to a uint16 data type was discussed when
        CIM V2.0 was defined. However, existing V1.0
        implementations used the string property. To remain
        compatible with those implementations, StartMode
        was grandfathered into the schema. Use of the
        deprecated qualifier allows the maintenance of the
        existing property but also permits an improved,
        clarified definition using EnabledDefault. 
        Deprecated description: StartMode is a string value
        that indicates whether the Service is automatically
        started by a System, an Operating System, and so
        on, or is started only upon request."
    ::= { msvmVirtualSwitchMgtServiceEntry 16 }

msvmvsmsStarted OBJECT-TYPE
    SYNTAX     TruthValue
    MAX-ACCESS read-only
    STATUS     current
    DESCRIPTION
        "Started is a Boolean that indicates whether the
        Service has been started (TRUE), or stopped
        (FALSE)."
    ::= { msvmVirtualSwitchMgtServiceEntry 17 }

msvmvsmsStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmVirtualSwitchMgtServiceEntry 18 }

msvmvsmsStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmVirtualSwitchMgtServiceEntry 19 }

msvmvsmsSystemCreationClassName OBJECT-TYPE
    SYNTAX     WtcsDisplayString (SIZE (0..256))
    MAX-ACCESS read-only
    STATUS     current
    DESCRIPTION
        "The CreationClassName of the scoping System."
    ::= { msvmVirtualSwitchMgtServiceEntry 20 }

msvmvsmsSystemName OBJECT-TYPE
    SYNTAX     WtcsDisplayString (SIZE (0..256))
    MAX-ACCESS read-only
    STATUS     current
    DESCRIPTION
        "The Name of the scoping System."
    ::= { msvmVirtualSwitchMgtServiceEntry 21 }

msvmvsmsTimeOfLastStateChange OBJECT-TYPE
    SYNTAX     DateAndTime
    MAX-ACCESS read-only
    STATUS     current
    DESCRIPTION
        "The date or time when the EnabledState of the
        element last changed. If the state of the element
        has not changed and this property is populated,
        then it must be set to a 0 interval value. If a
        state change was requested, but rejected or not yet
        processed, the property must not be updated."
    ::= { msvmVirtualSwitchMgtServiceEntry 22 }

msvmVLANEndpointTable OBJECT-TYPE
    SYNTAX     SEQUENCE OF MsvmVLANEndpoint
    MAX-ACCESS not-accessible
    STATUS     current
    DESCRIPTION
        "This class represents the VLAN endpoint of a
        switch port."
    ::= { msvmNetworking 23 }

msvmVLANEndpointEntry OBJECT-TYPE
    SYNTAX     MsvmVLANEndpoint
    MAX-ACCESS not-accessible
    STATUS     current
    DESCRIPTION
        "None"
    INDEX      { msvmveIndex }
    ::= { msvmVLANEndpointTable 1 }

MsvmVLANEndpoint ::= SEQUENCE {
    msvmveIndex Integer32,
    msvmveBroadcastResetSupported TruthValue,
    msvmveCaption WtcsDisplayString,
    msvmveCreationClassName WtcsDisplayString,
    msvmveDescription WtcsDisplayString,
    msvmveDesiredEndpointMode INTEGER,
    msvmveDesiredVLANTrunkEncapsul Integer32,
    msvmveElementName WtcsDisplayString,
    msvmveEnabledDefault INTEGER,
    msvmveEnabledState INTEGER,
    msvmveGVRPStatus INTEGER,
    msvmveHealthState INTEGER,
    msvmveInstallDate DateAndTime,
    msvmveName WtcsDisplayString,
    msvmveNameFormat WtcsDisplayString,
    msvmveOperationalEndpointMode INTEGER,
    msvmveOperationalStatus INTEGER,
    msvmveOperationalVLANTrunkEncap Integer32,
    msvmveOtherEnabledState WtcsDisplayString,
    msvmveOtherEndpointMode WtcsDisplayString,
    msvmveOtherTrunkEncapsulation WtcsDisplayString,
    msvmveOtherTypeDescription WtcsDisplayString,
    msvmveProtocolIFType Integer32,
    msvmveProtocolType INTEGER,
    msvmveRequestedState INTEGER,
    msvmveStatus WtcsDisplayString,
    msvmveStatusDescriptions WtcsDisplayString,
    msvmveSupportedEndpointModes Integer32,
    msvmveSystemCreationClassName WtcsDisplayString,
    msvmveSystemName WtcsDisplayString,
    msvmveTimeOfLastStateChange DateAndTime
}

msvmveIndex OBJECT-TYPE
    SYNTAX     Integer32 (1..2147483647)
    MAX-ACCESS read-only
    STATUS     current
    DESCRIPTION
        "The value of this object uniquely identifies the
        instance entry for this class."
    ::= { msvmVLANEndpointEntry 1 }

msvmveBroadcastResetSupported OBJECT-TYPE
    SYNTAX     TruthValue
    MAX-ACCESS read-only
    STATUS     current
    DESCRIPTION
        "A boolean indicating whether the instrumentation
        supports the BroadcastReset method."
    ::= { msvmVLANEndpointEntry 2 }

msvmveCaption OBJECT-TYPE
    SYNTAX     WtcsDisplayString (SIZE (0..64))
    MAX-ACCESS read-only
    STATUS     current
    DESCRIPTION
        "The Caption property is a short textual
        description (one- line string) of the object."
    ::= { msvmVLANEndpointEntry 3 }

msvmveCreationClassName OBJECT-TYPE
    SYNTAX     WtcsDisplayString (SIZE (0..256))
    MAX-ACCESS read-only
    STATUS     current
    DESCRIPTION
        "CreationClassName indicates the name of the class
        or the subclass used in the creation of an
        instance. When used with the other key properties
        of this class, this property allows all instances
        of this class and its subclasses to be uniquely
        identified."
    ::= { msvmVLANEndpointEntry 4 }

msvmveDescription OBJECT-TYPE
    SYNTAX     WtcsDisplayString
    MAX-ACCESS read-only
    STATUS     current
    DESCRIPTION
        "The Description property provides a textual
        description of the object."
    ::= { msvmVLANEndpointEntry 5 }

msvmveDesiredEndpointMode OBJECT-TYPE
    SYNTAX     INTEGER {
        dmtfReserved(0),
        other(1),
        access(2),
        dynamicAuto(3),
        dynamicDesirable(4),
        trunk(5),
        dot1QTunnel(6)
    }
    MAX-ACCESS read-only
    STATUS     current
    DESCRIPTION
        "The desired VLAN mode that is requested for use.
        (Note that the current mode is given by the
        OperationalEndpointMode property.) The following
        values are defined: 
        - Access: Puts the endpoint/switch port into
        permanent nontrunking mode and negotiates to
        convert the link into a nontrunk link. The endpoint
        becomes a nontrunk interface. 
        - Dynamic Auto: Makes the endpoint able to convert
        the link to a trunk link. The endpoint becomes a
        trunk interface if the neighboring interface is set
        to trunk or desirable mode. 
        - Dynamic Desirable: Makes the endpoint actively
        attempt to convert the link to a trunk link. The
        endpoint becomes a trunk interface if the
        neighboring interface is set to trunk, desirable,
        or auto mode. The default switch-port mode for all
        Ethernet interfaces is 'dynamic desirable.' 
        - Trunk: Puts the endpoint into permanent trunking
        mode and negotiates to convert the link into a
        trunk link. The endpoint becomes a trunk interface
        even if the neighboring interface is not a trunk
        interface. 
        - Dot1Q Tunnel: Configures the interface as a
        tunnel (nontrunking) endpoint/port to be connected
        in an asymmetric link with an 802.1Q trunk port.
        802.1Q tunneling is used to maintain customer VLAN
        integrity across a service provider network."
    ::= { msvmVLANEndpointEntry 6 }

msvmveDesiredVLANTrunkEncapsul OBJECT-TYPE
    SYNTAX     Integer32
    MAX-ACCESS read-only
    STATUS     current
    DESCRIPTION
        "The type of VLAN encapsulation that is requested
        for use. (Note that the encapsulation currently in
        use is given by the
        OperationalVLANTrunkEncapsulation property.) Note
        that this property is only applicable when the
        endpoint is operating in a trunking mode (see the
        OperationalEndpointMode property for additional
        details). This property is either 'not applicable'
        (i.e., the endpoint will never be placed in a
        trunking mode), a particular type (802.1q or Cisco
        ISL), or 'negotiate' (i.e., the result of the
        negotiation between this interface and its
        neighbor). The value, 'Negotiate' is not allowed if
        the endpoint does not support negotiation. This
        capability is hardware and vendor dependent. Refer
        to the associated
        VLANEndpointCapabilities.doesTrunkEncapsulationNego
        tiation property to validate whether a particular
        endpoint (port) supports encapsulation
        negotiation."
    ::= { msvmVLANEndpointEntry 7 }

msvmveElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmVLANEndpointEntry 8 }

msvmveEnabledDefault OBJECT-TYPE
    SYNTAX     INTEGER {
        enabled(2),
        disabled(3),
        notApplicable(5),
        enabledbutOffline(6),
        noDefault(7)
    }
    MAX-ACCESS read-only
    STATUS     current
    DESCRIPTION
        "An enumerated value indicating an administrator's
        default or startup configuration for the Enabled
        State of an element. By default, the element is
        'Enabled' (value=2)."
    ::= { msvmVLANEndpointEntry 9 }

msvmveEnabledState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "EnabledState is an integer enumeration that
        indicates the enabled and disabled states of an
        element. It can also indicate the transitions
        between these requested states. For example,
        shutting down (value=4) and starting (value=10) are
        transient states between enabled and disabled. The
        following text briefly summarizes the various
        enabled and disabled states: 
        Enabled (2) indicates that the element is or could
        be executing commands, will process any queued
        commands, and queues new requests. 
        Disabled (3) indicates that the element will not
        execute commands and will drop any new requests. 
        Shutting Down (4) indicates that the element is in
        the process of going to a Disabled state. 
        Not Applicable (5) indicates the element does not
        support being enabled or disabled. 
        Enabled but Offline (6) indicates that the element
        might be completing commands, and will drop any new
        requests. 
        Test (7) indicates that the element is in a test
        state. 
        Deferred (8) indicates that the element might be
        completing commands, but will queue any new
        requests. 
        Quiesce (9) indicates that the element is enabled
        but in a restricted mode. The behavior of the
        element is similar to the Enabled state, but it
        processes only a restricted set of commands. All
        other requests are queued. 
        Starting (10) indicates that the element is in the
        process of going to an Enabled state. New requests
        are queued."
    ::= { msvmVLANEndpointEntry 10 }

msvmveGVRPStatus OBJECT-TYPE
    SYNTAX     INTEGER {
        unknown(0),
        notApplicable(2),
        enabled(3),
        disabled(4)
    }
    MAX-ACCESS read-only
    STATUS     current
    DESCRIPTION
        "Indicates whether GARP VLAN Registration Protocol
        (GVRP) is enabled or disabled on the trunk
        endpoint/port. This property is 'not applicable'
        unless GVRP is supported by the endpoint. This is
        indicated in the Capabilities property,
        VLANEndpointCapabilities.Dot1QTagging. This
        property is applicable only when the endpoint is
        operating in trunking mode (determined by examining
        the SwitchEndpointMode property)."
    ::= { msvmVLANEndpointEntry 11 }

msvmveHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmVLANEndpointEntry 12 }

msvmveInstallDate OBJECT-TYPE
    SYNTAX     DateAndTime
    MAX-ACCESS read-only
    STATUS     current
    DESCRIPTION
        "A datetime value that indicates when the object
        was installed. Lack of a value does not indicate
        that the object is not installed."
    ::= { msvmVLANEndpointEntry 13 }

msvmveName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmVLANEndpointEntry 14 }

msvmveNameFormat OBJECT-TYPE
    SYNTAX     WtcsDisplayString (SIZE (0..256))
    MAX-ACCESS read-only
    STATUS     current
    DESCRIPTION
        "NameFormat contains the naming heuristic that is
        selected to ensure that the value of the Name
        property is unique. For example, you might choose
        to prepend the name of the port or interface with
        the Type of ProtocolEndpoint (for example, IPv4) of
        this instance followed by an underscore."
    ::= { msvmVLANEndpointEntry 15 }

msvmveOperationalEndpointMode OBJECT-TYPE
    SYNTAX     INTEGER {
        dmtfReserved(0),
        other(1),
        access(2),
        dynamicAuto(3),
        dynamicDesirable(4),
        trunk(5),
        dot1QTunnel(6)
    }
    MAX-ACCESS read-only
    STATUS     current
    DESCRIPTION
        "The configuration mode for the VLAN endpoint. The
        following values are defined: /n - Unknown: If the
        endpoint is not VLAN aware. /n - Access: Puts the
        endpoint into permanent nontrunking mode and
        negotiates to convert the link into a nontrunk
        link. The endpoint becomes a nontrunk interface. 
        - Dynamic Auto: Makes the endpoint able to convert
        the link to a trunk link. The endpoint becomes a
        trunk interface if the neighboring interface is set
        to trunk or desirable mode. 
        - Dynamic Desirable: Makes the endpoint actively
        attempt to convert the link to a trunk link. The
        endpoint becomes a trunk interface if the
        neighboring interface is set to trunk, desirable,
        or auto mode. The default switch-port mode for all
        Ethernet interfaces is 'dynamic desirable.' 
        - Trunk: Puts the endpoint into permanent trunking
        mode and negotiates to convert the link into a
        trunk link. The endpoint becomes a trunk interface
        even if the neighboring interface is not a trunk
        interface. 
        - Dot1Q Tunnel: Configures the interface as a
        tunnel (nontrunking) endpoint/port to be connected
        in an asymmetric link with an 802.1Q trunk port.
        802.1Q tunneling is used to maintain customer VLAN
        integrity across a service provider network."
    ::= { msvmVLANEndpointEntry 16 }

msvmveOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmVLANEndpointEntry 17 }

msvmveOperationalVLANTrunkEncap OBJECT-TYPE
    SYNTAX     Integer32
    MAX-ACCESS read-only
    STATUS     current
    DESCRIPTION
        "The type of VLAN encapsulation in use on a trunk
        endpoint/port. This property is either 'not
        applicable' (i.e., the endpoint is not operating in
        trunking mode), a particular type (802.1q or Cisco
        ISL), 'negotiating' (i.e., the endpoints are
        negotiating the encapsulation type). Note that this
        property is only applicable when the endpoint is
        operating in a trunking mode (see the
        OperationalEndpointMode property for additional
        details)."
    ::= { msvmVLANEndpointEntry 18 }

msvmveOtherEnabledState OBJECT-TYPE
    SYNTAX     WtcsDisplayString
    MAX-ACCESS read-only
    STATUS     current
    DESCRIPTION
        "A string that describes the enabled or disabled
        state of the element when the EnabledState property
        is set to 1 ('Other'). This property must be set to
        null when EnabledState is any value other than 1."
    ::= { msvmVLANEndpointEntry 19 }

msvmveOtherEndpointMode OBJECT-TYPE
    SYNTAX     WtcsDisplayString
    MAX-ACCESS read-only
    STATUS     current
    DESCRIPTION
        "A string describing the type of VLAN endpoint
        model that is supported by this VLANEndpoint, when
        the value of the mode property is set to 1 (i.e.,
        'Other'). This property should be set to NULL when
        the mode property is any value other than 1."
    ::= { msvmVLANEndpointEntry 20 }

msvmveOtherTrunkEncapsulation OBJECT-TYPE
    SYNTAX     WtcsDisplayString
    MAX-ACCESS read-only
    STATUS     current
    DESCRIPTION
        "A string describing the type of VLAN encapsulation
        that is supported by this VLANEndpoint, when the
        value of the encapsulation property is set to 1
        (i.e., 'Other'). This property should be set to
        NULL when the desired encapsulation property is any
        value other than 1."
    ::= { msvmVLANEndpointEntry 21 }

msvmveOtherTypeDescription OBJECT-TYPE
    SYNTAX     WtcsDisplayString (SIZE (0..64))
    MAX-ACCESS read-only
    STATUS     current
    DESCRIPTION
        "A string that describes the type of
        ProtocolEndpoint when the Type property of this
        class (or any of its subclasses) is set to 1
        (Other). This property should be set to null when
        the Type property is any value other than 1."
    ::= { msvmVLANEndpointEntry 22 }

msvmveProtocolIFType OBJECT-TYPE
    SYNTAX     Integer32
    MAX-ACCESS read-only
    STATUS     current
    DESCRIPTION
        "ProtocolIFType is an enumeration that is
        synchronized with the IANA ifType MIB. The ifType
        MIB is maintained at the URL,
        http://www.iana.org/assignments/ianaiftype-mib.
        Also, additional values defined by the DMTF are
        included. The property is used to categorize and
        classify instances of the ProtocolEndpoint class.
        Note that if the ProtocolIFType is set to 1
        (Other), then the type information should be
        provided in the OtherTypeDescription string
        property."
    ::= { msvmVLANEndpointEntry 23 }

msvmveProtocolType OBJECT-TYPE
    SYNTAX     INTEGER {
        unknown(0),
        other(1),
        ipv4(2),
        ipv6(3),
        ipx(4),
        appleTalk(5),
        decnet(6),
        sna(7),
        conp(8),
        clnp(9),
        vines(10),
        xns(11),
        atm(12),
        frameRelay(13),
        ethernet(14),
        tokenRing(15),
        fddi(16),
        infiniband(17),
        fibreChannel(18),
        isdnBRIEndpoint(19),
        isdnBChannelEndpoint(20),
        isdnDChannelEndpoint(21),
        ipv4v6(22),
        bgp(23),
        ospf(24),
        mpls(25),
        udp(26),
        tcp(27)
    }
    MAX-ACCESS read-only
    STATUS     current
    DESCRIPTION
        "Note: This property is deprecated in lieu of the
        ProtocolIFType enumeration. This deprecation was
        done to have better alignment between the IF-MIB of
        the IETF and this CIM class. 
        Deprecated description: ProtocolType is an
        enumeration that provides information to categorize
        and classify different instances of this class. For
        most instances, information in this enumeration and
        the definition of the subclass overlap. However,
        there are several cases where a specific subclass
        of ProtocolEndpoint is not required (for example,
        there is no Fibre Channel subclass of
        ProtocolEndpoint). Therefore, this property is
        needed to define the type of Endpoint."
    ::= { msvmVLANEndpointEntry 24 }

msvmveRequestedState OBJECT-TYPE
    SYNTAX     INTEGER {
        enabled(2),
        disabled(3),
        shutDown(4),
        noChange(5),
        offline(6),
        test(7),
        deferred(8),
        quiesce(9),
        reboot(10),
        reset(11),
        notApplicable(12)
    }
    MAX-ACCESS read-only
    STATUS     current
    DESCRIPTION
        "RequestedState is an integer enumeration that
        indicates the last requested or desired state for
        the element. The actual state of the element is
        represented by EnabledState. This property is
        provided to compare the last requested and current
        enabled or disabled states. Note that when
        EnabledState is set to 5 ('Not Applicable'), then
        this property has no meaning. By default, the
        RequestedState of the element is 5 ('No Change').
        Refer to the EnabledState property description for
        explanations of the values in the RequestedState
        enumeration. 
        
        It should be noted that there are two new values in
        RequestedState that build on the statuses of
        EnabledState. These are 'Reboot' (10) and 'Reset'
        (11). Reboot refers to doing a 'Shut Down' and then
        moving to an 'Enabled' state. Reset indicates that
        the element is first 'Disabled' and then 'Enabled'.
        The distinction between requesting 'Shut Down' and
        'Disabled' should also be noted. Shut Down requests
        an orderly transition to the Disabled state, and
        might involve removing power, to completely erase
        any existing state. The Disabled state requests an
        immediate disabling of the element, such that it
        will not execute or accept any commands or
        processing requests. 
        
        This property is set as the result of a method
        invocation (such as Start or StopService on
        CIM_Service), or can be overridden and defined as
        WRITEable in a subclass. The method approach is
        considered superior to a WRITEable property,
        because it allows an explicit invocation of the
        operation and the return of a result code. 
        
        A particular instance of EnabledLogicalElement
        might not support RequestedStateChange. If this
        occurs, the value 12 ('Not Applicable') is used."
    ::= { msvmVLANEndpointEntry 25 }

msvmveStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmVLANEndpointEntry 26 }

msvmveStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmVLANEndpointEntry 27 }

msvmveSupportedEndpointModes OBJECT-TYPE
    SYNTAX     Integer32
    MAX-ACCESS read-only
    STATUS     current
    DESCRIPTION
        "Endpoint mode supporteds by this port. This
        property is inherited from CIM_VLANEndpoint."
    ::= { msvmVLANEndpointEntry 28 }

msvmveSystemCreationClassName OBJECT-TYPE
    SYNTAX     WtcsDisplayString (SIZE (0..256))
    MAX-ACCESS read-only
    STATUS     current
    DESCRIPTION
        "The CreationClassName of the scoping System."
    ::= { msvmVLANEndpointEntry 29 }

msvmveSystemName OBJECT-TYPE
    SYNTAX     WtcsDisplayString (SIZE (0..256))
    MAX-ACCESS read-only
    STATUS     current
    DESCRIPTION
        "The Name of the scoping System."
    ::= { msvmVLANEndpointEntry 30 }

msvmveTimeOfLastStateChange OBJECT-TYPE
    SYNTAX     DateAndTime
    MAX-ACCESS read-only
    STATUS     current
    DESCRIPTION
        "The date or time when the EnabledState of the
        element last changed. If the state of the element
        has not changed and this property is populated,
        then it must be set to a 0 interval value. If a
        state change was requested, but rejected or not yet
        processed, the property must not be updated."
    ::= { msvmVLANEndpointEntry 31 }

msvmVLANEndpointSettingDataTable OBJECT-TYPE
    SYNTAX     SEQUENCE OF MsvmVLANEndpointSettingData
    MAX-ACCESS not-accessible
    STATUS     current
    DESCRIPTION
        "This class represents the settings for a VLAN
        endpoint of a switch port."
    ::= { msvmNetworking 24 }

msvmVLANEndpointSettingDataEntry OBJECT-TYPE
    SYNTAX     MsvmVLANEndpointSettingData
    MAX-ACCESS not-accessible
    STATUS     current
    DESCRIPTION
        "None"
    INDEX      { msvmvesdIndex }
    ::= { msvmVLANEndpointSettingDataTable 1 }

MsvmVLANEndpointSettingData ::= SEQUENCE {
    msvmvesdIndex Integer32,
    msvmvesdAccessVLAN Integer32,
    msvmvesdCaption WtcsDisplayString,
    msvmvesdDefaultVLAN Integer32,
    msvmvesdDescription WtcsDisplayString,
    msvmvesdElementName WtcsDisplayString,
    msvmvesdInstanceID WtcsDisplayString,
    msvmvesdNativeVLAN Integer32,
    msvmvesdPruneEligibleVLANList Integer32,
    msvmvesdTrunkedVLANList Integer32
}

msvmvesdIndex OBJECT-TYPE
    SYNTAX     Integer32 (1..2147483647)
    MAX-ACCESS read-only
    STATUS     current
    DESCRIPTION
        "The value of this object uniquely identifies the
        instance entry for this class."
    ::= { msvmVLANEndpointSettingDataEntry 1 }

msvmvesdAccessVLAN OBJECT-TYPE
    SYNTAX     Integer32
    MAX-ACCESS read-only
    STATUS     current
    DESCRIPTION
        "The access VLAN for the referenced VLANEndpoint."
    ::= { msvmVLANEndpointSettingDataEntry 2 }

msvmvesdCaption OBJECT-TYPE
    SYNTAX     WtcsDisplayString (SIZE (0..64))
    MAX-ACCESS read-only
    STATUS     current
    DESCRIPTION
        "The Caption property is a short textual
        description (one- line string) of the object."
    ::= { msvmVLANEndpointSettingDataEntry 3 }

msvmvesdDefaultVLAN OBJECT-TYPE
    SYNTAX     Integer32
    MAX-ACCESS read-only
    STATUS     current
    DESCRIPTION
        "Default value for the native VLAN on this trunk
        endpoint/port. This property is applicable only
        when the endpoint is operating in trunking mode
        (determined by examining the
        OperationalEndpointMode property)."
    ::= { msvmVLANEndpointSettingDataEntry 4 }

msvmvesdDescription OBJECT-TYPE
    SYNTAX     WtcsDisplayString
    MAX-ACCESS read-only
    STATUS     current
    DESCRIPTION
        "The Description property provides a textual
        description of the object."
    ::= { msvmVLANEndpointSettingDataEntry 5 }

msvmvesdElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmVLANEndpointSettingDataEntry 6 }

msvmvesdInstanceID OBJECT-TYPE
    SYNTAX     WtcsDisplayString
    MAX-ACCESS read-only
    STATUS     current
    DESCRIPTION
        "Within the scope of the instantiating Namespace,
        InstanceID opaquely and uniquely identifies an
        instance of this class. To ensure uniqueness within
        the NameSpace, the value of InstanceID should be
        constructed using the following 'preferred'
        algorithm: 
        <OrgID>:<LocalID> 
        Where <OrgID> and <LocalID> are separated by a
        colon (:), and where <OrgID> must include a
        copyrighted, trademarked, or otherwise unique name
        that is owned by the business entity that is
        creating or defining the InstanceID or that is a
        registered ID assigned to the business entity by a
        recognized global authority. (This requirement is
        similar to the <Schema Name>_<Class Name> structure
        of Schema class names.) In addition, to ensure
        uniqueness, <OrgID> must not contain a colon (:).
        When using this algorithm, the first colon to
        appear in InstanceID must appear between <OrgID>
        and <LocalID>. 
        <LocalID> is chosen by the business entity and
        should not be reused to identify different
        underlying (real-world) elements. If the above
        'preferred' algorithm is not used, the defining
        entity must assure that the resulting InstanceID is
        not reused across any InstanceIDs produced by this
        or other providers for the NameSpace of this
        instance. 
        For DMTF-defined instances, the 'preferred'
        algorithm must be used with the <OrgID> set to
        CIM."
    ::= { msvmVLANEndpointSettingDataEntry 7 }

msvmvesdNativeVLAN OBJECT-TYPE
    SYNTAX     Integer32
    MAX-ACCESS read-only
    STATUS     current
    DESCRIPTION
        "VLAN Id that is used to tag untagged traffic
        received on this trunk endpoint/port. This property
        is applicable only when the endpoint is operating
        in trunking mode (determined by examining the
        SwitchEndpointMode property)."
    ::= { msvmVLANEndpointSettingDataEntry 8 }

msvmvesdPruneEligibleVLANList OBJECT-TYPE
    SYNTAX     Integer32
    MAX-ACCESS read-only
    STATUS     current
    DESCRIPTION
        "If a VLAN Id is part of this array, then the
        system MAY prune that VLAN on the related trunk
        endpoint/port. This property is applicable only
        when the endpoint is operating in trunking mode
        (determined by examining the
        OperationalEndpointMode property)."
    ::= { msvmVLANEndpointSettingDataEntry 9 }

msvmvesdTrunkedVLANList OBJECT-TYPE
    SYNTAX     Integer32
    MAX-ACCESS read-only
    STATUS     current
    DESCRIPTION
        "If a VLAN Id is part of this array, then the
        system MAY trunk the traffic on the related
        endpoint/port. This property is applicable only
        when the endpoint is operating in trunking mode
        (determined by examining the
        OperationalEndpointMode property)."
    ::= { msvmVLANEndpointSettingDataEntry 10 }

msvmProcessor OBJECT-IDENTITY
    STATUS     current
    DESCRIPTION
        "The processor classes model a processor for a
        virtual system."
    ::= { informantHyperV 6 }

msvmProcessorTable OBJECT-TYPE
    SYNTAX     SEQUENCE OF MsvmProcessor
    MAX-ACCESS not-accessible
    STATUS     current
    DESCRIPTION
        "Represents the virtual processor in a virtual
        computer system."
    ::= { msvmProcessor 1 }

msvmProcessorEntry OBJECT-TYPE
    SYNTAX     MsvmProcessor
    MAX-ACCESS not-accessible
    STATUS     current
    DESCRIPTION
        "None"
    INDEX      { msvmprIndex }
    ::= { msvmProcessorTable 1 }

MsvmProcessor ::= SEQUENCE {
    msvmprIndex Integer32,
    msvmprAdditionalAvailability INTEGER,
    msvmprAddressWidth Integer32,
    msvmprAvailability INTEGER,
    msvmprCPUStatus INTEGER,
    msvmprCaption WtcsDisplayString,
    msvmprCharacteristics INTEGER,
    msvmprCreationClassName WtcsDisplayString,
    msvmprCurrentClockSpeed Gauge32,
    msvmprDataWidth Integer32,
    msvmprDescription WtcsDisplayString,
    msvmprDeviceID WtcsDisplayString,
    msvmprElementName WtcsDisplayString,
    msvmprEnabledDefault INTEGER,
    msvmprEnabledState INTEGER,
    msvmprErrorCleared TruthValue,
    msvmprErrorDescription WtcsDisplayString,
    msvmprExternalBusClockSpeed Gauge32,
    msvmprFamily Integer32,
    msvmprHealthState INTEGER,
    msvmprIdentifyingDescriptions WtcsDisplayString,
    msvmprInstallDate DateAndTime,
    msvmprLastErrorCode Gauge32,
    msvmprLoadPercentage Integer32,
    msvmprLoadPercentageHistory Integer32,
    msvmprLocationIndicator INTEGER,
    msvmprMaxClockSpeed Gauge32,
    msvmprMaxQuiesceTime Gauge32,
    msvmprName WtcsDisplayString,
    msvmprOperationalStatus INTEGER,
    msvmprOtherEnabledState INTEGER,
    msvmprOtherFamilyDescription Integer32,
    msvmprOtherIdentifyingInfo WtcsDisplayString,
    msvmprPowerManagementCapability INTEGER,
    msvmprPowerManagementSupported TruthValue,
    msvmprPowerOnHours Gauge32,
    msvmprRequestedState INTEGER,
    msvmprRole WtcsDisplayString,
    msvmprStatus WtcsDisplayString,
    msvmprStatusDescriptions INTEGER,
    msvmprStatusInfo INTEGER,
    msvmprStepping Integer32,
    msvmprSystemCreationClassName WtcsDisplayString,
    msvmprSystemName WtcsDisplayString,
    msvmprTimeOfLastStateChange DateAndTime,
    msvmprTotalPowerOnHours Gauge32,
    msvmprUniqueID WtcsDisplayString,
    msvmprUpgradeMethod Integer32
}

msvmprIndex OBJECT-TYPE
    SYNTAX     Integer32 (1..2147483647)
    MAX-ACCESS read-only
    STATUS     current
    DESCRIPTION
        "The value of this object uniquely identifies the
        instance entry for this class."
    ::= { msvmProcessorEntry 1 }

msvmprAdditionalAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Note: The use of this property has been
        deprecated. 
        Deprecated description: The primary availability
        and status of the Device. (Additional status
        information can be specified using the Additional
        Availability array property.) For example, the
        Availability property indicates that the Device is
        running and has full power (value=3), or is in a
        warning (4), test (5), degraded (10) or power save
        state (values 13-15 and 17). The Power Save states
        are defined as follows: Value 13 ('Power Save -
        Unknown') indicates that the Device is known to be
        in a power save mode, but its exact status in this
        mode is unknown; value 14 ('Power Save - Low Power
        Mode') indicates that the Device is in a power save
        state but still functioning, and might exhibit
        degraded performance; value 15 ('Power Save -
        Standby') indicates that the Device is not
        functioning but could be brought to full power
        'quickly'; and value 17 ('Power Save - Warning')
        indicates that the Device is in a warning state,
        but is also in a power save mode."
    ::= { msvmProcessorEntry 2 }

msvmprAddressWidth OBJECT-TYPE
    SYNTAX     Integer32
    UNITS "Bits"
    MAX-ACCESS read-only
    STATUS     current
    DESCRIPTION
        "Processor address width in bits."
    ::= { msvmProcessorEntry 3 }

msvmprAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Additional availability and status of the Device
        in addition to that specified in the Availability
        property. The Availability property denotes the
        primary status and availability of the Device. In
        some cases, this property will not be sufficient to
        denote the complete status of the Device. In those
        cases, the AdditionalAvailability property can be
        used to provide further information. For example,
        the primary Availability of a device might be 'Off
        line' (value=8) or in a low-power state
        (AdditionalAvailability value=14), or the Device
        could be running Diagnostics
        (AdditionalAvailability value=5, 'In Test')."
    ::= { msvmProcessorEntry 4 }

msvmprCPUStatus OBJECT-TYPE
    SYNTAX     INTEGER {
        unknown(0),
        cpuEnabled(1),
        cpuDisabledbyUserusingBIOSSetup(2),
        cpuDisabledByBIOSPOSTError(3),
        cpuIsIdle(4),
        other(7)
    }
    MAX-ACCESS read-only
    STATUS     current
    DESCRIPTION
        "The CPUStatus property that indicates the current
        status of the Processor. For example, the Processor
        might be disabled by the user using BIOS (value=2),
        or disabled due to a POST error (value=3).
        Information in this property can be obtained from
        SMBIOS, the Type 4 structure, and the Status
        attribute."
    ::= { msvmProcessorEntry 5 }

msvmprCaption OBJECT-TYPE
    SYNTAX     WtcsDisplayString (SIZE (0..64))
    MAX-ACCESS read-only
    STATUS     current
    DESCRIPTION
        "The Caption property is a short textual
        description (one- line string) of the object."
    ::= { msvmProcessorEntry 6 }

msvmprCharacteristics OBJECT-TYPE
    SYNTAX     INTEGER {
        unknown(0),
        dmtfReserved(1),
        bit64Capable(2),
        bit32Capable(3)
    }
    MAX-ACCESS read-only
    STATUS     current
    DESCRIPTION
        "An array of enumerated integers that specify the
        features supported by the Processor. For example,
        one can specify that 64-bit capability is provided
        (value=2). Values specified in the enumeration
        could be taken from SMBIOS (the Type 4 structure,
        the Processor Characteristics Byte attributes."
    ::= { msvmProcessorEntry 7 }

msvmprCreationClassName OBJECT-TYPE
    SYNTAX     WtcsDisplayString (SIZE (0..256))
    MAX-ACCESS read-only
    STATUS     current
    DESCRIPTION
        "CreationClassName indicates the name of the class
        or the subclass used in the creation of an
        instance. When used with the other key properties
        of this class, this property allows all instances
        of this class and its subclasses to be uniquely
        identified."
    ::= { msvmProcessorEntry 8 }

msvmprCurrentClockSpeed OBJECT-TYPE
    SYNTAX     Gauge32
    UNITS "MegaHertz"
    MAX-ACCESS read-only
    STATUS     current
    DESCRIPTION
        "The current speed (in MHz) of this Processor."
    ::= { msvmProcessorEntry 9 }

msvmprDataWidth OBJECT-TYPE
    SYNTAX     Integer32
    UNITS "Bits"
    MAX-ACCESS read-only
    STATUS     current
    DESCRIPTION
        "Processor data width in bits."
    ::= { msvmProcessorEntry 10 }

msvmprDescription OBJECT-TYPE
    SYNTAX     WtcsDisplayString
    MAX-ACCESS read-only
    STATUS     current
    DESCRIPTION
        "The Description property provides a textual
        description of the object."
    ::= { msvmProcessorEntry 11 }

msvmprDeviceID OBJECT-TYPE
    SYNTAX     WtcsDisplayString (SIZE (0..64))
    MAX-ACCESS read-only
    STATUS     current
    DESCRIPTION
        "An address or other identifying information used
        to uniquely name the LogicalDevice."
    ::= { msvmProcessorEntry 12 }

msvmprElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmProcessorEntry 13 }

msvmprEnabledDefault OBJECT-TYPE
    SYNTAX     INTEGER {
        enabled(2),
        disabled(3),
        notApplicable(5),
        enabledbutOffline(6),
        noDefault(7)
    }
    MAX-ACCESS read-only
    STATUS     current
    DESCRIPTION
        "An enumerated value indicating an administrator's
        default or startup configuration for the Enabled
        State of an element. By default, the element is
        'Enabled' (value=2)."
    ::= { msvmProcessorEntry 14 }

msvmprEnabledState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "A string that describes the enabled or disabled
        state of the element when the EnabledState property
        is set to 1 ('Other'). This property must be set to
        null when EnabledState is any value other than 1."
    ::= { msvmProcessorEntry 15 }

msvmprErrorCleared OBJECT-TYPE
    SYNTAX     TruthValue
    MAX-ACCESS read-only
    STATUS     current
    DESCRIPTION
        "Note: The use of this method is deprecated. 
        Deprecated description: ErrorCleared is a Boolean
        property that indicates that the error reported in
        LastErrorCode is now cleared."
    ::= { msvmProcessorEntry 16 }

msvmprErrorDescription OBJECT-TYPE
    SYNTAX     WtcsDisplayString
    MAX-ACCESS read-only
    STATUS     current
    DESCRIPTION
        "Note: The use of this method is deprecated. 
        Deprecated description: ErrorDescription is a
        free-form string that supplies more information
        about the error recorded in LastErrorCode and
        information on any corrective actions that can be
        taken."
    ::= { msvmProcessorEntry 17 }

msvmprExternalBusClockSpeed OBJECT-TYPE
    SYNTAX     Gauge32
    UNITS "MegaHertz"
    MAX-ACCESS read-only
    STATUS     current
    DESCRIPTION
        "The speed (in MHz) of the external bus interface
        (also known as the front side bus)."
    ::= { msvmProcessorEntry 18 }

msvmprFamily OBJECT-TYPE
    SYNTAX     Integer32
    MAX-ACCESS read-only
    STATUS     current
    DESCRIPTION
        "A string that describes the Processor Family type.
        It is used when the Family property is set to 1
        ('Other'). This string should be set to NULL when
        the Family property is any value other than 1."
    ::= { msvmProcessorEntry 19 }

msvmprHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmProcessorEntry 20 }

msvmprIdentifyingDescriptions OBJECT-TYPE
    SYNTAX     WtcsDisplayString
    MAX-ACCESS read-only
    STATUS     current
    DESCRIPTION
        "OtherIdentifyingInfo captures data, in addition to
        DeviceID information, that could be used to
        identify a LogicalDevice. For example, you could
        use this property to hold the operating system's
        user-friendly name for the Device."
    ::= { msvmProcessorEntry 21 }

msvmprInstallDate OBJECT-TYPE
    SYNTAX     DateAndTime
    MAX-ACCESS read-only
    STATUS     current
    DESCRIPTION
        "A datetime value that indicates when the object
        was installed. Lack of a value does not indicate
        that the object is not installed."
    ::= { msvmProcessorEntry 22 }

msvmprLastErrorCode OBJECT-TYPE
    SYNTAX     Gauge32
    MAX-ACCESS read-only
    STATUS     current
    DESCRIPTION
        "Note: The use of this method is deprecated. 
        Deprecated description: LastErrorCode captures the
        last error code reported by the LogicalDevice."
    ::= { msvmProcessorEntry 23 }

msvmprLoadPercentage OBJECT-TYPE
    SYNTAX     Integer32
    UNITS "Percent"
    MAX-ACCESS read-only
    STATUS     current
    DESCRIPTION
        "Loading of this Processor, averaged over the last
        minute, in Percent."
    ::= { msvmProcessorEntry 24 }

msvmprLoadPercentageHistory OBJECT-TYPE
    SYNTAX     Integer32
    MAX-ACCESS read-only
    STATUS     current
    DESCRIPTION
        "The recorded history of percentage of the total
        processing power being consumed by the virtual
        system. This property is inherited from
        CIM_Processor."
    ::= { msvmProcessorEntry 25 }

msvmprLocationIndicator OBJECT-TYPE
    SYNTAX     INTEGER {
        unknown(0),
        on(2),
        off(3),
        notSupported(4)
    }
    MAX-ACCESS read-only
    STATUS     current
    DESCRIPTION
        "An integer that reflects the state of an indicator
        (e.g., LED) that is part of a device. Reading the
        value gives the current state. Writing the value
        with 'On'/'Off' turns the indicator on/off, other
        values may not be written."
    ::= { msvmProcessorEntry 26 }

msvmprMaxClockSpeed OBJECT-TYPE
    SYNTAX     Gauge32
    UNITS "MegaHertz"
    MAX-ACCESS read-only
    STATUS     current
    DESCRIPTION
        "The maximum speed (in MHz) of this Processor."
    ::= { msvmProcessorEntry 27 }

msvmprMaxQuiesceTime OBJECT-TYPE
    SYNTAX     Gauge32
    UNITS "MilliSeconds"
    MAX-ACCESS read-only
    STATUS     current
    DESCRIPTION
        "Note: The use of this property has been
        deprecated. When evaluating the use of Quiesce, it
        was determined that this single property is not
        adequate for describing when a device will
        automatically exit a quiescent state. In fact, the
        most likely scenario for a device to exit a
        quiescent state was determined to be based on the
        number of outstanding requests queued rather than
        on a maximum time. This decision will be
        re-evaluated and repositioned later. 
        Deprecated description: Maximum time, in
        milliseconds, that a Device can run in a 'Quiesced'
        state. The state is defined in its Availability and
        AdditionalAvailability properties, where 'Quiesced'
        is conveyed by the value 21. What occurs at the end
        of the time limit is device-specific. The Device
        can unquiesce, can be offline, or can take other
        actions. A value of 0 indicates that a Device can
        remain quiesced indefinitely."
    ::= { msvmProcessorEntry 28 }

msvmprName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmProcessorEntry 29 }

msvmprOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmProcessorEntry 30 }

msvmprOtherEnabledState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "EnabledState is an integer enumeration that
        indicates the enabled and disabled states of an
        element. It can also indicate the transitions
        between these requested states. For example,
        shutting down (value=4) and starting (value=10) are
        transient states between enabled and disabled. The
        following text briefly summarizes the various
        enabled and disabled states: 
        Enabled (2) indicates that the element is or could
        be executing commands, will process any queued
        commands, and queues new requests. 
        Disabled (3) indicates that the element will not
        execute commands and will drop any new requests. 
        Shutting Down (4) indicates that the element is in
        the process of going to a Disabled state. 
        Not Applicable (5) indicates the element does not
        support being enabled or disabled. 
        Enabled but Offline (6) indicates that the element
        might be completing commands, and will drop any new
        requests. 
        Test (7) indicates that the element is in a test
        state. 
        Deferred (8) indicates that the element might be
        completing commands, but will queue any new
        requests. 
        Quiesce (9) indicates that the element is enabled
        but in a restricted mode. The behavior of the
        element is similar to the Enabled state, but it
        processes only a restricted set of commands. All
        other requests are queued. 
        Starting (10) indicates that the element is in the
        process of going to an Enabled state. New requests
        are queued."
    ::= { msvmProcessorEntry 31 }

msvmprOtherFamilyDescription OBJECT-TYPE
    SYNTAX     Integer32
    MAX-ACCESS read-only
    STATUS     current
    DESCRIPTION
        "The Processor family type. For example, values
        include 'Pentium(R) processor with MMX(TM)
        technology' (value=14) and '68040' (value=96)."
    ::= { msvmProcessorEntry 32 }

msvmprOtherIdentifyingInfo OBJECT-TYPE
    SYNTAX     WtcsDisplayString (SIZE (0..256))
    MAX-ACCESS read-only
    STATUS     current
    DESCRIPTION
        "An array of free-form strings providing
        explanations and details behind the entries in the
        OtherIdentifyingInfo array. Note that each entry of
        this array is related to the entry in
        OtherIdentifyingInfo that is located at the same
        index."
    ::= { msvmProcessorEntry 33 }

msvmprPowerManagementCapability OBJECT-TYPE
    SYNTAX     INTEGER {
        unknown(0),
        notSupported(1),
        disabled(2),
        enabled(3),
        powerSavingModesEnteredAutomatic(4),
        powerStateSettable(5),
        powerCyclingSupported(6),
        timedPowerOnSupported(7)
    }
    MAX-ACCESS read-only
    STATUS     current
    DESCRIPTION
        "Note: The use of this property has been
        deprecated. Instead, use the PowerCapabilites
        property in an associated
        PowerManagementCapabilities class. Deprecated
        description: An enumerated array describing the
        power management capabilities of the Device."
    ::= { msvmProcessorEntry 34 }

msvmprPowerManagementSupported OBJECT-TYPE
    SYNTAX     TruthValue
    MAX-ACCESS read-only
    STATUS     current
    DESCRIPTION
        "Note: The use of this property has been
        deprecated. Instead, the existence of an associated
        PowerManagementCapabilities class (associated using
        the ElementCapabilities relationship) indicates
        that power management is supported. Deprecated
        description: Boolean that indicates that the Device
        can use power management."
    ::= { msvmProcessorEntry 35 }

msvmprPowerOnHours OBJECT-TYPE
    SYNTAX     Gauge32
    UNITS "Hours"
    MAX-ACCESS read-only
    STATUS     current
    DESCRIPTION
        "Note: The use of this method is deprecated. 
        Deprecated description: The number of consecutive
        hours that this Device has been powered on since
        its last power cycle."
    ::= { msvmProcessorEntry 36 }

msvmprRequestedState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "EnabledState is an integer enumeration that
        indicates the enabled and disabled states of an
        element. It can also indicate the transitions
        between these requested states. For example,
        shutting down (value=4) and starting (value=10) are
        transient states between enabled and disabled. The
        following text briefly summarizes the various
        enabled and disabled states: 
        Enabled (2) indicates that the element is or could
        be executing commands, will process any queued
        commands, and queues new requests. 
        Disabled (3) indicates that the element will not
        execute commands and will drop any new requests. 
        Shutting Down (4) indicates that the element is in
        the process of going to a Disabled state. 
        Not Applicable (5) indicates the element does not
        support being enabled or disabled. 
        Enabled but Offline (6) indicates that the element
        might be completing commands, and will drop any new
        requests. 
        Test (7) indicates that the element is in a test
        state. 
        Deferred (8) indicates that the element might be
        completing commands, but will queue any new
        requests. 
        Quiesce (9) indicates that the element is enabled
        but in a restricted mode. The behavior of the
        element is similar to the Enabled state, but it
        processes only a restricted set of commands. All
        other requests are queued. 
        Starting (10) indicates that the element is in the
        process of going to an Enabled state. New requests
        are queued."
    ::= { msvmProcessorEntry 37 }

msvmprRole OBJECT-TYPE
    SYNTAX     WtcsDisplayString
    MAX-ACCESS read-only
    STATUS     current
    DESCRIPTION
        "A free-form string that describes the role of the
        Processor, for example, 'Central Processor' or
        'Math Processor'."
    ::= { msvmProcessorEntry 38 }

msvmprStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmProcessorEntry 39 }

msvmprStatusDescriptions OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmProcessorEntry 40 }

msvmprStatusInfo OBJECT-TYPE
    SYNTAX     INTEGER {
        other(1),
        unknown(2),
        enabled(3),
        disabled(4),
        notApplicable(5)
    }
    MAX-ACCESS read-only
    STATUS     current
    DESCRIPTION
        "Note: The use of this method is deprecated in lieu
        of a more clearly named property (EnabledState)
        that is inherited from ManagedSystemElement and
        that has additional enumerated values. 
        Deprecated description: The StatusInfo property
        indicates whether the Logical Device is in an
        enabled state (value=3), disabled state (value=4),
        some other state (value=1), or an unknown state
        (value=2). If this property does not apply to the
        LogicalDevice, the value 5 ('Not Applicable')
        should be used. If a Device is
        ('Enabled')(value=3), it has been powered up and is
        configured and operational. The Device might or
        might not be functionally active, depending on
        whether its Availability (or
        AdditionalAvailability) indicates that it is
        ('Running/Full Power')(value=3) or ('Off line')
        (value=8). In an enabled but offline mode, a Device
        might be performing out-of-band requests, such as
        running Diagnostics. If StatusInfo is ('Disabled')
        (value=4), a Device can only be 'enabled' or
        powered off. In a personal computer environment,
        ('Disabled') means that the driver of the device is
        not available in the stack. In other environments,
        a Device can be disabled by removing its
        configuration file. A disabled device is physically
        present in a System and consuming resources, but it
        cannot be communicated with until a driver is
        loaded, a configuration file is loaded, or some
        other 'enabling' activity has occurred."
    ::= { msvmProcessorEntry 41 }

msvmprStepping OBJECT-TYPE
    SYNTAX     Integer32
    MAX-ACCESS read-only
    STATUS     current
    DESCRIPTION
        "The Processor family type. For example, values
        include 'Pentium(R) processor with MMX(TM)
        technology' (value=14) and '68040' (value=96)."
    ::= { msvmProcessorEntry 42 }

msvmprSystemCreationClassName OBJECT-TYPE
    SYNTAX     WtcsDisplayString (SIZE (0..256))
    MAX-ACCESS read-only
    STATUS     current
    DESCRIPTION
        "The CreationClassName of the scoping system."
    ::= { msvmProcessorEntry 43 }

msvmprSystemName OBJECT-TYPE
    SYNTAX     WtcsDisplayString (SIZE (0..256))
    MAX-ACCESS read-only
    STATUS     current
    DESCRIPTION
        "The System Name of the scoping system."
    ::= { msvmProcessorEntry 44 }

msvmprTimeOfLastStateChange OBJECT-TYPE
    SYNTAX     DateAndTime
    MAX-ACCESS read-only
    STATUS     current
    DESCRIPTION
        "The date or time when the EnabledState of the
        element last changed. If the state of the element
        has not changed and this property is populated,
        then it must be set to a 0 interval value. If a
        state change was requested, but rejected or not yet
        processed, the property must not be updated."
    ::= { msvmProcessorEntry 45 }

msvmprTotalPowerOnHours OBJECT-TYPE
    SYNTAX     Gauge32
    UNITS "Hours"
    MAX-ACCESS read-only
    STATUS     current
    DESCRIPTION
        "Note: The use of this method is deprecated. 
        Deprecated description: The total number of hours
        that this Device has been powered on."
    ::= { msvmProcessorEntry 46 }

msvmprUniqueID OBJECT-TYPE
    SYNTAX     WtcsDisplayString
    MAX-ACCESS read-only
    STATUS     current
    DESCRIPTION
        "A globally unique identifier for the Processor.
        This identifier can be unique only within a
        Processor Family."
    ::= { msvmProcessorEntry 47 }

msvmprUpgradeMethod OBJECT-TYPE
    SYNTAX     Integer32
    MAX-ACCESS read-only
    STATUS     current
    DESCRIPTION
        "CPU socket information that includes data on how
        this Processor can be upgraded (if upgrades are
        supported). This property is an integer
        enumeration."
    ::= { msvmProcessorEntry 48 }

msvmProcessorPoolTable OBJECT-TYPE
    SYNTAX     SEQUENCE OF MsvmProcessorPool
    MAX-ACCESS not-accessible
    STATUS     current
    DESCRIPTION
        "Aggregates the processor resources that may be
        allocated to a virtual system."
    ::= { msvmProcessor 2 }

msvmProcessorPoolEntry OBJECT-TYPE
    SYNTAX     MsvmProcessorPool
    MAX-ACCESS not-accessible
    STATUS     current
    DESCRIPTION
        "None"
    INDEX      { msvmppIndex }
    ::= { msvmProcessorPoolTable 1 }

MsvmProcessorPool ::= SEQUENCE {
    msvmppIndex Integer32,
    msvmppAllocationUnits WtcsDisplayString,
    msvmppCapacity Gauge32,
    msvmppCaption WtcsDisplayString,
    msvmppDescription WtcsDisplayString,
    msvmppElementName WtcsDisplayString,
    msvmppHealthState INTEGER,
    msvmppInstallDate DateAndTime,
    msvmppInstanceID WtcsDisplayString,
    msvmppName WtcsDisplayString,
    msvmppOperationalStatus INTEGER,
    msvmppOtherResourceType INTEGER,
    msvmppPoolID WtcsDisplayString,
    msvmppPrimordial TruthValue,
    msvmppReserved Gauge32,
    msvmppResourceSubType WtcsDisplayString,
    msvmppResourceType INTEGER,
    msvmppStatus WtcsDisplayString,
    msvmppStatusDescriptions WtcsDisplayString,
    msvmppUnreservable Integer32
}

msvmppIndex OBJECT-TYPE
    SYNTAX     Integer32 (1..2147483647)
    MAX-ACCESS read-only
    STATUS     current
    DESCRIPTION
        "The value of this object uniquely identifies the
        instance entry for this class."
    ::= { msvmProcessorPoolEntry 1 }

msvmppAllocationUnits OBJECT-TYPE
    SYNTAX     WtcsDisplayString
    MAX-ACCESS read-only
    STATUS     current
    DESCRIPTION
        "This property specifies the units of allocation
        used by the ResourcePool.  For example, when
        ResourceType=Processor, AllocationUnits may be set
        to MHZ. When ResourceType=Memory, AllocationUnits
        may be set to MB"
    ::= { msvmProcessorPoolEntry 2 }

msvmppCapacity OBJECT-TYPE
    SYNTAX     Gauge32
    MAX-ACCESS read-only
    STATUS     current
    DESCRIPTION
        "This property represents the maximum amount (in
        units of AllocationUnits) of reservations that the
        ResourcePool can support."
    ::= { msvmProcessorPoolEntry 3 }

msvmppCaption OBJECT-TYPE
    SYNTAX     WtcsDisplayString (SIZE (0..64))
    MAX-ACCESS read-only
    STATUS     current
    DESCRIPTION
        "The Caption property is a short textual
        description (one- line string) of the object."
    ::= { msvmProcessorPoolEntry 4 }

msvmppDescription OBJECT-TYPE
    SYNTAX     WtcsDisplayString
    MAX-ACCESS read-only
    STATUS     current
    DESCRIPTION
        "The Description property provides a textual
        description of the object."
    ::= { msvmProcessorPoolEntry 5 }

msvmppElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmProcessorPoolEntry 6 }

msvmppHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmProcessorPoolEntry 7 }

msvmppInstallDate OBJECT-TYPE
    SYNTAX     DateAndTime
    MAX-ACCESS read-only
    STATUS     current
    DESCRIPTION
        "A datetime value that indicates when the object
        was installed. Lack of a value does not indicate
        that the object is not installed."
    ::= { msvmProcessorPoolEntry 8 }

msvmppInstanceID OBJECT-TYPE
    SYNTAX     WtcsDisplayString
    MAX-ACCESS read-only
    STATUS     current
    DESCRIPTION
        "Within the scope of the instantiating Namespace,
        InstanceID opaquely and uniquely identifies an
        instance of this class. To ensure uniqueness within
        the NameSpace, the value of InstanceID should be
        constructed using the following 'preferred'
        algorithm: 
        <OrgID>:<LocalID> 
        Where <OrgID> and <LocalID> are separated by a
        colon (:), and where <OrgID> must include a
        copyrighted, trademarked, or otherwise unique name
        that is owned by the business entity that is
        creating or defining the InstanceID or that is a
        registered ID assigned to the business entity by a
        recognized global authority. (This requirement is
        similar to the <Schema Name>_<Class Name> structure
        of Schema class names.) In addition, to ensure
        uniqueness, <OrgID> must not contain a colon (:).
        When using this algorithm, the first colon to
        appear in InstanceID must appear between <OrgID>
        and <LocalID>. 
        <LocalID> is chosen by the business entity and
        should not be reused to identify different
        underlying (real-world) elements. If the above
        'preferred' algorithm is not used, the defining
        entity must assure that the resulting InstanceID is
        not reused across any InstanceIDs produced by this
        or other providers for the NameSpace of this
        instance. 
        For DMTF-defined instances, the 'preferred'
        algorithm must be used with the <OrgID> set to
        CIM."
    ::= { msvmProcessorPoolEntry 9 }

msvmppName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmProcessorPoolEntry 10 }

msvmppOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmProcessorPoolEntry 11 }

msvmppOtherResourceType OBJECT-TYPE
    SYNTAX     INTEGER {
        other(1),
        computerSystem(2),
        processor(3),
        memory(4),
        ideController(5),
        parallelSCSIHBA(6),
        fcHBA(7),
        iSCSIHBA(8),
        ibHCA(9),
        ethernetAdapter(10),
        iOSlot(11),
        iODevice(12),
        floppyDrive(13),
        cdDrive(14),
        dvddrive(15),
        serialport(16),
        parallelport(17),
        usbController(18),
        graphicscontroller(19),
        storageExtent(20),
        disk(21),
        tape(22),
        otherstoragedevice(23),
        firewireController(24),
        partitionableUnit(25),
        basePartitionableUnit(26),
        powerSupply(27),
        coolingDevice(28),
        dmtfreserved(29)
    }
    MAX-ACCESS read-only
    STATUS     current
    DESCRIPTION
        "The type of resource this ResourcePool may
        allocate."
    ::= { msvmProcessorPoolEntry 12 }

msvmppPoolID OBJECT-TYPE
    SYNTAX     WtcsDisplayString
    MAX-ACCESS read-only
    STATUS     current
    DESCRIPTION
        "An opaque identifier for the pool.  This property
        is used to provide correlation across save and
        restore of configuration data to underlying
        persistent storage."
    ::= { msvmProcessorPoolEntry 13 }

msvmppPrimordial OBJECT-TYPE
    SYNTAX     TruthValue
    MAX-ACCESS read-only
    STATUS     current
    DESCRIPTION
        "If true, 'Primordial' indicates that this
        ResourcePool is the base from which resources are
        drawn and returned in the activity of resource
        management. Being primordial means that this
        ResourcePool shall not be created or deleted by
        consumers of this model. However, other actions,
        modeled or not, may affect the characteristics or
        size of primordial ResourcePools. If false,
        'Primordial' indicates that the ResourcePool, a
        concrete Resource Pool, is subject to resource
        allocation services functions. This distinction is
        important because higher-level ResourcePools may be
        assembled using the Component or
        ElementAllocatedFromPool associations. Although the
        higher-level abstractions can be created and
        deleted, the most basic, (i.e. primordial),
        hardware-based ResourcePools cannot. They are
        physically realized as part of the System, or are
        actually managed by some other System and imported
        as if they were physically realized."
    ::= { msvmProcessorPoolEntry 14 }

msvmppReserved OBJECT-TYPE
    SYNTAX     Gauge32
    MAX-ACCESS read-only
    STATUS     current
    DESCRIPTION
        "This property represents the current reservations
        (in units of AllocationUnits) spread across all
        active allocations from this pool.  In a
        hierarchical configuration, this represents the sum
        of all descendant ResourcePool current
        reservations."
    ::= { msvmProcessorPoolEntry 15 }

msvmppResourceSubType OBJECT-TYPE
    SYNTAX     WtcsDisplayString
    MAX-ACCESS read-only
    STATUS     current
    DESCRIPTION
        "A string describing an implementation specific
        sub-type for this pool.  For example, this may be
        used to distinguish different models of the same
        resource type."
    ::= { msvmProcessorPoolEntry 16 }

msvmppResourceType OBJECT-TYPE
    SYNTAX     INTEGER {
        other(1),
        computerSystem(2),
        processor(3),
        memory(4),
        ideController(5),
        parallelSCSIHBA(6),
        fcHBA(7),
        iSCSIHBA(8),
        ibHCA(9),
        ethernetAdapter(10),
        iOSlot(11),
        iODevice(12),
        floppyDrive(13),
        cdDrive(14),
        dvddrive(15),
        serialport(16),
        parallelport(17),
        usbController(18),
        graphicscontroller(19),
        storageExtent(20),
        disk(21),
        tape(22),
        otherstoragedevice(23),
        firewireController(24),
        partitionableUnit(25),
        basePartitionableUnit(26),
        powerSupply(27),
        coolingDevice(28),
        dmtfreserved(29)
    }
    MAX-ACCESS read-only
    STATUS     current
    DESCRIPTION
        "A string that describes the resource type when a
        well defined value is not available and
        ResourceType is set to 0 for Other."
    ::= { msvmProcessorPoolEntry 17 }

msvmppStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmProcessorPoolEntry 18 }

msvmppStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmProcessorPoolEntry 19 }

msvmppUnreservable OBJECT-TYPE
    SYNTAX     Integer32
    MAX-ACCESS read-only
    STATUS     current
    DESCRIPTION
        "This property is inherited from
        CIM_ProcessorPool."
    ::= { msvmProcessorPoolEntry 20 }

msvmProcessorSettingDataTable OBJECT-TYPE
    SYNTAX     SEQUENCE OF MsvmProcessorSettingData
    MAX-ACCESS not-accessible
    STATUS     current
    DESCRIPTION
        "Represents the virtual processor settings for a
        virtual system."
    ::= { msvmProcessor 3 }

msvmProcessorSettingDataEntry OBJECT-TYPE
    SYNTAX     MsvmProcessorSettingData
    MAX-ACCESS not-accessible
    STATUS     current
    DESCRIPTION
        "None"
    INDEX      { msvmpsdIndex }
    ::= { msvmProcessorSettingDataTable 1 }

MsvmProcessorSettingData ::= SEQUENCE {
    msvmpsdIndex Integer32,
    msvmpsdAddress WtcsDisplayString,
    msvmpsdAllocationUnits WtcsDisplayString,
    msvmpsdAutomaticAllocation TruthValue,
    msvmpsdAutomaticDeallocation TruthValue,
    msvmpsdCaption WtcsDisplayString,
    msvmpsdConnection WtcsDisplayString,
    msvmpsdConsumerVisibility INTEGER,
    msvmpsdDescription WtcsDisplayString,
    msvmpsdDeviceID WtcsDisplayString,
    msvmpsdDeviceIDFormat WtcsDisplayString,
    msvmpsdElementName WtcsDisplayString,
    msvmpsdHostResource WtcsDisplayString,
    msvmpsdInstanceID WtcsDisplayString,
    msvmpsdIsVirtualized TruthValue,
    msvmpsdLimit Gauge32,
    msvmpsdLimitCPUID TruthValue,
    msvmpsdMappingBehavior INTEGER,
    msvmpsdOtherResourceType INTEGER,
    msvmpsdParent WtcsDisplayString,
    msvmpsdPoolID WtcsDisplayString,
    msvmpsdProcessorsPerSocket Integer32,
    msvmpsdReservation Gauge32,
    msvmpsdResourceSubType WtcsDisplayString,
    msvmpsdResourceType INTEGER,
    msvmpsdSocketCount Integer32,
    msvmpsdThreadsEnabled TruthValue,
    msvmpsdVirtualQuantity Gauge32,
    msvmpsdWeight Gauge32
}

msvmpsdIndex OBJECT-TYPE
    SYNTAX     Integer32 (1..2147483647)
    MAX-ACCESS read-only
    STATUS     current
    DESCRIPTION
        "The value of this object uniquely identifies the
        instance entry for this class."
    ::= { msvmProcessorSettingDataEntry 1 }

msvmpsdAddress OBJECT-TYPE
    SYNTAX     WtcsDisplayString
    MAX-ACCESS read-only
    STATUS     current
    DESCRIPTION
        "The address of the resource.For example, the MAC
        address of a Ethernet port."
    ::= { msvmProcessorSettingDataEntry 2 }

msvmpsdAllocationUnits OBJECT-TYPE
    SYNTAX     WtcsDisplayString
    MAX-ACCESS read-only
    STATUS     current
    DESCRIPTION
        "This property specifies the units of allocation
        used by the Reservation and Limit properties.  For
        example, when ResourceType=Processor,
        AllocationUnits may be set to MHZ. When
        ResourceType=Memory, AllocationUnits may be set to
        MB"
    ::= { msvmProcessorSettingDataEntry 3 }

msvmpsdAutomaticAllocation OBJECT-TYPE
    SYNTAX     TruthValue
    MAX-ACCESS read-only
    STATUS     current
    DESCRIPTION
        "This property specifies if the resource will be
        automatically allocated.  For example when set to
        true, when the consuming virtual computer system is
        powered on, this resource would be allocated.  A
        value of false indicates the resource must be
        explicitly allocated.  For example, the setting may
        represent removable media (cdrom, floppy, etc.)
        where at power on time, the media isnot present. 
        An explicit operation is required to allocate the
        resource."
    ::= { msvmProcessorSettingDataEntry 4 }

msvmpsdAutomaticDeallocation OBJECT-TYPE
    SYNTAX     TruthValue
    MAX-ACCESS read-only
    STATUS     current
    DESCRIPTION
        "This property specifies if the resource will be
        automatically de-allocated.  For example, when set
        to true, when the consuming virtual computer system
        is powered off, this resource would be
        de-allocated.  When set to false, the resource will
        remain allocated and must be explicitly
        de-allocated."
    ::= { msvmProcessorSettingDataEntry 5 }

msvmpsdCaption OBJECT-TYPE
    SYNTAX     WtcsDisplayString (SIZE (0..64))
    MAX-ACCESS read-only
    STATUS     current
    DESCRIPTION
        "The Caption property is a short textual
        description (one- line string) of the object."
    ::= { msvmProcessorSettingDataEntry 6 }

msvmpsdConnection OBJECT-TYPE
    SYNTAX     WtcsDisplayString
    MAX-ACCESS read-only
    STATUS     current
    DESCRIPTION
        "The thing to which this resource is connected. 
        For example, a named network or switch port."
    ::= { msvmProcessorSettingDataEntry 7 }

msvmpsdConsumerVisibility OBJECT-TYPE
    SYNTAX     INTEGER {
        unknown(0),
        passedThrough(2),
        virtualized(3),
        notrepresented(4)
    }
    MAX-ACCESS read-only
    STATUS     current
    DESCRIPTION
        "Describes the consumers visibility to the
        allocated  resource.
        A value of 'Passed-Through' indicates the
        underlying or host resource is utilized and passed
        through to the consumer, possibly using
        partitioning. At least one item shall be present in
        the DeviceID property.  
        A value of 'Virtualized' indicates the resource is
        virtualized and may not map directly to an
        underlying/host resource. Some implementations may
        support specific assignment for virtualized
        resources, in which case the host resource(s) are
        exposed using the DeviceID property. 
        A value of 'Not represented' indicates a
        representation of the resource does not exist
        within the context of the resource consumer."
    ::= { msvmProcessorSettingDataEntry 8 }

msvmpsdDescription OBJECT-TYPE
    SYNTAX     WtcsDisplayString
    MAX-ACCESS read-only
    STATUS     current
    DESCRIPTION
        "The Description property provides a textual
        description of the object."
    ::= { msvmProcessorSettingDataEntry 9 }

msvmpsdDeviceID OBJECT-TYPE
    SYNTAX     WtcsDisplayString
    MAX-ACCESS read-only
    STATUS     current
    DESCRIPTION
        "Address or other identifying information to
        uniquely name the logical device. This property is
        inherited from CIM_LogicalDevice and it is always
        set to 'Microsoft:<GUID>'."
    ::= { msvmProcessorSettingDataEntry 10 }

msvmpsdDeviceIDFormat OBJECT-TYPE
    SYNTAX     WtcsDisplayString
    MAX-ACCESS read-only
    STATUS     current
    DESCRIPTION
        "The format of the corresponding device ID, or the
        supported device IDs when used to represent a
        capability. This property is inherited from
        CIM_ResourceAllocationSettingData and is not used."
    ::= { msvmProcessorSettingDataEntry 11 }

msvmpsdElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmProcessorSettingDataEntry 12 }

msvmpsdHostResource OBJECT-TYPE
    SYNTAX     WtcsDisplayString
    MAX-ACCESS read-only
    STATUS     current
    DESCRIPTION
        "This property exposes specific assignment to host
        or underlying resources.        The embedded
        instances shall contain only key properties and be
        treated as Object Paths. If the virtual resource
        may be scheduled on a number of underlying
        resources, this property shall be left NULL. In
        that case, the DeviceAllocatedFromPool or
        ResourceAllocationFromPool associations may be used
        to determine the pool of host resources this
        virtual resource may be scheduled on. If specific
        assignment is utilized, all underlying resources
        used by this virtual resource shall be listed in
        this array.  Typically the array will contain one
        item, however for aggregate allocations, such as
        multiple processors, multiple host resources may be
        specified."
    ::= { msvmProcessorSettingDataEntry 13 }

msvmpsdInstanceID OBJECT-TYPE
    SYNTAX     WtcsDisplayString
    MAX-ACCESS read-only
    STATUS     current
    DESCRIPTION
        "Within the scope of the instantiating Namespace,
        InstanceID opaquely and uniquely identifies an
        instance of this class. To ensure uniqueness within
        the NameSpace, the value of InstanceID should be
        constructed using the following 'preferred'
        algorithm: 
        <OrgID>:<LocalID> 
        Where <OrgID> and <LocalID> are separated by a
        colon (:), and where <OrgID> must include a
        copyrighted, trademarked, or otherwise unique name
        that is owned by the business entity that is
        creating or defining the InstanceID or that is a
        registered ID assigned to the business entity by a
        recognized global authority. (This requirement is
        similar to the <Schema Name>_<Class Name> structure
        of Schema class names.) In addition, to ensure
        uniqueness, <OrgID> must not contain a colon (:).
        When using this algorithm, the first colon to
        appear in InstanceID must appear between <OrgID>
        and <LocalID>. 
        <LocalID> is chosen by the business entity and
        should not be reused to identify different
        underlying (real-world) elements. If the above
        'preferred' algorithm is not used, the defining
        entity must assure that the resulting InstanceID is
        not reused across any InstanceIDs produced by this
        or other providers for the NameSpace of this
        instance. 
        For DMTF-defined instances, the 'preferred'
        algorithm must be used with the <OrgID> set to
        CIM."
    ::= { msvmProcessorSettingDataEntry 14 }

msvmpsdIsVirtualized OBJECT-TYPE
    SYNTAX     TruthValue
    MAX-ACCESS read-only
    STATUS     current
    DESCRIPTION
        "Specifies if this device is virtualized or passed
        through, possibly using partitioning. When set to
        False, the underlying or host resource is utilized.
        At least one item shall be present in the DeviceID
        property. When set to True, the resource is
        virtualized and may not map directly to an
        underlying/host resource. Some implementations may
        support specific assignment for virtualized
        resources, in which case the host resource(s) are
        exposed using the DeviceID property. This property
        is set to True."
    ::= { msvmProcessorSettingDataEntry 15 }

msvmpsdLimit OBJECT-TYPE
    SYNTAX     Gauge32
    MAX-ACCESS read-only
    STATUS     current
    DESCRIPTION
        "This property specifies the upper bound, or
        maximum amount of resource that will be granted for
        this allocation. For example, a system which
        supports memory paging may support setting the
        Limit of a Memory allocation below that of the
        VirtualQuantity, thus forcing paging to occur for
        this allocation."
    ::= { msvmProcessorSettingDataEntry 16 }

msvmpsdLimitCPUID OBJECT-TYPE
    SYNTAX     TruthValue
    MAX-ACCESS read-only
    STATUS     current
    DESCRIPTION
        "This property is inherited from
        CIM_ResourceAllocationSettingData and is not used."
    ::= { msvmProcessorSettingDataEntry 17 }

msvmpsdMappingBehavior OBJECT-TYPE
    SYNTAX     INTEGER {
        unknown(0),
        notSupported(1),
        dedicated(2),
        softAffinity(3),
        hardAffinity(4)
    }
    MAX-ACCESS read-only
    STATUS     current
    DESCRIPTION
        "Specifies how this resource maps to underlying
        resourcesIf the HostResource array contains any
        entries, this property reflects how the resource
        maps to those specific resources."
    ::= { msvmProcessorSettingDataEntry 18 }

msvmpsdOtherResourceType OBJECT-TYPE
    SYNTAX     INTEGER {
        other(1),
        computerSystem(2),
        processor(3),
        memory(4),
        ideController(5),
        parallelSCSIHBA(6),
        fcHBA(7),
        iSCSIHBA(8),
        ibHCA(9),
        ethernetAdapter(10),
        iOSlot(11),
        iODevice(12),
        floppyDrive(13),
        cdDrive(14),
        dvddrive(15),
        serialport(16),
        parallelport(17),
        usbController(18),
        graphicscontroller(19),
        storageExtent(20),
        disk(21),
        tape(22),
        otherstoragedevice(23),
        firewireController(24),
        partitionableUnit(25),
        basePartitionableUnit(26),
        powerSupply(27),
        coolingDevice(28),
        dmtfreserved(29)
    }
    MAX-ACCESS read-only
    STATUS     current
    DESCRIPTION
        "The type of resource this allocation setting
        represents."
    ::= { msvmProcessorSettingDataEntry 19 }

msvmpsdParent OBJECT-TYPE
    SYNTAX     WtcsDisplayString
    MAX-ACCESS read-only
    STATUS     current
    DESCRIPTION
        "The Parent of the resource.  For example, a
        controller for the current allocation"
    ::= { msvmProcessorSettingDataEntry 20 }

msvmpsdPoolID OBJECT-TYPE
    SYNTAX     WtcsDisplayString
    MAX-ACCESS read-only
    STATUS     current
    DESCRIPTION
        "This property specifies which ResourcePool the
        resource is currently allocated from, or which
        ResourcePool the resource will be allocated from
        when the allocation occurs."
    ::= { msvmProcessorSettingDataEntry 21 }

msvmpsdProcessorsPerSocket OBJECT-TYPE
    SYNTAX     Integer32
    MAX-ACCESS read-only
    STATUS     current
    DESCRIPTION
        "The number of processors, or cores, configured for
        each socket in the virtual system."
    ::= { msvmProcessorSettingDataEntry 22 }

msvmpsdReservation OBJECT-TYPE
    SYNTAX     Gauge32
    MAX-ACCESS read-only
    STATUS     current
    DESCRIPTION
        "This property specifies the amount of resource
        guaranteed to be available for this allocation.  On
        system which support over-commitment of resources,
        this value is typically used for admission control
        to prevent an an allocation from being accepted
        thus preventing starvation."
    ::= { msvmProcessorSettingDataEntry 23 }

msvmpsdResourceSubType OBJECT-TYPE
    SYNTAX     WtcsDisplayString
    MAX-ACCESS read-only
    STATUS     current
    DESCRIPTION
        "A string describing an implementation specific
        sub-type for this resource.  For example, this may
        be used to distinguish different models of the same
        resource type."
    ::= { msvmProcessorSettingDataEntry 24 }

msvmpsdResourceType OBJECT-TYPE
    SYNTAX     INTEGER {
        other(0),
        computerSystem(1),
        cpu(2),
        memory(3),
        ideController(4),
        parallelSCSIHBA(5),
        fcSCSIHBA(6),
        iSCSIHBA(7),
        fcpAdapter(8),
        ibHCA(9),
        ethernetAdapter(10),
        iOSlot(11),
        iODevice(12),
        floppyDrive(13),
        cdDVDdrive(14),
        serialport(15),
        parallelport(16),
        usbController(17),
        graphicscontroller(18),
        disk(19),
        tape(20),
        otherstoragedevice(21),
        firewireController(22),
        partitionableUnit(23),
        dmtfreserved(24)
    }
    MAX-ACCESS read-only
    STATUS     current
    DESCRIPTION
        "A string that describes the resource type when a
        well defined value is not available and
        ResourceType has the value 'Other'."
    ::= { msvmProcessorSettingDataEntry 25 }

msvmpsdSocketCount OBJECT-TYPE
    SYNTAX     Integer32
    MAX-ACCESS read-only
    STATUS     current
    DESCRIPTION
        "An integer that defines the number of processor
        sockets in the virtual machine. The total number of
        processors is the value of this property times the
        value of the ProcessorsPerSocket property."
    ::= { msvmProcessorSettingDataEntry 26 }

msvmpsdThreadsEnabled OBJECT-TYPE
    SYNTAX     TruthValue
    MAX-ACCESS read-only
    STATUS     current
    DESCRIPTION
        "Specifies whether hardware threads should be
        visible to the virtual system. If the physical
        processor does not support hardware threads, this
        value has no effect in the virtual system."
    ::= { msvmProcessorSettingDataEntry 27 }

msvmpsdVirtualQuantity OBJECT-TYPE
    SYNTAX     Gauge32
    MAX-ACCESS read-only
    STATUS     current
    DESCRIPTION
        "This property specifies the quantity of resources
        presented to the consumer.  For example, when
        ResourceType=Processor,  this property would
        reflect the number of discrete Processors presented
        to the virtual computer system.  When
        ResourceType=Memory, this property could reflect
        the number of MB reported to the virtual computer
        system."
    ::= { msvmProcessorSettingDataEntry 28 }

msvmpsdWeight OBJECT-TYPE
    SYNTAX     Gauge32
    MAX-ACCESS read-only
    STATUS     current
    DESCRIPTION
        "This property specifies a relative priority for
        this allocation in relation to other allocations
        from the same ResourcePool.  This property has no
        unit of measure, and is only relevant when compared
        to other allocations vying for the same host
        resources."
    ::= { msvmProcessorSettingDataEntry 29 }

msvmProfileRegistration OBJECT-IDENTITY
    STATUS     current
    DESCRIPTION
        "The following are virtualization WMI classes
        related to profile registration."
    ::= { informantHyperV 7 }

msvmResourcePoolComponentTable OBJECT-TYPE
    SYNTAX     SEQUENCE OF MsvmResourcePoolComponent
    MAX-ACCESS not-accessible
    STATUS     current
    DESCRIPTION
        "Represents a resource pool component of the
        Microsoft Windows Hyper-V platform."
    ::= { msvmProfileRegistration 1 }

msvmResourcePoolComponentEntry OBJECT-TYPE
    SYNTAX     MsvmResourcePoolComponent
    MAX-ACCESS not-accessible
    STATUS     current
    DESCRIPTION
        "None"
    INDEX      { msvmrpcIndex }
    ::= { msvmResourcePoolComponentTable 1 }

MsvmResourcePoolComponent ::= SEQUENCE {
    msvmrpcIndex Integer32,
    msvmrpcAllocCapabilityClassName WtcsDisplayString,
    msvmrpcCLSID WtcsDisplayString,
    msvmrpcContext Gauge32,
    msvmrpcEnabled TruthValue,
    msvmrpcName WtcsDisplayString,
    msvmrpcResourcePoolClassName WtcsDisplayString
}

msvmrpcIndex OBJECT-TYPE
    SYNTAX     Integer32 (1..2147483647)
    MAX-ACCESS read-only
    STATUS     current
    DESCRIPTION
        "The value of this object uniquely identifies the
        instance entry for this class."
    ::= { msvmResourcePoolComponentEntry 1 }

msvmrpcAllocCapabilityClassName OBJECT-TYPE
    SYNTAX     WtcsDisplayString
    MAX-ACCESS read-only
    STATUS     current
    DESCRIPTION
        "The name of the class derived from
        CIM_AllocationCapabilities that describes the
        allocation capabilities of this resource pool. This
        property is inherited from
        Msvm_VirtualizationComponent."
    ::= { msvmResourcePoolComponentEntry 2 }

msvmrpcCLSID OBJECT-TYPE
    SYNTAX     WtcsDisplayString
    MAX-ACCESS read-only
    STATUS     current
    DESCRIPTION
        "GUID that represents the class identifier of the
        component's COM object."
    ::= { msvmResourcePoolComponentEntry 3 }

msvmrpcContext OBJECT-TYPE
    SYNTAX     Gauge32
    MAX-ACCESS read-only
    STATUS     current
    DESCRIPTION
        "Context in which the newly created object will
        run. This value is passed in the dwClsContext
        parameter to CoCreateInstance."
    ::= { msvmResourcePoolComponentEntry 4 }

msvmrpcEnabled OBJECT-TYPE
    SYNTAX     TruthValue
    MAX-ACCESS read-only
    STATUS     current
    DESCRIPTION
        "If true, this instance is enabled and can be used
        to complete client requests."
    ::= { msvmResourcePoolComponentEntry 5 }

msvmrpcName OBJECT-TYPE
    SYNTAX     WtcsDisplayString
    MAX-ACCESS read-only
    STATUS     current
    DESCRIPTION
        "Language-neutral string that uniquely identifies
        the component. The following format is suggested to
        prevent naming conflicts:
        
        vendor|component|version
        
        For example, this component name represents version
        1.0 of the Microsoft Emulated Network Port
        Component:
        Microsoft|EmulatedNetworkPortComponent|V1.0"
    ::= { msvmResourcePoolComponentEntry 6 }

msvmrpcResourcePoolClassName OBJECT-TYPE
    SYNTAX     WtcsDisplayString
    MAX-ACCESS read-only
    STATUS     current
    DESCRIPTION
        "The name of the class derived from
        CIM_ResourcePool that implements the resource pool.
        This property is inherited from
        Msvm_VirtualizationComponent."
    ::= { msvmResourcePoolComponentEntry 7 }

msvmResourcePoolRegistrateTable OBJECT-TYPE
    SYNTAX     SEQUENCE OF MsvmResourcePoolRegistration
    MAX-ACCESS not-accessible
    STATUS     current
    DESCRIPTION
        "Registers a component as supplying global resource
        pool-related objects."
    ::= { msvmProfileRegistration 2 }

msvmResourcePoolRegistrateEntry OBJECT-TYPE
    SYNTAX     MsvmResourcePoolRegistration
    MAX-ACCESS not-accessible
    STATUS     current
    DESCRIPTION
        "None"
    INDEX      { msvmrprIndex }
    ::= { msvmResourcePoolRegistrateTable 1 }

MsvmResourcePoolRegistration ::= SEQUENCE {
    msvmrprIndex Integer32,
    msvmrprComponent WtcsDisplayString,
    msvmrprResourceType WtcsDisplayString
}

msvmrprIndex OBJECT-TYPE
    SYNTAX     Integer32 (1..2147483647)
    MAX-ACCESS read-only
    STATUS     current
    DESCRIPTION
        "The value of this object uniquely identifies the
        instance entry for this class."
    ::= { msvmResourcePoolRegistrateEntry 1 }

msvmrprComponent OBJECT-TYPE
    SYNTAX     WtcsDisplayString
    MAX-ACCESS read-only
    STATUS     current
    DESCRIPTION
        "Reference to an Msvm_ResourcePoolComponent
        instance that describes the COM object that
        implements this class."
    ::= { msvmResourcePoolRegistrateEntry 2 }

msvmrprResourceType OBJECT-TYPE
    SYNTAX     WtcsDisplayString
    MAX-ACCESS read-only
    STATUS     current
    DESCRIPTION
        "Reference to an Msvm_ResourceDefinition instance
        that describes a resource type supported by the
        component."
    ::= { msvmResourcePoolRegistrateEntry 3 }

msvmResourceTypeDefinitionTable OBJECT-TYPE
    SYNTAX     SEQUENCE OF MsvmResourceTypeDefinition
    MAX-ACCESS not-accessible
    STATUS     current
    DESCRIPTION
        "Defines a mapping of a resource type to its
        implementation classes."
    ::= { msvmProfileRegistration 3 }

msvmResourceTypeDefinitionEntry OBJECT-TYPE
    SYNTAX     MsvmResourceTypeDefinition
    MAX-ACCESS not-accessible
    STATUS     current
    DESCRIPTION
        "None"
    INDEX      { msvmrtdIndex }
    ::= { msvmResourceTypeDefinitionTable 1 }

MsvmResourceTypeDefinition ::= SEQUENCE {
    msvmrtdIndex Integer32,
    msvmrtdLogicalDeviceClassName WtcsDisplayString,
    msvmrtdOtherResourceType WtcsDisplayString,
    msvmrtdResourceSubType WtcsDisplayString,
    msvmrtdResourceType INTEGER,
    msvmrtdSettingDataClassName WtcsDisplayString
}

msvmrtdIndex OBJECT-TYPE
    SYNTAX     Integer32 (1..2147483647)
    MAX-ACCESS read-only
    STATUS     current
    DESCRIPTION
        "The value of this object uniquely identifies the
        instance entry for this class."
    ::= { msvmResourceTypeDefinitionEntry 1 }

msvmrtdLogicalDeviceClassName OBJECT-TYPE
    SYNTAX     WtcsDisplayString
    MAX-ACCESS read-only
    STATUS     current
    DESCRIPTION
        "The name of the class derived from
        CIM_LogicalDevice that implements the logical
        device for this resource type. This property is
        inherited from CIM_ResourceAllocationSettingData."
    ::= { msvmResourceTypeDefinitionEntry 2 }

msvmrtdOtherResourceType OBJECT-TYPE
    SYNTAX     WtcsDisplayString
    MAX-ACCESS read-only
    STATUS     current
    DESCRIPTION
        "A string that describes the resource type when a
        well defined value is not available and
        ResourceType has the value 'Other'."
    ::= { msvmResourceTypeDefinitionEntry 3 }

msvmrtdResourceSubType OBJECT-TYPE
    SYNTAX     WtcsDisplayString
    MAX-ACCESS read-only
    STATUS     current
    DESCRIPTION
        "A string describing an implementation specific
        sub-type for this resource.  For example, this may
        be used to distinguish different models of the same
        resource type."
    ::= { msvmResourceTypeDefinitionEntry 4 }

msvmrtdResourceType OBJECT-TYPE
    SYNTAX     INTEGER {
        other(1),
        computerSystem(2),
        processor(3),
        memory(4),
        ideController(5),
        parallelSCSIHBA(6),
        fcHBA(7),
        iSCSIHBA(8),
        ibHCA(9),
        ethernetAdapter(10),
        iOSlot(11),
        iODevice(12),
        floppyDrive(13),
        cdDrive(14),
        dvddrive(15),
        serialport(16),
        parallelport(17),
        usbController(18),
        graphicscontroller(19),
        storageExtent(20),
        disk(21),
        tape(22),
        otherstoragedevice(23),
        firewireController(24),
        partitionableUnit(25),
        basePartitionableUnit(26),
        powerSupply(27),
        coolingDevice(28),
        dmtfreserved(29)
    }
    MAX-ACCESS read-only
    STATUS     current
    DESCRIPTION
        "The type of resource this allocation setting
        represents."
    ::= { msvmResourceTypeDefinitionEntry 5 }

msvmrtdSettingDataClassName OBJECT-TYPE
    SYNTAX     WtcsDisplayString
    MAX-ACCESS read-only
    STATUS     current
    DESCRIPTION
        "The name of the class derived from
        CIM_ResourceAllocationSettingData that implements
        the settings for this resource type. This property
        is inherited from
        CIM_ResourceAllocationSettingData."
    ::= { msvmResourceTypeDefinitionEntry 6 }

msvmVirtualSystemRscComponTable OBJECT-TYPE
    SYNTAX     SEQUENCE OF MsvmVirtualSysResourceComponent
    MAX-ACCESS not-accessible
    STATUS     current
    DESCRIPTION
        "Represents a virtual device component of the
        Microsoft Windows Hyper-V platform."
    ::= { msvmProfileRegistration 4 }

msvmVirtualSystemRscComponEntry OBJECT-TYPE
    SYNTAX     MsvmVirtualSysResourceComponent
    MAX-ACCESS not-accessible
    STATUS     current
    DESCRIPTION
        "None"
    INDEX      { msvmvsrcIndex }
    ::= { msvmVirtualSystemRscComponTable 1 }

MsvmVirtualSysResourceComponent ::= SEQUENCE {
    msvmvsrcIndex Integer32,
    msvmvsrcCLSID WtcsDisplayString,
    msvmvsrcContext Gauge32,
    msvmvsrcEnabled TruthValue,
    msvmvsrcHotAdd TruthValue,
    msvmvsrcHotRemove TruthValue,
    msvmvsrcName WtcsDisplayString,
    msvmvsrcType INTEGER
}

msvmvsrcIndex OBJECT-TYPE
    SYNTAX     Integer32 (1..2147483647)
    MAX-ACCESS read-only
    STATUS     current
    DESCRIPTION
        "The value of this object uniquely identifies the
        instance entry for this class."
    ::= { msvmVirtualSystemRscComponEntry 1 }

msvmvsrcCLSID OBJECT-TYPE
    SYNTAX     WtcsDisplayString
    MAX-ACCESS read-only
    STATUS     current
    DESCRIPTION
        "GUID that represents the class identifier of the
        component's COM object."
    ::= { msvmVirtualSystemRscComponEntry 2 }

msvmvsrcContext OBJECT-TYPE
    SYNTAX     Gauge32
    MAX-ACCESS read-only
    STATUS     current
    DESCRIPTION
        "Context in which the newly created object will
        run. This value is passed in the dwClsContext
        parameter to CoCreateInstance."
    ::= { msvmVirtualSystemRscComponEntry 3 }

msvmvsrcEnabled OBJECT-TYPE
    SYNTAX     TruthValue
    MAX-ACCESS read-only
    STATUS     current
    DESCRIPTION
        "If true, this instance is enabled and can be used
        to complete client requests."
    ::= { msvmVirtualSystemRscComponEntry 4 }

msvmvsrcHotAdd OBJECT-TYPE
    SYNTAX     TruthValue
    MAX-ACCESS read-only
    STATUS     current
    DESCRIPTION
        "If true, this instance can be hot-added to a VM."
    ::= { msvmVirtualSystemRscComponEntry 5 }

msvmvsrcHotRemove OBJECT-TYPE
    SYNTAX     TruthValue
    MAX-ACCESS read-only
    STATUS     current
    DESCRIPTION
        "If true, this instance can be hot-removed from a
        VM."
    ::= { msvmVirtualSystemRscComponEntry 6 }

msvmvsrcName OBJECT-TYPE
    SYNTAX     WtcsDisplayString
    MAX-ACCESS read-only
    STATUS     current
    DESCRIPTION
        "Language-neutral string that uniquely identifies
        the component. The following format is suggested to
        prevent naming conflicts:
        
        vendor|component|version
        
        For example, this component name represents version
        1.0 of the Microsoft Emulated Network Port
        Component:
        Microsoft|EmulatedNetworkPortComponent|V1.0"
    ::= { msvmVirtualSystemRscComponEntry 7 }

msvmvsrcType OBJECT-TYPE
    SYNTAX     INTEGER {
        notChangeable(0),
        singleton(1),
        multiInstance(2),
        subdevice(3)
    }
    MAX-ACCESS read-only
    STATUS     current
    DESCRIPTION
        "The relationship of the WMI object that is
        described here with the virtual device.Singleton is
        a top level WMI object that is tied 1:1 with a
        Virtual Device and can only exist once per
        VM.MultiInstance is a top level WMI object that can
        exist multiple times per VM and is tied 1:1 with a
        Virtual Device.Subdevice is a WMI object that has
        not parent reference but is controlled by only one
        Virtual Device that can exist only once per VM. The
        WMI object though can exist multiples times."
    ::= { msvmVirtualSystemRscComponEntry 8 }

msvmVirtualSystemRscRegistTable OBJECT-TYPE
    SYNTAX     SEQUENCE OF MsvmVirtualSystemResourceReg
    MAX-ACCESS not-accessible
    STATUS     current
    DESCRIPTION
        "Registers a component as supplying virtual
        system-specific resource-related objects."
    ::= { msvmProfileRegistration 5 }

msvmVirtualSystemRscRegistEntry OBJECT-TYPE
    SYNTAX     MsvmVirtualSystemResourceReg
    MAX-ACCESS not-accessible
    STATUS     current
    DESCRIPTION
        "None"
    INDEX      { msvmvsrrIndex }
    ::= { msvmVirtualSystemRscRegistTable 1 }

MsvmVirtualSystemResourceReg ::= SEQUENCE {
    msvmvsrrIndex Integer32,
    msvmvsrrComponent WtcsDisplayString,
    msvmvsrrIsRootDevice TruthValue,
    msvmvsrrResourceType WtcsDisplayString
}

msvmvsrrIndex OBJECT-TYPE
    SYNTAX     Integer32 (1..2147483647)
    MAX-ACCESS read-only
    STATUS     current
    DESCRIPTION
        "The value of this object uniquely identifies the
        instance entry for this class."
    ::= { msvmVirtualSystemRscRegistEntry 1 }

msvmvsrrComponent OBJECT-TYPE
    SYNTAX     WtcsDisplayString
    MAX-ACCESS read-only
    STATUS     current
    DESCRIPTION
        "Reference to an
        Msvm_VirtualSystemResourceComponent instance that
        describes the COM object that implements this
        class."
    ::= { msvmVirtualSystemRscRegistEntry 2 }

msvmvsrrIsRootDevice OBJECT-TYPE
    SYNTAX     TruthValue
    MAX-ACCESS read-only
    STATUS     current
    DESCRIPTION
        "If true, this registration indicates that the
        specified resource type is the root (or
        parent-less) device for this component. Only one
        registration may exist with IsRootDevice to set
        true. Otherwise, this registration represents a
        mapping to a sub-device. This property is always
        set to False."
    ::= { msvmVirtualSystemRscRegistEntry 3 }

msvmvsrrResourceType OBJECT-TYPE
    SYNTAX     WtcsDisplayString
    MAX-ACCESS read-only
    STATUS     current
    DESCRIPTION
        "None"
    ::= { msvmVirtualSystemRscRegistEntry 4 }

msvmResourceManagement OBJECT-IDENTITY
    STATUS     current
    DESCRIPTION
        "The following are virtualization WMI classes
        related to resource management."
    ::= { informantHyperV 8 }

msvmAllocationCapabilitiesTable OBJECT-TYPE
    SYNTAX     SEQUENCE OF MsvmAllocationCapabilities
    MAX-ACCESS not-accessible
    STATUS     current
    DESCRIPTION
        "Defines the means by which a client can discover
        the valid range of default settings for a virtual
        resource."
    ::= { msvmResourceManagement 1 }

msvmAllocationCapabilitiesEntry OBJECT-TYPE
    SYNTAX     MsvmAllocationCapabilities
    MAX-ACCESS not-accessible
    STATUS     current
    DESCRIPTION
        "None"
    INDEX      { msvmalcIndex }
    ::= { msvmAllocationCapabilitiesTable 1 }

MsvmAllocationCapabilities ::= SEQUENCE {
    msvmalcIndex Integer32,
    msvmalcCaption WtcsDisplayString,
    msvmalcDescription WtcsDisplayString,
    msvmalcElementName WtcsDisplayString,
    msvmalcInstanceID WtcsDisplayString,
    msvmalcOtherResourceType WtcsDisplayString,
    msvmalcRequestTypesSupported INTEGER,
    msvmalcResourceSubType WtcsDisplayString,
    msvmalcResourceType INTEGER,
    msvmalcSharingMode INTEGER,
    msvmalcSupportedAddStates INTEGER,
    msvmalcSupportedRemoveStates INTEGER
}

msvmalcIndex OBJECT-TYPE
    SYNTAX     Integer32 (1..2147483647)
    MAX-ACCESS read-only
    STATUS     current
    DESCRIPTION
        "The value of this object uniquely identifies the
        instance entry for this class."
    ::= { msvmAllocationCapabilitiesEntry 1 }

msvmalcCaption OBJECT-TYPE
    SYNTAX     WtcsDisplayString (SIZE (0..64))
    MAX-ACCESS read-only
    STATUS     current
    DESCRIPTION
        "The Caption property is a short textual
        description (one- line string) of the object."
    ::= { msvmAllocationCapabilitiesEntry 2 }

msvmalcDescription OBJECT-TYPE
    SYNTAX     WtcsDisplayString
    MAX-ACCESS read-only
    STATUS     current
    DESCRIPTION
        "The Description property provides a textual
        description of the object."
    ::= { msvmAllocationCapabilitiesEntry 3 }

msvmalcElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmAllocationCapabilitiesEntry 4 }

msvmalcInstanceID OBJECT-TYPE
    SYNTAX     WtcsDisplayString
    MAX-ACCESS read-only
    STATUS     current
    DESCRIPTION
        "Within the scope of the instantiating Namespace,
        InstanceID opaquely and uniquely identifies an
        instance of this class. In order to ensure
        uniqueness within the NameSpace, the value of
        InstanceID SHOULD be constructed using the
        following 'preferred' algorithm: 
        <OrgID>:<LocalID> 
        Where <OrgID> and <LocalID> are separated by a
        colon ':', and where <OrgID> MUST include a
        copyrighted, trademarked or otherwise unique name
        that is owned by the business entity
        creating/defining the InstanceID, or is a
        registered ID that is assigned to the business
        entity by a recognized global authority (This is
        similar to the <Schema Name>_<Class Name> structure
        of Schema class names.) In addition, to ensure
        uniqueness <OrgID> MUST NOT contain a colon (':').
        When using this algorithm, the first colon to
        appear in InstanceID MUST appear between <OrgID>
        and <LocalID>. 
        <LocalID> is chosen by the business entity and
        SHOULD not be re-used to identify different
        underlying (real-world) elements. If the above
        'preferred' algorithm is not used, the defining
        entity MUST assure that the resultant InstanceID is
        not re-used across any InstanceIDs produced by this
        or other providers for this instance's NameSpace. 
        For DMTF defined instances, the 'preferred'
        algorithm MUST be used with the <OrgID> set to
        'CIM'."
    ::= { msvmAllocationCapabilitiesEntry 5 }

msvmalcOtherResourceType OBJECT-TYPE
    SYNTAX     WtcsDisplayString
    MAX-ACCESS read-only
    STATUS     current
    DESCRIPTION
        "A string that describes the resource type when a
        well defined value is not available and
        ResourceType has the value 'Other'."
    ::= { msvmAllocationCapabilitiesEntry 6 }

msvmalcRequestTypesSupported OBJECT-TYPE
    SYNTAX     INTEGER {
        unknown(0),
        specific(1),
        general(2),
        both(3)
    }
    MAX-ACCESS read-only
    STATUS     current
    DESCRIPTION
        "Indicates whether requesting a specific resource
        is supported
        'Specific' -- request can include a request for
        specific resource
        'General' -- request does not include specific
        resource
        'Both' -- both specific and general are supported."
    ::= { msvmAllocationCapabilitiesEntry 7 }

msvmalcResourceSubType OBJECT-TYPE
    SYNTAX     WtcsDisplayString
    MAX-ACCESS read-only
    STATUS     current
    DESCRIPTION
        "A string describing an implementation specific
        sub-type for this resource.  For example, this may
        be used to distinguish different models of the same
        resource type."
    ::= { msvmAllocationCapabilitiesEntry 8 }

msvmalcResourceType OBJECT-TYPE
    SYNTAX     INTEGER {
        other(1),
        computerSystem(2),
        processor(3),
        memory(4),
        ideController(5),
        parallelSCSIHBA(6),
        fcHBA(7),
        iSCSIHBA(8),
        ibHCA(9),
        ethernetAdapter(10),
        iOSlot(11),
        iODevice(12),
        floppyDrive(13),
        cdDVDdrive(14),
        serialport(15),
        parallelport(16),
        usbController(17),
        graphicscontroller(18),
        disk(19),
        tape(20),
        otherstoragedevice(21),
        firewireController(22),
        partitionableUnit(23),
        basePartitionableUnit(24),
        powerSupply(25),
        coolingDevice(26),
        dmtfreserved(27)
    }
    MAX-ACCESS read-only
    STATUS     current
    DESCRIPTION
        "The type of resource this allocation setting
        represents."
    ::= { msvmAllocationCapabilitiesEntry 9 }

msvmalcSharingMode OBJECT-TYPE
    SYNTAX     INTEGER {
        unknown(0),
        dedicated(1),
        shared(2)
    }
    MAX-ACCESS read-only
    STATUS     current
    DESCRIPTION
        "Indicates how access to underlying resource is
        granted: 
        'Exclusive' -- exclusive access to underlying
        resource
        'Shared' -- shared use of underlying resource.
        Actual quantity is controlled by min, max size,
        weights, etc."
    ::= { msvmAllocationCapabilitiesEntry 10 }

msvmalcSupportedAddStates OBJECT-TYPE
    SYNTAX     INTEGER {
        unknown(0),
        other(1),
        enabled(2),
        disabled(3),
        shuttingDown(4),
        notApplicable(5),
        enabledbutOffline(6),
        inTest(7),
        deferred(8),
        quiesce(9),
        starting(10),
        paused(11),
        suspended(12)
    }
    MAX-ACCESS read-only
    STATUS     current
    DESCRIPTION
        "Indicates the System states that the addition of
        this resource is supported"
    ::= { msvmAllocationCapabilitiesEntry 11 }

msvmalcSupportedRemoveStates OBJECT-TYPE
    SYNTAX     INTEGER {
        unknown(0),
        other(1),
        enabled(2),
        disabled(3),
        shuttingDown(4),
        notApplicable(5),
        enabledbutOffline(6),
        inTest(7),
        deferred(8),
        quiesce(9),
        starting(10),
        paused(11),
        suspended(12)
    }
    MAX-ACCESS read-only
    STATUS     current
    DESCRIPTION
        "Indicates the System states that the removal of
        this resource is supported"
    ::= { msvmAllocationCapabilitiesEntry 12 }

msvmElementAllocateFromPoolTable OBJECT-TYPE
    SYNTAX     SEQUENCE OF MsvmElementAllocatedFromPool
    MAX-ACCESS not-accessible
    STATUS     current
    DESCRIPTION
        "ElementAllocatedFromPool associates an instance of
        CIM_LogicalElement representing an allocated
        Resource with the CIM_ResourcePool from which it
        was allocated."
    ::= { msvmResourceManagement 2 }

msvmElementAllocateFromPoolEntry OBJECT-TYPE
    SYNTAX     MsvmElementAllocatedFromPool
    MAX-ACCESS not-accessible
    STATUS     current
    DESCRIPTION
        "None"
    INDEX      { msvmeafpIndex }
    ::= { msvmElementAllocateFromPoolTable 1 }

MsvmElementAllocatedFromPool ::= SEQUENCE {
    msvmeafpIndex Integer32,
    msvmeafpAntecedent WtcsDisplayString,
    msvmeafpDependent WtcsDisplayString
}

msvmeafpIndex OBJECT-TYPE
    SYNTAX     Integer32 (1..2147483647)
    MAX-ACCESS read-only
    STATUS     current
    DESCRIPTION
        "The value of this object uniquely identifies the
        instance entry for this class."
    ::= { msvmElementAllocateFromPoolEntry 1 }

msvmeafpAntecedent OBJECT-TYPE
    SYNTAX     WtcsDisplayString
    MAX-ACCESS read-only
    STATUS     current
    DESCRIPTION
        "Antecedent represents the independent object in
        this association."
    ::= { msvmElementAllocateFromPoolEntry 2 }

msvmeafpDependent OBJECT-TYPE
    SYNTAX     WtcsDisplayString
    MAX-ACCESS read-only
    STATUS     current
    DESCRIPTION
        "Dependent represents the object that is dependent
        on the Antecedent."
    ::= { msvmElementAllocateFromPoolEntry 3 }

msvmElementCapabilitiesTable OBJECT-TYPE
    SYNTAX     SEQUENCE OF MsvmElementCapabilities
    MAX-ACCESS not-accessible
    STATUS     current
    DESCRIPTION
        "ElementCapabilities represents the association
        between ManagedElements and their Capabilities."
    ::= { msvmResourceManagement 3 }

msvmElementCapabilitiesEntry OBJECT-TYPE
    SYNTAX     MsvmElementCapabilities
    MAX-ACCESS not-accessible
    STATUS     current
    DESCRIPTION
        "None"
    INDEX      { msvmecIndex }
    ::= { msvmElementCapabilitiesTable 1 }

MsvmElementCapabilities ::= SEQUENCE {
    msvmecIndex Integer32,
    msvmecCapabilities WtcsDisplayString,
    msvmecManagedElement WtcsDisplayString
}

msvmecIndex OBJECT-TYPE
    SYNTAX     Integer32 (1..2147483647)
    MAX-ACCESS read-only
    STATUS     current
    DESCRIPTION
        "The value of this object uniquely identifies the
        instance entry for this class."
    ::= { msvmElementCapabilitiesEntry 1 }

msvmecCapabilities OBJECT-TYPE
    SYNTAX     WtcsDisplayString
    MAX-ACCESS read-only
    STATUS     current
    DESCRIPTION
        "The Capabilities object associated with the
        element."
    ::= { msvmElementCapabilitiesEntry 2 }

msvmecManagedElement OBJECT-TYPE
    SYNTAX     WtcsDisplayString
    MAX-ACCESS read-only
    STATUS     current
    DESCRIPTION
        "The managed element."
    ::= { msvmElementCapabilitiesEntry 3 }

msvmResourceAllocFromPoolTable OBJECT-TYPE
    SYNTAX     SEQUENCE OF MsvmResourceAllocationFromPool
    MAX-ACCESS not-accessible
    STATUS     current
    DESCRIPTION
        "ResourceAllocationFromPool associates an instance
        of CIM_ResourceAllocationSettingData representing a
        resource allocation with the CIM_ResourcePool from
        which it is allocated."
    ::= { msvmResourceManagement 4 }

msvmResourceAllocFromPoolEntry OBJECT-TYPE
    SYNTAX     MsvmResourceAllocationFromPool
    MAX-ACCESS not-accessible
    STATUS     current
    DESCRIPTION
        "None"
    INDEX      { msvmrafpIndex }
    ::= { msvmResourceAllocFromPoolTable 1 }

MsvmResourceAllocationFromPool ::= SEQUENCE {
    msvmrafpIndex Integer32,
    msvmrafpAntecedent WtcsDisplayString,
    msvmrafpDependent WtcsDisplayString
}

msvmrafpIndex OBJECT-TYPE
    SYNTAX     Integer32 (1..2147483647)
    MAX-ACCESS read-only
    STATUS     current
    DESCRIPTION
        "The value of this object uniquely identifies the
        instance entry for this class."
    ::= { msvmResourceAllocFromPoolEntry 1 }

msvmrafpAntecedent OBJECT-TYPE
    SYNTAX     WtcsDisplayString
    MAX-ACCESS read-only
    STATUS     current
    DESCRIPTION
        "Antecedent represents the independent object in
        this association."
    ::= { msvmResourceAllocFromPoolEntry 2 }

msvmrafpDependent OBJECT-TYPE
    SYNTAX     WtcsDisplayString
    MAX-ACCESS read-only
    STATUS     current
    DESCRIPTION
        "Dependent represents the object that is dependent
        on the Antecedent."
    ::= { msvmResourceAllocFromPoolEntry 3 }

msvmResourceAllocSetDataTable OBJECT-TYPE
    SYNTAX     SEQUENCE OF MsvmResourceAllocationSetData
    MAX-ACCESS not-accessible
    STATUS     current
    DESCRIPTION
        "Represents the current and recorded allocation
        states of a virtual resource."
    ::= { msvmResourceManagement 5 }

msvmResourceAllocSetDataEntry OBJECT-TYPE
    SYNTAX     MsvmResourceAllocationSetData
    MAX-ACCESS not-accessible
    STATUS     current
    DESCRIPTION
        "None"
    INDEX      { msvmrasdIndex }
    ::= { msvmResourceAllocSetDataTable 1 }

MsvmResourceAllocationSetData ::= SEQUENCE {
    msvmrasdIndex Integer32,
    msvmrasdAddress WtcsDisplayString,
    msvmrasdAllocationUnits WtcsDisplayString,
    msvmrasdAutomaticAllocation TruthValue,
    msvmrasdAutomaticDeallocation TruthValue,
    msvmrasdCaption WtcsDisplayString,
    msvmrasdConnection WtcsDisplayString,
    msvmrasdConsumerVisibility INTEGER,
    msvmrasdDescription WtcsDisplayString,
    msvmrasdElementName WtcsDisplayString,
    msvmrasdHostResource WtcsDisplayString,
    msvmrasdInstanceID WtcsDisplayString,
    msvmrasdLimit Gauge32,
    msvmrasdMappingBehavior INTEGER,
    msvmrasdOtherResourceType WtcsDisplayString,
    msvmrasdParent WtcsDisplayString,
    msvmrasdPoolID WtcsDisplayString,
    msvmrasdReservation Gauge32,
    msvmrasdResourceSubType WtcsDisplayString,
    msvmrasdResourceType INTEGER,
    msvmrasdVirtualQuantity Gauge32,
    msvmrasdVirtualSystemIdentifiers WtcsDisplayString,
    msvmrasdWeight Gauge32
}

msvmrasdIndex OBJECT-TYPE
    SYNTAX     Integer32 (1..2147483647)
    MAX-ACCESS read-only
    STATUS     current
    DESCRIPTION
        "The value of this object uniquely identifies the
        instance entry for this class."
    ::= { msvmResourceAllocSetDataEntry 1 }

msvmrasdAddress OBJECT-TYPE
    SYNTAX     WtcsDisplayString
    MAX-ACCESS read-only
    STATUS     current
    DESCRIPTION
        "The address of the resource.For example, the MAC
        address of a Ethernet port."
    ::= { msvmResourceAllocSetDataEntry 2 }

msvmrasdAllocationUnits OBJECT-TYPE
    SYNTAX     WtcsDisplayString
    MAX-ACCESS read-only
    STATUS     current
    DESCRIPTION
        "This property specifies the units of allocation
        used by the Reservation and Limit properties.  For
        example, when ResourceType=Processor,
        AllocationUnits may be set to MHZ. When
        ResourceType=Memory, AllocationUnits may be set to
        MB"
    ::= { msvmResourceAllocSetDataEntry 3 }

msvmrasdAutomaticAllocation OBJECT-TYPE
    SYNTAX     TruthValue
    MAX-ACCESS read-only
    STATUS     current
    DESCRIPTION
        "This property specifies if the resource will be
        automatically allocated.  For example when set to
        true, when the consuming virtual computer system is
        powered on, this resource would be allocated.  A
        value of false indicates the resource must be
        explicitly allocated.  For example, the setting may
        represent removable media (cdrom, floppy, etc.)
        where at power on time, the media isnot present. 
        An explicit operation is required to allocate the
        resource."
    ::= { msvmResourceAllocSetDataEntry 4 }

msvmrasdAutomaticDeallocation OBJECT-TYPE
    SYNTAX     TruthValue
    MAX-ACCESS read-only
    STATUS     current
    DESCRIPTION
        "This property specifies if the resource will be
        automatically de-allocated.  For example, when set
        to true, when the consuming virtual computer system
        is powered off, this resource would be
        de-allocated.  When set to false, the resource will
        remain allocated and must be explicitly
        de-allocated."
    ::= { msvmResourceAllocSetDataEntry 5 }

msvmrasdCaption OBJECT-TYPE
    SYNTAX     WtcsDisplayString (SIZE (0..64))
    MAX-ACCESS read-only
    STATUS     current
    DESCRIPTION
        "The Caption property is a short textual
        description (one- line string) of the object."
    ::= { msvmResourceAllocSetDataEntry 6 }

msvmrasdConnection OBJECT-TYPE
    SYNTAX     WtcsDisplayString
    MAX-ACCESS read-only
    STATUS     current
    DESCRIPTION
        "The thing to which this resource is connected. 
        For example, a named network or switch port."
    ::= { msvmResourceAllocSetDataEntry 7 }

msvmrasdConsumerVisibility OBJECT-TYPE
    SYNTAX     INTEGER {
        unknown(0),
        passedThrough(2),
        virtualized(3),
        notrepresented(4)
    }
    MAX-ACCESS read-only
    STATUS     current
    DESCRIPTION
        "Describes the consumers visibility to the
        allocated  resource.
        A value of 'Passed-Through' indicates the
        underlying or host resource is utilized and passed
        through to the consumer, possibly using
        partitioning. At least one item shall be present in
        the DeviceID property.  
        A value of 'Virtualized' indicates the resource is
        virtualized and may not map directly to an
        underlying/host resource. Some implementations may
        support specific assignment for virtualized
        resources, in which case the host resource(s) are
        exposed using the DeviceID property. 
        A value of 'Not represented' indicates a
        representation of the resource does not exist
        within the context of the resource consumer."
    ::= { msvmResourceAllocSetDataEntry 8 }

msvmrasdDescription OBJECT-TYPE
    SYNTAX     WtcsDisplayString
    MAX-ACCESS read-only
    STATUS     current
    DESCRIPTION
        "The Description property provides a textual
        description of the object."
    ::= { msvmResourceAllocSetDataEntry 9 }

msvmrasdElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmResourceAllocSetDataEntry 10 }

msvmrasdHostResource OBJECT-TYPE
    SYNTAX     WtcsDisplayString
    MAX-ACCESS read-only
    STATUS     current
    DESCRIPTION
        "This property exposes specific assignment to host
        or underlying resources.        The embedded
        instances shall contain only key properties and be
        treated as Object Paths. If the virtual resource
        may be scheduled on a number of underlying
        resources, this property shall be left NULL. In
        that case, the DeviceAllocatedFromPool or
        ResourceAllocationFromPool associations may be used
        to determine the pool of host resources this
        virtual resource may be scheduled on. If specific
        assignment is utilized, all underlying resources
        used by this virtual resource shall be listed in
        this array.  Typically the array will contain one
        item, however for aggregate allocations, such as
        multiple processors, multiple host resources may be
        specified."
    ::= { msvmResourceAllocSetDataEntry 11 }

msvmrasdInstanceID OBJECT-TYPE
    SYNTAX     WtcsDisplayString
    MAX-ACCESS read-only
    STATUS     current
    DESCRIPTION
        "Within the scope of the instantiating Namespace,
        InstanceID opaquely and uniquely identifies an
        instance of this class. To ensure uniqueness within
        the NameSpace, the value of InstanceID should be
        constructed using the following 'preferred'
        algorithm: 
        <OrgID>:<LocalID> 
        Where <OrgID> and <LocalID> are separated by a
        colon (:), and where <OrgID> must include a
        copyrighted, trademarked, or otherwise unique name
        that is owned by the business entity that is
        creating or defining the InstanceID or that is a
        registered ID assigned to the business entity by a
        recognized global authority. (This requirement is
        similar to the <Schema Name>_<Class Name> structure
        of Schema class names.) In addition, to ensure
        uniqueness, <OrgID> must not contain a colon (:).
        When using this algorithm, the first colon to
        appear in InstanceID must appear between <OrgID>
        and <LocalID>. 
        <LocalID> is chosen by the business entity and
        should not be reused to identify different
        underlying (real-world) elements. If the above
        'preferred' algorithm is not used, the defining
        entity must assure that the resulting InstanceID is
        not reused across any InstanceIDs produced by this
        or other providers for the NameSpace of this
        instance. 
        For DMTF-defined instances, the 'preferred'
        algorithm must be used with the <OrgID> set to
        CIM."
    ::= { msvmResourceAllocSetDataEntry 12 }

msvmrasdLimit OBJECT-TYPE
    SYNTAX     Gauge32
    MAX-ACCESS read-only
    STATUS     current
    DESCRIPTION
        "This property specifies the upper bound, or
        maximum amount of resource that will be granted for
        this allocation. For example, a system which
        supports memory paging may support setting the
        Limit of a Memory allocation below that of the
        VirtualQuantity, thus forcing paging to occur for
        this allocation."
    ::= { msvmResourceAllocSetDataEntry 13 }

msvmrasdMappingBehavior OBJECT-TYPE
    SYNTAX     INTEGER {
        unknown(0),
        notSupported(1),
        dedicated(2),
        softAffinity(3),
        hardAffinity(4)
    }
    MAX-ACCESS read-only
    STATUS     current
    DESCRIPTION
        "Specifies how this resource maps to underlying
        resourcesIf the HostResource array contains any
        entries, this property reflects how the resource
        maps to those specific resources."
    ::= { msvmResourceAllocSetDataEntry 14 }

msvmrasdOtherResourceType OBJECT-TYPE
    SYNTAX     WtcsDisplayString
    MAX-ACCESS read-only
    STATUS     current
    DESCRIPTION
        "A string that describes the resource type when a
        well defined value is not available and
        ResourceType has the value 'Other'."
    ::= { msvmResourceAllocSetDataEntry 15 }

msvmrasdParent OBJECT-TYPE
    SYNTAX     WtcsDisplayString
    MAX-ACCESS read-only
    STATUS     current
    DESCRIPTION
        "The Parent of the resource.  For example, a
        controller for the current allocation"
    ::= { msvmResourceAllocSetDataEntry 16 }

msvmrasdPoolID OBJECT-TYPE
    SYNTAX     WtcsDisplayString
    MAX-ACCESS read-only
    STATUS     current
    DESCRIPTION
        "This property specifies which ResourcePool the
        resource is currently allocated from, or which
        ResourcePool the resource will be allocated from
        when the allocation occurs."
    ::= { msvmResourceAllocSetDataEntry 17 }

msvmrasdReservation OBJECT-TYPE
    SYNTAX     Gauge32
    MAX-ACCESS read-only
    STATUS     current
    DESCRIPTION
        "This property specifies the amount of resource
        guaranteed to be available for this allocation.  On
        system which support over-commitment of resources,
        this value is typically used for admission control
        to prevent an an allocation from being accepted
        thus preventing starvation."
    ::= { msvmResourceAllocSetDataEntry 18 }

msvmrasdResourceSubType OBJECT-TYPE
    SYNTAX     WtcsDisplayString
    MAX-ACCESS read-only
    STATUS     current
    DESCRIPTION
        "A string describing an implementation specific
        sub-type for this resource.  For example, this may
        be used to distinguish different models of the same
        resource type."
    ::= { msvmResourceAllocSetDataEntry 19 }

msvmrasdResourceType OBJECT-TYPE
    SYNTAX     INTEGER {
        other(1),
        computerSystem(2),
        processor(3),
        memory(4),
        ideController(5),
        parallelSCSIHBA(6),
        fcHBA(7),
        iSCSIHBA(8),
        ibHCA(9),
        ethernetAdapter(10),
        iOSlot(11),
        iODevice(12),
        floppyDrive(13),
        cdDrive(14),
        dvddrive(15),
        serialport(16),
        parallelport(17),
        usbController(18),
        graphicscontroller(19),
        storageExtent(20),
        disk(21),
        tape(22),
        otherstoragedevice(23),
        firewireController(24),
        partitionableUnit(25),
        basePartitionableUnit(26),
        powerSupply(27),
        coolingDevice(28),
        dmtfreserved(29)
    }
    MAX-ACCESS read-only
    STATUS     current
    DESCRIPTION
        "The type of resource this allocation setting
        represents."
    ::= { msvmResourceAllocSetDataEntry 20 }

msvmrasdVirtualQuantity OBJECT-TYPE
    SYNTAX     Gauge32
    MAX-ACCESS read-only
    STATUS     current
    DESCRIPTION
        "This property specifies the quantity of resources
        presented to the consumer.  For example, when
        ResourceType=Processor,  this property would
        reflect the number of discrete Processors presented
        to the virtual computer system.  When
        ResourceType=Memory, this property could reflect
        the number of MB reported to the virtual computer
        system."
    ::= { msvmResourceAllocSetDataEntry 21 }

msvmrasdVirtualSystemIdentifiers OBJECT-TYPE
    SYNTAX     WtcsDisplayString
    MAX-ACCESS read-only
    STATUS     current
    DESCRIPTION
        "A free form string array of identifiers of this
        resource presented to the virtual computer system's
        operating system. The indexes and values per index
        are defined on a per resource basis, that is, for
        each enumerated ResourceType value."
    ::= { msvmResourceAllocSetDataEntry 22 }

msvmrasdWeight OBJECT-TYPE
    SYNTAX     Gauge32
    MAX-ACCESS read-only
    STATUS     current
    DESCRIPTION
        "This property specifies a relative priority for
        this allocation in relation to other allocations
        from the same ResourcePool.  This property has no
        unit of measure, and is only relevant when compared
        to other allocations vying for the same host
        resources."
    ::= { msvmResourceAllocSetDataEntry 23 }

msvmResourcePoolTable OBJECT-TYPE
    SYNTAX     SEQUENCE OF MsvmResourcePool
    MAX-ACCESS not-accessible
    STATUS     current
    DESCRIPTION
        "Describes a type of virtual resource available for
        use in virtual systems."
    ::= { msvmResourceManagement 6 }

msvmResourcePoolEntry OBJECT-TYPE
    SYNTAX     MsvmResourcePool
    MAX-ACCESS not-accessible
    STATUS     current
    DESCRIPTION
        "None"
    INDEX      { msvmrpIndex }
    ::= { msvmResourcePoolTable 1 }

MsvmResourcePool ::= SEQUENCE {
    msvmrpIndex Integer32,
    msvmrpAllocationUnits WtcsDisplayString,
    msvmrpCapacity Gauge32,
    msvmrpCaption WtcsDisplayString,
    msvmrpDescription WtcsDisplayString,
    msvmrpElementName WtcsDisplayString,
    msvmrpHealthState INTEGER,
    msvmrpInstallDate DateAndTime,
    msvmrpInstanceID WtcsDisplayString,
    msvmrpName WtcsDisplayString,
    msvmrpOperationalStatus INTEGER,
    msvmrpOtherResourceType WtcsDisplayString,
    msvmrpPoolID WtcsDisplayString,
    msvmrpPrimordial TruthValue,
    msvmrpReserved Gauge32,
    msvmrpResourceSubType WtcsDisplayString,
    msvmrpResourceType INTEGER,
    msvmrpStatus WtcsDisplayString,
    msvmrpStatusDescriptions WtcsDisplayString
}

msvmrpIndex OBJECT-TYPE
    SYNTAX     Integer32 (1..2147483647)
    MAX-ACCESS read-only
    STATUS     current
    DESCRIPTION
        "The value of this object uniquely identifies the
        instance entry for this class."
    ::= { msvmResourcePoolEntry 1 }

msvmrpAllocationUnits OBJECT-TYPE
    SYNTAX     WtcsDisplayString
    MAX-ACCESS read-only
    STATUS     current
    DESCRIPTION
        "This property specifies the units of allocation
        used by the ResourcePool.  For example, when
        ResourceType=Processor, AllocationUnits may be set
        to MHZ. When ResourceType=Memory, AllocationUnits
        may be set to MB"
    ::= { msvmResourcePoolEntry 2 }

msvmrpCapacity OBJECT-TYPE
    SYNTAX     Gauge32
    MAX-ACCESS read-only
    STATUS     current
    DESCRIPTION
        "This property represents the maximum amount (in
        units of AllocationUnits) of reservations that the
        ResourcePool can support."
    ::= { msvmResourcePoolEntry 3 }

msvmrpCaption OBJECT-TYPE
    SYNTAX     WtcsDisplayString (SIZE (0..64))
    MAX-ACCESS read-only
    STATUS     current
    DESCRIPTION
        "The Caption property is a short textual
        description (one- line string) of the object."
    ::= { msvmResourcePoolEntry 4 }

msvmrpDescription OBJECT-TYPE
    SYNTAX     WtcsDisplayString
    MAX-ACCESS read-only
    STATUS     current
    DESCRIPTION
        "The Description property provides a textual
        description of the object."
    ::= { msvmResourcePoolEntry 5 }

msvmrpElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmResourcePoolEntry 6 }

msvmrpHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmResourcePoolEntry 7 }

msvmrpInstallDate OBJECT-TYPE
    SYNTAX     DateAndTime
    MAX-ACCESS read-only
    STATUS     current
    DESCRIPTION
        "A datetime value that indicates when the object
        was installed. Lack of a value does not indicate
        that the object is not installed."
    ::= { msvmResourcePoolEntry 8 }

msvmrpInstanceID OBJECT-TYPE
    SYNTAX     WtcsDisplayString
    MAX-ACCESS read-only
    STATUS     current
    DESCRIPTION
        "Within the scope of the instantiating Namespace,
        InstanceID opaquely and uniquely identifies an
        instance of this class. To ensure uniqueness within
        the NameSpace, the value of InstanceID should be
        constructed using the following 'preferred'
        algorithm: 
        <OrgID>:<LocalID> 
        Where <OrgID> and <LocalID> are separated by a
        colon (:), and where <OrgID> must include a
        copyrighted, trademarked, or otherwise unique name
        that is owned by the business entity that is
        creating or defining the InstanceID or that is a
        registered ID assigned to the business entity by a
        recognized global authority. (This requirement is
        similar to the <Schema Name>_<Class Name> structure
        of Schema class names.) In addition, to ensure
        uniqueness, <OrgID> must not contain a colon (:).
        When using this algorithm, the first colon to
        appear in InstanceID must appear between <OrgID>
        and <LocalID>. 
        <LocalID> is chosen by the business entity and
        should not be reused to identify different
        underlying (real-world) elements. If the above
        'preferred' algorithm is not used, the defining
        entity must assure that the resulting InstanceID is
        not reused across any InstanceIDs produced by this
        or other providers for the NameSpace of this
        instance. 
        For DMTF-defined instances, the 'preferred'
        algorithm must be used with the <OrgID> set to
        CIM."
    ::= { msvmResourcePoolEntry 9 }

msvmrpName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmResourcePoolEntry 10 }

msvmrpOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmResourcePoolEntry 11 }

msvmrpOtherResourceType OBJECT-TYPE
    SYNTAX     WtcsDisplayString
    MAX-ACCESS read-only
    STATUS     current
    DESCRIPTION
        "A string that describes the resource type when a
        well defined value is not available and
        ResourceType is set to 0 for Other."
    ::= { msvmResourcePoolEntry 12 }

msvmrpPoolID OBJECT-TYPE
    SYNTAX     WtcsDisplayString
    MAX-ACCESS read-only
    STATUS     current
    DESCRIPTION
        "An opaque identifier for the pool.  This property
        is used to provide correlation across save and
        restore of configuration data to underlying
        persistent storage."
    ::= { msvmResourcePoolEntry 13 }

msvmrpPrimordial OBJECT-TYPE
    SYNTAX     TruthValue
    MAX-ACCESS read-only
    STATUS     current
    DESCRIPTION
        "If true, 'Primordial' indicates that this
        ResourcePool is the base from which resources are
        drawn and returned in the activity of resource
        management. Being primordial means that this
        ResourcePool shall not be created or deleted by
        consumers of this model. However, other actions,
        modeled or not, may affect the characteristics or
        size of primordial ResourcePools. If false,
        'Primordial' indicates that the ResourcePool, a
        concrete Resource Pool, is subject to resource
        allocation services functions. This distinction is
        important because higher-level ResourcePools may be
        assembled using the Component or
        ElementAllocatedFromPool associations. Although the
        higher-level abstractions can be created and
        deleted, the most basic, (i.e. primordial),
        hardware-based ResourcePools cannot. They are
        physically realized as part of the System, or are
        actually managed by some other System and imported
        as if they were physically realized."
    ::= { msvmResourcePoolEntry 14 }

msvmrpReserved OBJECT-TYPE
    SYNTAX     Gauge32
    MAX-ACCESS read-only
    STATUS     current
    DESCRIPTION
        "This property represents the current reservations
        (in units of AllocationUnits) spread across all
        active allocations from this pool.  In a
        hierarchical configuration, this represents the sum
        of all descendant ResourcePool current
        reservations."
    ::= { msvmResourcePoolEntry 15 }

msvmrpResourceSubType OBJECT-TYPE
    SYNTAX     WtcsDisplayString
    MAX-ACCESS read-only
    STATUS     current
    DESCRIPTION
        "A string describing an implementation specific
        sub-type for this pool.  For example, this may be
        used to distinguish different models of the same
        resource type."
    ::= { msvmResourcePoolEntry 16 }

msvmrpResourceType OBJECT-TYPE
    SYNTAX     INTEGER {
        other(1),
        computerSystem(2),
        processor(3),
        memory(4),
        ideController(5),
        parallelSCSIHBA(6),
        fcHBA(7),
        iSCSIHBA(8),
        ibHCA(9),
        ethernetAdapter(10),
        iOSlot(11),
        iODevice(12),
        floppyDrive(13),
        cdDrive(14),
        dvddrive(15),
        serialport(16),
        parallelport(17),
        usbController(18),
        graphicscontroller(19),
        storageExtent(20),
        disk(21),
        tape(22),
        otherstoragedevice(23),
        firewireController(24),
        partitionableUnit(25),
        basePartitionableUnit(26),
        powerSupply(27),
        coolingDevice(28),
        dmtfreserved(29)
    }
    MAX-ACCESS read-only
    STATUS     current
    DESCRIPTION
        "The type of resource this ResourcePool may
        allocate."
    ::= { msvmResourcePoolEntry 17 }

msvmrpStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmResourcePoolEntry 18 }

msvmrpStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmResourcePoolEntry 19 }

msvmDefineCapabilitiesTable OBJECT-TYPE
    SYNTAX     SEQUENCE OF MsvmSettingsDefineCapabilities
    MAX-ACCESS not-accessible
    STATUS     current
    DESCRIPTION
        "Provides a link between the
        CIM_AllocationCapabilities instance and the
        minimum, maximum, incremental, and default settings
        for a resource."
    ::= { msvmResourceManagement 7 }

msvmDefineCapabilitiesEntry OBJECT-TYPE
    SYNTAX     MsvmSettingsDefineCapabilities
    MAX-ACCESS not-accessible
    STATUS     current
    DESCRIPTION
        "None"
    INDEX      { msvmsdcIndex }
    ::= { msvmDefineCapabilitiesTable 1 }

MsvmSettingsDefineCapabilities ::= SEQUENCE {
    msvmsdcIndex Integer32,
    msvmsdcGroupComponent WtcsDisplayString,
    msvmsdcPartComponent WtcsDisplayString,
    msvmsdcPropertyPolicy INTEGER,
    msvmsdcValueRange INTEGER,
    msvmsdcValueRole INTEGER
}

msvmsdcIndex OBJECT-TYPE
    SYNTAX     Integer32 (1..2147483647)
    MAX-ACCESS read-only
    STATUS     current
    DESCRIPTION
        "The value of this object uniquely identifies the
        instance entry for this class."
    ::= { msvmDefineCapabilitiesEntry 1 }

msvmsdcGroupComponent OBJECT-TYPE
    SYNTAX     WtcsDisplayString
    MAX-ACCESS read-only
    STATUS     current
    DESCRIPTION
        "The parent element in the association."
    ::= { msvmDefineCapabilitiesEntry 2 }

msvmsdcPartComponent OBJECT-TYPE
    SYNTAX     WtcsDisplayString
    MAX-ACCESS read-only
    STATUS     current
    DESCRIPTION
        "The child element in the association."
    ::= { msvmDefineCapabilitiesEntry 3 }

msvmsdcPropertyPolicy OBJECT-TYPE
    SYNTAX     INTEGER {
        independent(0),
        correlated(1)
    }
    MAX-ACCESS read-only
    STATUS     current
    DESCRIPTION
        "PropertyPolicy defines whether or not the
        non-null, non-key properties of the associated
        SettingData instance are treated independently or
        as a correlated set. For instance, an independent
        set of maximum properties might be defined, when
        there is no relationship between each property. On
        the other hand, several correlated sets of maximum
        properties might need to be defined when the
        maximum values of each are dependent on some of the
        others."
    ::= { msvmDefineCapabilitiesEntry 4 }

msvmsdcValueRange OBJECT-TYPE
    SYNTAX     INTEGER {
        point(0),
        minimums(1),
        maximums(2),
        increments(3)
    }
    MAX-ACCESS read-only
    STATUS     current
    DESCRIPTION
        "The ValueRange property indicates further
        semantics on the interpretation of all non-null,
        non-key properties of the Component SettingData. 
        'Point' indicates that this SettingData instance
        provides a single set of values. 
        'Minimums', 'Maximums', and 'Increments', are only
        evaluated against non-null, non-key,
        non-enumerated, non-boolean, numeric properties of
        the SettingData instance. Each property of that set
        shall be mathematically comparable to other
        instances of that property. 
        'Minimums' indicates that this SettingData instance
        provides minimum values for evaluated properties.
        When used with PropertyPolicy = 'Independent', only
        one such setting per particular SettingData
        instance shall be specified for any Capabilities.
        Unless restricted by a Maximums on the same set of
        properties, all values that compare higher than the
        specified values are also considered to be
        supported by the associated capabilities instance. 
        'Maximums' indicates that this SettingData instance
        provides maximum values for evaluated properties.
        When used with PropertyPolicy = 'Independent', only
        one such setting per particular SettingData
        instance shall be specified for any Capabilities.
        Unless restricted by a Minimums on the same set of
        properties, all values that compare lower than the
        specified values are also considered to be
        supported by the associated capabilities instance. 
        'Increments' indicates that this SettingData
        instance provides increment values for evaluated
        properties. For the associated Capabilities, if an
        evaluated property currently has no corresponding
        minimums or maximums, then the property has no
        affect. Otherwise, for each evaluated property: its
        value x shall be between the minimum and maximum,
        inclusively, and shall have the property that both
        the result of maximum minus x and the result of x
        minus minimum are each an integer multiple of the
        increment. If either minimum or maximum is not
        specified and the other is, then the missing value
        shall be respectively assumed to be the lowest or
        highest supported value for the property's
        data-type. Additionally, if both a minimum and a
        maximum are specified for an evaluated property,
        then the result of maximum minus minimum shall be
        an integer multiple of the increment."
    ::= { msvmDefineCapabilitiesEntry 5 }

msvmsdcValueRole OBJECT-TYPE
    SYNTAX     INTEGER {
        default(0),
        optimal(1),
        mean(2),
        supported(3)
    }
    MAX-ACCESS read-only
    STATUS     current
    DESCRIPTION
        "The ValueRole property indicates further semantics
        on the interpretation of the non-null, non-key
        properties of the Component SettingData. 
        'Default' indicates that property values of the
        component SettingData instance will be used as
        default values, when a new SettingData instance is
        created for elements whose capabilities are defined
        by the associated Capabilities instance. 
        Across instances of settingdata, for particular
        properties having the same semantic purpose, at
        most one such settingdata instance shall be
        specified as a default. 
        'Optimal' indicates that the SettingData instance
        represents optimal setting values for elements
        associated with the associated capabilities
        instance. Multiple component SettingData instances
        may be declared as optimal. 'Mean' indicates that
        the non-null, non-key, non-enumerated, non-boolean,
        numeric properties of the associated SettingData
        instance represents an average point along some
        dimension. For different combinations of
        SettingData properties, multiple component
        SettingData instances may be declared as 'Mean'. 
        'Supported' indicates that the non-null, non-key
        properties of the Component SettingData instance
        represents a set of supported property values that
        are not otherwise qualified."
    ::= { msvmDefineCapabilitiesEntry 6 }

msvmSerialDevices OBJECT-IDENTITY
    STATUS     current
    DESCRIPTION
        "The serial devices in a virtual machine consist of
        serial controllers and serial ports. Each virtual
        system has exactly one serial controller, and each
        serial controller has exactly two serial ports.
        
        The settings for the serial controller are not
        configurable; therefore, there is no setting data
        instance associated with it. Also, you cannot add
        or remove serial controllers or serial ports from a
        virtual system. Therefore, there are no resource
        pool instances for serial devices."
    ::= { informantHyperV 9 }

msvmSerialControllerTable OBJECT-TYPE
    SYNTAX     SEQUENCE OF MsvmSerialController
    MAX-ACCESS not-accessible
    STATUS     current
    DESCRIPTION
        "Represents the capabilities and management of the
        serial controller."
    ::= { msvmSerialDevices 1 }

msvmSerialControllerEntry OBJECT-TYPE
    SYNTAX     MsvmSerialController
    MAX-ACCESS not-accessible
    STATUS     current
    DESCRIPTION
        "None"
    INDEX      { msvmscIndex }
    ::= { msvmSerialControllerTable 1 }

MsvmSerialController ::= SEQUENCE {
    msvmsdIndex Integer32,
    msvmsdAdditionalAvailability INTEGER,
    msvmsdAvailability INTEGER,
    msvmsdCapabilities Integer32,
    msvmsdCapabilityDescriptions WtcsDisplayString,
    msvmsdCaption WtcsDisplayString,
    msvmsdCreationClassName WtcsDisplayString,
    msvmsdDescription WtcsDisplayString,
    msvmsdDeviceID WtcsDisplayString,
    msvmsdElementName WtcsDisplayString,
    msvmsdEnabledDefault INTEGER,
    msvmsdEnabledState INTEGER,
    msvmsdErrorCleared TruthValue,
    msvmsdErrorDescription WtcsDisplayString,
    msvmsdHealthState INTEGER,
    msvmsdIdentifyingDescriptions WtcsDisplayString,
    msvmsdInstallDate DateAndTime,
    msvmsdLastErrorCode Gauge32,
    msvmsdLocationIndicator INTEGER,
    msvmsdMaxBaudRate Gauge32,
    msvmsdMaxNumberControlled Gauge32,
    msvmsdMaxQuiesceTime Gauge32,
    msvmsdName WtcsDisplayString,
    msvmsdOperationalStatus INTEGER,
    msvmsdOtherEnabledState WtcsDisplayString,
    msvmsdOtherIdentifyingInfo WtcsDisplayString,
    msvmsdPowerManagementCapability INTEGER,
    msvmsdPowerManagementSupported TruthValue,
    msvmsdPowerOnHours Gauge32,
    msvmsdProtocolDescription WtcsDisplayString,
    msvmsdProtocolSupported Integer32,
    msvmsdRequestedState INTEGER,
    msvmsdSecurity INTEGER,
    msvmsdStatus WtcsDisplayString,
    msvmsdStatusDescriptions WtcsDisplayString,
    msvmsdStatusInfo INTEGER,
    msvmsdSystemCreationClassName WtcsDisplayString,
    msvmsdSystemName WtcsDisplayString,
    msvmsdTimeOfLastReset DateAndTime,
    msvmsdTimeOfLastStateChange DateAndTime,
    msvmsdTotalPowerOnHours Gauge32
}

msvmsdIndex OBJECT-TYPE
    SYNTAX     Integer32 (1..2147483647)
    MAX-ACCESS read-only
    STATUS     current
    DESCRIPTION
        "The value of this object uniquely identifies the
        instance entry for this class."
    ::= { msvmSerialControllerEntry 1 }

msvmsdAdditionalAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Additional availability and status of the Device
        in addition to that specified in the Availability
        property. The Availability property denotes the
        primary status and availability of the Device. In
        some cases, this property will not be sufficient to
        denote the complete status of the Device. In those
        cases, the AdditionalAvailability property can be
        used to provide further information. For example,
        the primary Availability of a device might be 'Off
        line' (value=8) or in a low-power state
        (AdditionalAvailability value=14), or the Device
        could be running Diagnostics
        (AdditionalAvailability value=5, 'In Test')."
    ::= { msvmSerialControllerEntry 2 }

msvmsdAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Note: The use of this property has been
        deprecated. 
        Deprecated description: The primary availability
        and status of the Device. (Additional status
        information can be specified using the Additional
        Availability array property.) For example, the
        Availability property indicates that the Device is
        running and has full power (value=3), or is in a
        warning (4), test (5), degraded (10) or power save
        state (values 13-15 and 17). The Power Save states
        are defined as follows: Value 13 ('Power Save -
        Unknown') indicates that the Device is known to be
        in a power save mode, but its exact status in this
        mode is unknown; value 14 ('Power Save - Low Power
        Mode') indicates that the Device is in a power save
        state but still functioning, and might exhibit
        degraded performance; value 15 ('Power Save -
        Standby') indicates that the Device is not
        functioning but could be brought to full power
        'quickly'; and value 17 ('Power Save - Warning')
        indicates that the Device is in a warning state,
        but is also in a power save mode."
    ::= { msvmSerialControllerEntry 3 }

msvmsdCapabilities OBJECT-TYPE
    SYNTAX     Integer32
    MAX-ACCESS read-only
    STATUS     current
    DESCRIPTION
        "The Capabilities property defines chip level
        compatibility for the SerialController. Therefore,
        this property describes the buffering and other
        capabilities of the SerialController that might be
        inherent in the chip hardware. The property is an
        enumerated integer."
    ::= { msvmSerialControllerEntry 4 }

msvmsdCapabilityDescriptions OBJECT-TYPE
    SYNTAX     WtcsDisplayString
    MAX-ACCESS read-only
    STATUS     current
    DESCRIPTION
        "An array of free-form strings that provides more
        detailed explanations for any of the
        SerialController features that are indicated in the
        Capabilities array. Note, each entry of this array
        is related to the entry in the Capabilities array
        that is located at the same index."
    ::= { msvmSerialControllerEntry 5 }

msvmsdCaption OBJECT-TYPE
    SYNTAX     WtcsDisplayString (SIZE (0..64))
    MAX-ACCESS read-only
    STATUS     current
    DESCRIPTION
        "The Caption property is a short textual
        description (one- line string) of the object."
    ::= { msvmSerialControllerEntry 6 }

msvmsdCreationClassName OBJECT-TYPE
    SYNTAX     WtcsDisplayString (SIZE (0..256))
    MAX-ACCESS read-only
    STATUS     current
    DESCRIPTION
        "CreationClassName indicates the name of the class
        or the subclass used in the creation of an
        instance. When used with the other key properties
        of this class, this property allows all instances
        of this class and its subclasses to be uniquely
        identified."
    ::= { msvmSerialControllerEntry 7 }

msvmsdDescription OBJECT-TYPE
    SYNTAX     WtcsDisplayString
    MAX-ACCESS read-only
    STATUS     current
    DESCRIPTION
        "The Description property provides a textual
        description of the object."
    ::= { msvmSerialControllerEntry 8 }

msvmsdDeviceID OBJECT-TYPE
    SYNTAX     WtcsDisplayString (SIZE (0..64))
    MAX-ACCESS read-only
    STATUS     current
    DESCRIPTION
        "An address or other identifying information used
        to uniquely name the LogicalDevice."
    ::= { msvmSerialControllerEntry 9 }

msvmsdElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmSerialControllerEntry 10 }

msvmsdEnabledDefault OBJECT-TYPE
    SYNTAX     INTEGER {
        enabled(2),
        disabled(3),
        notApplicable(5),
        enabledbutOffline(6),
        noDefault(7)
    }
    MAX-ACCESS read-only
    STATUS     current
    DESCRIPTION
        "An enumerated value indicating an administrator's
        default or startup configuration for the Enabled
        State of an element. By default, the element is
        'Enabled' (value=2)."
    ::= { msvmSerialControllerEntry 11 }

msvmsdEnabledState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "EnabledState is an integer enumeration that
        indicates the enabled and disabled states of an
        element. It can also indicate the transitions
        between these requested states. For example,
        shutting down (value=4) and starting (value=10) are
        transient states between enabled and disabled. The
        following text briefly summarizes the various
        enabled and disabled states: 
        Enabled (2) indicates that the element is or could
        be executing commands, will process any queued
        commands, and queues new requests. 
        Disabled (3) indicates that the element will not
        execute commands and will drop any new requests. 
        Shutting Down (4) indicates that the element is in
        the process of going to a Disabled state. 
        Not Applicable (5) indicates the element does not
        support being enabled or disabled. 
        Enabled but Offline (6) indicates that the element
        might be completing commands, and will drop any new
        requests. 
        Test (7) indicates that the element is in a test
        state. 
        Deferred (8) indicates that the element might be
        completing commands, but will queue any new
        requests. 
        Quiesce (9) indicates that the element is enabled
        but in a restricted mode. The behavior of the
        element is similar to the Enabled state, but it
        processes only a restricted set of commands. All
        other requests are queued. 
        Starting (10) indicates that the element is in the
        process of going to an Enabled state. New requests
        are queued."
    ::= { msvmSerialControllerEntry 12 }

msvmsdErrorCleared OBJECT-TYPE
    SYNTAX     TruthValue
    MAX-ACCESS read-only
    STATUS     current
    DESCRIPTION
        "Note: The use of this method is deprecated. 
        Deprecated description: ErrorCleared is a Boolean
        property that indicates that the error reported in
        LastErrorCode is now cleared."
    ::= { msvmSerialControllerEntry 13 }

msvmsdErrorDescription OBJECT-TYPE
    SYNTAX     WtcsDisplayString
    MAX-ACCESS read-only
    STATUS     current
    DESCRIPTION
        "Note: The use of this method is deprecated. 
        Deprecated description: ErrorDescription is a
        free-form string that supplies more information
        about the error recorded in LastErrorCode and
        information on any corrective actions that can be
        taken."
    ::= { msvmSerialControllerEntry 14 }

msvmsdHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmSerialControllerEntry 15 }

msvmsdIdentifyingDescriptions OBJECT-TYPE
    SYNTAX     WtcsDisplayString
    MAX-ACCESS read-only
    STATUS     current
    DESCRIPTION
        "An array of free-form strings providing
        explanations and details behind the entries in the
        OtherIdentifyingInfo array. Note that each entry of
        this array is related to the entry in
        OtherIdentifyingInfo that is located at the same
        index."
    ::= { msvmSerialControllerEntry 16 }

msvmsdInstallDate OBJECT-TYPE
    SYNTAX     DateAndTime
    MAX-ACCESS read-only
    STATUS     current
    DESCRIPTION
        "A datetime value that indicates when the object
        was installed. Lack of a value does not indicate
        that the object is not installed."
    ::= { msvmSerialControllerEntry 17 }

msvmsdLastErrorCode OBJECT-TYPE
    SYNTAX     Gauge32
    MAX-ACCESS read-only
    STATUS     current
    DESCRIPTION
        "Note: The use of this method is deprecated. 
        Deprecated description: LastErrorCode captures the
        last error code reported by the LogicalDevice."
    ::= { msvmSerialControllerEntry 18 }

msvmsdLocationIndicator OBJECT-TYPE
    SYNTAX     INTEGER {
        unknown(0),
        on(2),
        off(3),
        notSupported(4)
    }
    MAX-ACCESS read-only
    STATUS     current
    DESCRIPTION
        "An integer that reflects the state of an indicator
        (e.g., LED) that is part of a device. Reading the
        value gives the current state. Writing the value
        with 'On'/'Off' turns the indicator on/off, other
        values may not be written."
    ::= { msvmSerialControllerEntry 19 }

msvmsdMaxBaudRate OBJECT-TYPE
    SYNTAX     Gauge32
    UNITS "Bits per Second"
    MAX-ACCESS read-only
    STATUS     current
    DESCRIPTION
        "Maximum baud rate in Bits per Second that is
        supported by the SerialController."
    ::= { msvmSerialControllerEntry 20 }

msvmsdMaxNumberControlled OBJECT-TYPE
    SYNTAX     Gauge32
    MAX-ACCESS read-only
    STATUS     current
    DESCRIPTION
        "Maximum number of directly addressable entities
        that are supported by this Controller. A value of 0
        should be used if the number is unknown or
        unlimited."
    ::= { msvmSerialControllerEntry 21 }

msvmsdMaxQuiesceTime OBJECT-TYPE
    SYNTAX     Gauge32
    UNITS "MilliSeconds"
    MAX-ACCESS read-only
    STATUS     current
    DESCRIPTION
        "Note: The use of this property has been
        deprecated. When evaluating the use of Quiesce, it
        was determined that this single property is not
        adequate for describing when a device will
        automatically exit a quiescent state. In fact, the
        most likely scenario for a device to exit a
        quiescent state was determined to be based on the
        number of outstanding requests queued rather than
        on a maximum time. This decision will be
        re-evaluated and repositioned later. 
        Deprecated description: Maximum time, in
        milliseconds, that a Device can run in a 'Quiesced'
        state. The state is defined in its Availability and
        AdditionalAvailability properties, where 'Quiesced'
        is conveyed by the value 21. What occurs at the end
        of the time limit is device-specific. The Device
        can unquiesce, can be offline, or can take other
        actions. A value of 0 indicates that a Device can
        remain quiesced indefinitely."
    ::= { msvmSerialControllerEntry 22 }

msvmsdName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmSerialControllerEntry 23 }

msvmsdOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmSerialControllerEntry 24 }

msvmsdOtherEnabledState OBJECT-TYPE
    SYNTAX     WtcsDisplayString
    MAX-ACCESS read-only
    STATUS     current
    DESCRIPTION
        "A string that describes the enabled or disabled
        state of the element when the EnabledState property
        is set to 1 ('Other'). This property must be set to
        null when EnabledState is any value other than 1."
    ::= { msvmSerialControllerEntry 25 }

msvmsdOtherIdentifyingInfo OBJECT-TYPE
    SYNTAX     WtcsDisplayString (SIZE (0..256))
    MAX-ACCESS read-only
    STATUS     current
    DESCRIPTION
        "OtherIdentifyingInfo captures data, in addition to
        DeviceID information, that could be used to
        identify a LogicalDevice. For example, you could
        use this property to hold the operating system's
        user-friendly name for the Device."
    ::= { msvmSerialControllerEntry 26 }

msvmsdPowerManagementCapability OBJECT-TYPE
    SYNTAX     INTEGER {
        unknown(0),
        notSupported(1),
        disabled(2),
        enabled(3),
        powerSavingModesEnteredAutomatic(4),
        powerStateSettable(5),
        powerCyclingSupported(6),
        timedPowerOnSupported(7)
    }
    MAX-ACCESS read-only
    STATUS     current
    DESCRIPTION
        "Note: The use of this property has been
        deprecated. Instead, use the PowerCapabilites
        property in an associated
        PowerManagementCapabilities class. Deprecated
        description: An enumerated array describing the
        power management capabilities of the Device."
    ::= { msvmSerialControllerEntry 27 }

msvmsdPowerManagementSupported OBJECT-TYPE
    SYNTAX     TruthValue
    MAX-ACCESS read-only
    STATUS     current
    DESCRIPTION
        "Note: The use of this property has been
        deprecated. Instead, the existence of an associated
        PowerManagementCapabilities class (associated using
        the ElementCapabilities relationship) indicates
        that power management is supported. Deprecated
        description: Boolean that indicates that the Device
        can use power management."
    ::= { msvmSerialControllerEntry 28 }

msvmsdPowerOnHours OBJECT-TYPE
    SYNTAX     Gauge32
    UNITS "Hours"
    MAX-ACCESS read-only
    STATUS     current
    DESCRIPTION
        "Note: The use of this method is deprecated. 
        Deprecated description: The number of consecutive
        hours that this Device has been powered on since
        its last power cycle."
    ::= { msvmSerialControllerEntry 29 }

msvmsdProtocolDescription OBJECT-TYPE
    SYNTAX     WtcsDisplayString
    MAX-ACCESS read-only
    STATUS     current
    DESCRIPTION
        "A free-form string that provides more information
        that is related to the ProtocolSupported by the
        Controller."
    ::= { msvmSerialControllerEntry 30 }

msvmsdProtocolSupported OBJECT-TYPE
    SYNTAX     Integer32
    MAX-ACCESS read-only
    STATUS     current
    DESCRIPTION
        "The protocol used by the Controller to access
        controlled Devices."
    ::= { msvmSerialControllerEntry 31 }

msvmsdRequestedState OBJECT-TYPE
    SYNTAX     INTEGER {
        enabled(2),
        disabled(3),
        shutDown(4),
        noChange(5),
        offline(6),
        test(7),
        deferred(8),
        quiesce(9),
        reboot(10),
        reset(11),
        notApplicable(12)
    }
    MAX-ACCESS read-only
    STATUS     current
    DESCRIPTION
        "RequestedState is an integer enumeration that
        indicates the last requested or desired state for
        the element. The actual state of the element is
        represented by EnabledState. This property is
        provided to compare the last requested and current
        enabled or disabled states. Note that when
        EnabledState is set to 5 ('Not Applicable'), then
        this property has no meaning. By default, the
        RequestedState of the element is 5 ('No Change').
        Refer to the EnabledState property description for
        explanations of the values in the RequestedState
        enumeration. 
        
        It should be noted that there are two new values in
        RequestedState that build on the statuses of
        EnabledState. These are 'Reboot' (10) and 'Reset'
        (11). Reboot refers to doing a 'Shut Down' and then
        moving to an 'Enabled' state. Reset indicates that
        the element is first 'Disabled' and then 'Enabled'.
        The distinction between requesting 'Shut Down' and
        'Disabled' should also be noted. Shut Down requests
        an orderly transition to the Disabled state, and
        might involve removing power, to completely erase
        any existing state. The Disabled state requests an
        immediate disabling of the element, such that it
        will not execute or accept any commands or
        processing requests. 
        
        This property is set as the result of a method
        invocation (such as Start or StopService on
        CIM_Service), or can be overridden and defined as
        WRITEable in a subclass. The method approach is
        considered superior to a WRITEable property,
        because it allows an explicit invocation of the
        operation and the return of a result code. 
        
        A particular instance of EnabledLogicalElement
        might not support RequestedStateChange. If this
        occurs, the value 12 ('Not Applicable') is used."
    ::= { msvmSerialControllerEntry 32 }

msvmsdSecurity OBJECT-TYPE
    SYNTAX     INTEGER {
        other(1),
        unknown(2),
        none(3),
        externalInterfaceLockedOut(4),
        externalInterfaceEnabled(5),
        bootBypass(6)
    }
    MAX-ACCESS read-only
    STATUS     current
    DESCRIPTION
        "An enumeration that indicates the operational
        security for the Controller. For example,
        information that the external interface of the
        Device is locked out (value=4) or 'Boot Bypass'
        (value=6) can be described using this property."
    ::= { msvmSerialControllerEntry 33 }

msvmsdStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmSerialControllerEntry 34 }

msvmsdStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmSerialControllerEntry 35 }

msvmsdStatusInfo OBJECT-TYPE
    SYNTAX     INTEGER {
        other(1),
        unknown(2),
        enabled(3),
        disabled(4),
        notApplicable(5)
    }
    MAX-ACCESS read-only
    STATUS     current
    DESCRIPTION
        "Note: The use of this method is deprecated in lieu
        of a more clearly named property (EnabledState)
        that is inherited from ManagedSystemElement and
        that has additional enumerated values. 
        Deprecated description: The StatusInfo property
        indicates whether the Logical Device is in an
        enabled state (value=3), disabled state (value=4),
        some other state (value=1), or an unknown state
        (value=2). If this property does not apply to the
        LogicalDevice, the value 5 ('Not Applicable')
        should be used. If a Device is
        ('Enabled')(value=3), it has been powered up and is
        configured and operational. The Device might or
        might not be functionally active, depending on
        whether its Availability (or
        AdditionalAvailability) indicates that it is
        ('Running/Full Power')(value=3) or ('Off line')
        (value=8). In an enabled but offline mode, a Device
        might be performing out-of-band requests, such as
        running Diagnostics. If StatusInfo is ('Disabled')
        (value=4), a Device can only be 'enabled' or
        powered off. In a personal computer environment,
        ('Disabled') means that the driver of the device is
        not available in the stack. In other environments,
        a Device can be disabled by removing its
        configuration file. A disabled device is physically
        present in a System and consuming resources, but it
        cannot be communicated with until a driver is
        loaded, a configuration file is loaded, or some
        other 'enabling' activity has occurred."
    ::= { msvmSerialControllerEntry 36 }

msvmsdSystemCreationClassName OBJECT-TYPE
    SYNTAX     WtcsDisplayString (SIZE (0..256))
    MAX-ACCESS read-only
    STATUS     current
    DESCRIPTION
        "The CreationClassName of the scoping system."
    ::= { msvmSerialControllerEntry 37 }

msvmsdSystemName OBJECT-TYPE
    SYNTAX     WtcsDisplayString (SIZE (0..256))
    MAX-ACCESS read-only
    STATUS     current
    DESCRIPTION
        "The System Name of the scoping system."
    ::= { msvmSerialControllerEntry 38 }

msvmsdTimeOfLastReset OBJECT-TYPE
    SYNTAX     DateAndTime
    MAX-ACCESS read-only
    STATUS     current
    DESCRIPTION
        "Time of last reset of the Controller."
    ::= { msvmSerialControllerEntry 39 }

msvmsdTimeOfLastStateChange OBJECT-TYPE
    SYNTAX     DateAndTime
    MAX-ACCESS read-only
    STATUS     current
    DESCRIPTION
        "The date or time when the EnabledState of the
        element last changed. If the state of the element
        has not changed and this property is populated,
        then it must be set to a 0 interval value. If a
        state change was requested, but rejected or not yet
        processed, the property must not be updated."
    ::= { msvmSerialControllerEntry 40 }

msvmsdTotalPowerOnHours OBJECT-TYPE
    SYNTAX     Gauge32
    UNITS "Hours"
    MAX-ACCESS read-only
    STATUS     current
    DESCRIPTION
        "Note: The use of this method is deprecated. 
        Deprecated description: The total number of hours
        that this Device has been powered on."
    ::= { msvmSerialControllerEntry 41 }

msvmSerialPortTable OBJECT-TYPE
    SYNTAX     SEQUENCE OF MsvmSerialPort
    MAX-ACCESS not-accessible
    STATUS     current
    DESCRIPTION
        "Represents a serial port associated with the
        serial controller."
    ::= { msvmSerialDevices 2 }

msvmSerialPortEntry OBJECT-TYPE
    SYNTAX     MsvmSerialPort
    MAX-ACCESS not-accessible
    STATUS     current
    DESCRIPTION
        "None"
    INDEX      { msvmspIndex }
    ::= { msvmSerialPortTable 1 }

MsvmSerialPort ::= SEQUENCE {
    msvmspeIndex Integer32,
    msvmspeAdditionalAvailability INTEGER,
    msvmspeAvailability INTEGER,
    msvmspeCaption WtcsDisplayString,
    msvmspeCreationClassName WtcsDisplayString,
    msvmspeDescription WtcsDisplayString,
    msvmspeDeviceID WtcsDisplayString,
    msvmspeElementName WtcsDisplayString,
    msvmspeEnabledDefault INTEGER,
    msvmspeEnabledState INTEGER,
    msvmspeErrorCleared TruthValue,
    msvmspeErrorDescription WtcsDisplayString,
    msvmspeHealthState INTEGER,
    msvmspeIdentifyingDescriptions WtcsDisplayString,
    msvmspeInstallDate DateAndTime,
    msvmspeLastErrorCode Gauge32,
    msvmspeLocationIndicator INTEGER,
    msvmspeMaxQuiesceTime Gauge32,
    msvmspeMaxSpeed Gauge32,
    msvmspeName WtcsDisplayString,
    msvmspeOperationalStatus INTEGER,
    msvmspeOtherEnabledState WtcsDisplayString,
    msvmspeOtherIdentifyingInfo WtcsDisplayString,
    msvmspeOtherPortType WtcsDisplayString,
    msvmspePortType INTEGER,
    msvmspePowerManagementCapability INTEGER,
    msvmspePowerManagementSupported TruthValue,
    msvmspePowerOnHours Gauge32,
    msvmspeRequestedSpeed Gauge32,
    msvmspeRequestedState INTEGER,
    msvmspeSpeed Gauge32,
    msvmspeStatus WtcsDisplayString,
    msvmspeStatusDescriptions WtcsDisplayString,
    msvmspeStatusInfo INTEGER,
    msvmspeSystemCreationClassName WtcsDisplayString,
    msvmspeSystemName WtcsDisplayString,
    msvmspeTimeOfLastStateChange DateAndTime,
    msvmspeTotalPowerOnHours Gauge32,
    msvmspeUsageRestriction INTEGER
}

msvmspeIndex OBJECT-TYPE
    SYNTAX     Integer32 (1..2147483647)
    MAX-ACCESS read-only
    STATUS     current
    DESCRIPTION
        "The value of this object uniquely identifies the
        instance entry for this class."
    ::= { msvmSerialPortEntry 1 }

msvmspeAdditionalAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Additional availability and status of the Device
        in addition to that specified in the Availability
        property. The Availability property denotes the
        primary status and availability of the Device. In
        some cases, this property will not be sufficient to
        denote the complete status of the Device. In those
        cases, the AdditionalAvailability property can be
        used to provide further information. For example,
        the primary Availability of a device might be 'Off
        line' (value=8) or in a low-power state
        (AdditionalAvailability value=14), or the Device
        could be running Diagnostics
        (AdditionalAvailability value=5, 'In Test')."
    ::= { msvmSerialPortEntry 2 }

msvmspeAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Note: The use of this property has been
        deprecated. 
        Deprecated description: The primary availability
        and status of the Device. (Additional status
        information can be specified using the Additional
        Availability array property.) For example, the
        Availability property indicates that the Device is
        running and has full power (value=3), or is in a
        warning (4), test (5), degraded (10) or power save
        state (values 13-15 and 17). The Power Save states
        are defined as follows: Value 13 ('Power Save -
        Unknown') indicates that the Device is known to be
        in a power save mode, but its exact status in this
        mode is unknown; value 14 ('Power Save - Low Power
        Mode') indicates that the Device is in a power save
        state but still functioning, and might exhibit
        degraded performance; value 15 ('Power Save -
        Standby') indicates that the Device is not
        functioning but could be brought to full power
        'quickly'; and value 17 ('Power Save - Warning')
        indicates that the Device is in a warning state,
        but is also in a power save mode."
    ::= { msvmSerialPortEntry 3 }

msvmspeCaption OBJECT-TYPE
    SYNTAX     WtcsDisplayString (SIZE (0..64))
    MAX-ACCESS read-only
    STATUS     current
    DESCRIPTION
        "The Caption property is a short textual
        description (one- line string) of the object."
    ::= { msvmSerialPortEntry 4 }

msvmspeCreationClassName OBJECT-TYPE
    SYNTAX     WtcsDisplayString (SIZE (0..256))
    MAX-ACCESS read-only
    STATUS     current
    DESCRIPTION
        "CreationClassName indicates the name of the class
        or the subclass used in the creation of an
        instance. When used with the other key properties
        of this class, this property allows all instances
        of this class and its subclasses to be uniquely
        identified."
    ::= { msvmSerialPortEntry 5 }

msvmspeDescription OBJECT-TYPE
    SYNTAX     WtcsDisplayString
    MAX-ACCESS read-only
    STATUS     current
    DESCRIPTION
        "The Description property provides a textual
        description of the object."
    ::= { msvmSerialPortEntry 6 }

msvmspeDeviceID OBJECT-TYPE
    SYNTAX     WtcsDisplayString (SIZE (0..64))
    MAX-ACCESS read-only
    STATUS     current
    DESCRIPTION
        "An address or other identifying information used
        to uniquely name the LogicalDevice."
    ::= { msvmSerialPortEntry 7 }

msvmspeElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmSerialPortEntry 8 }

msvmspeEnabledDefault OBJECT-TYPE
    SYNTAX     INTEGER {
        enabled(2),
        disabled(3),
        notApplicable(5),
        enabledbutOffline(6),
        noDefault(7)
    }
    MAX-ACCESS read-only
    STATUS     current
    DESCRIPTION
        "An enumerated value indicating an administrator's
        default or startup configuration for the Enabled
        State of an element. By default, the element is
        'Enabled' (value=2)."
    ::= { msvmSerialPortEntry 9 }

msvmspeEnabledState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "EnabledState is an integer enumeration that
        indicates the enabled and disabled states of an
        element. It can also indicate the transitions
        between these requested states. For example,
        shutting down (value=4) and starting (value=10) are
        transient states between enabled and disabled. The
        following text briefly summarizes the various
        enabled and disabled states: 
        Enabled (2) indicates that the element is or could
        be executing commands, will process any queued
        commands, and queues new requests. 
        Disabled (3) indicates that the element will not
        execute commands and will drop any new requests. 
        Shutting Down (4) indicates that the element is in
        the process of going to a Disabled state. 
        Not Applicable (5) indicates the element does not
        support being enabled or disabled. 
        Enabled but Offline (6) indicates that the element
        might be completing commands, and will drop any new
        requests. 
        Test (7) indicates that the element is in a test
        state. 
        Deferred (8) indicates that the element might be
        completing commands, but will queue any new
        requests. 
        Quiesce (9) indicates that the element is enabled
        but in a restricted mode. The behavior of the
        element is similar to the Enabled state, but it
        processes only a restricted set of commands. All
        other requests are queued. 
        Starting (10) indicates that the element is in the
        process of going to an Enabled state. New requests
        are queued."
    ::= { msvmSerialPortEntry 10 }

msvmspeErrorCleared OBJECT-TYPE
    SYNTAX     TruthValue
    MAX-ACCESS read-only
    STATUS     current
    DESCRIPTION
        "Note: The use of this method is deprecated. 
        Deprecated description: ErrorCleared is a Boolean
        property that indicates that the error reported in
        LastErrorCode is now cleared."
    ::= { msvmSerialPortEntry 11 }

msvmspeErrorDescription OBJECT-TYPE
    SYNTAX     WtcsDisplayString
    MAX-ACCESS read-only
    STATUS     current
    DESCRIPTION
        "Note: The use of this method is deprecated. 
        Deprecated description: ErrorDescription is a
        free-form string that supplies more information
        about the error recorded in LastErrorCode and
        information on any corrective actions that can be
        taken."
    ::= { msvmSerialPortEntry 12 }

msvmspeHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmSerialPortEntry 13 }

msvmspeIdentifyingDescriptions OBJECT-TYPE
    SYNTAX     WtcsDisplayString
    MAX-ACCESS read-only
    STATUS     current
    DESCRIPTION
        "An array of free-form strings providing
        explanations and details behind the entries in the
        OtherIdentifyingInfo array. Note that each entry of
        this array is related to the entry in
        OtherIdentifyingInfo that is located at the same
        index."
    ::= { msvmSerialPortEntry 14 }

msvmspeInstallDate OBJECT-TYPE
    SYNTAX     DateAndTime
    MAX-ACCESS read-only
    STATUS     current
    DESCRIPTION
        "A datetime value that indicates when the object
        was installed. Lack of a value does not indicate
        that the object is not installed."
    ::= { msvmSerialPortEntry 15 }

msvmspeLastErrorCode OBJECT-TYPE
    SYNTAX     Gauge32
    MAX-ACCESS read-only
    STATUS     current
    DESCRIPTION
        "Note: The use of this method is deprecated. 
        Deprecated description: LastErrorCode captures the
        last error code reported by the LogicalDevice."
    ::= { msvmSerialPortEntry 16 }

msvmspeLocationIndicator OBJECT-TYPE
    SYNTAX     INTEGER {
        unknown(0),
        on(2),
        off(3),
        notSupported(4)
    }
    MAX-ACCESS read-only
    STATUS     current
    DESCRIPTION
        "An integer that reflects the state of an indicator
        (e.g., LED) that is part of a device. Reading the
        value gives the current state. Writing the value
        with 'On'/'Off' turns the indicator on/off, other
        values may not be written."
    ::= { msvmSerialPortEntry 17 }

msvmspeMaxQuiesceTime OBJECT-TYPE
    SYNTAX     Gauge32
    UNITS "MilliSeconds"
    MAX-ACCESS read-only
    STATUS     current
    DESCRIPTION
        "Note: The use of this property has been
        deprecated. When evaluating the use of Quiesce, it
        was determined that this single property is not
        adequate for describing when a device will
        automatically exit a quiescent state. In fact, the
        most likely scenario for a device to exit a
        quiescent state was determined to be based on the
        number of outstanding requests queued rather than
        on a maximum time. This decision will be
        re-evaluated and repositioned later. 
        Deprecated description: Maximum time, in
        milliseconds, that a Device can run in a 'Quiesced'
        state. The state is defined in its Availability and
        AdditionalAvailability properties, where 'Quiesced'
        is conveyed by the value 21. What occurs at the end
        of the time limit is device-specific. The Device
        can unquiesce, can be offline, or can take other
        actions. A value of 0 indicates that a Device can
        remain quiesced indefinitely."
    ::= { msvmSerialPortEntry 18 }

msvmspeMaxSpeed OBJECT-TYPE
    SYNTAX     Gauge32
    UNITS "Bits per Second"
    MAX-ACCESS read-only
    STATUS     current
    DESCRIPTION
        "The maximum bandwidth of the Port in Bits per
        Second."
    ::= { msvmSerialPortEntry 19 }

msvmspeName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmSerialPortEntry 20 }

msvmspeOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmSerialPortEntry 21 }

msvmspeOtherEnabledState OBJECT-TYPE
    SYNTAX     WtcsDisplayString
    MAX-ACCESS read-only
    STATUS     current
    DESCRIPTION
        "A string that describes the enabled or disabled
        state of the element when the EnabledState property
        is set to 1 ('Other'). This property must be set to
        null when EnabledState is any value other than 1."
    ::= { msvmSerialPortEntry 22 }

msvmspeOtherIdentifyingInfo OBJECT-TYPE
    SYNTAX     WtcsDisplayString (SIZE (0..256))
    MAX-ACCESS read-only
    STATUS     current
    DESCRIPTION
        "OtherIdentifyingInfo captures data, in addition to
        DeviceID information, that could be used to
        identify a LogicalDevice. For example, you could
        use this property to hold the operating system's
        user-friendly name for the Device."
    ::= { msvmSerialPortEntry 23 }

msvmspeOtherPortType OBJECT-TYPE
    SYNTAX     WtcsDisplayString
    MAX-ACCESS read-only
    STATUS     current
    DESCRIPTION
        "Describes the type of module, when PortType is set
        to 1 ('Other')."
    ::= { msvmSerialPortEntry 24 }

msvmspePortType OBJECT-TYPE
    SYNTAX     INTEGER {
        unknown(0),
        other(1),
        notApplicable(2)
    }
    MAX-ACCESS read-only
    STATUS     current
    DESCRIPTION
        "PortType is defined to force consistent naming of
        the 'type' property in subclasses and to guarantee
        unique enum values for all instances of
        NetworkPort. When set to 1 ('Other'), related
        property OtherPortType contains a string
        description of the type of port. A range of values,
        DMTF_Reserved, has been defined that allows
        subclasses to override and define their specific
        types of ports."
    ::= { msvmSerialPortEntry 25 }

msvmspePowerManagementCapability OBJECT-TYPE
    SYNTAX     INTEGER {
        unknown(0),
        notSupported(1),
        disabled(2),
        enabled(3),
        powerSavingModesEnteredAutomatic(4),
        powerStateSettable(5),
        powerCyclingSupported(6),
        timedPowerOnSupported(7)
    }
    MAX-ACCESS read-only
    STATUS     current
    DESCRIPTION
        "Note: The use of this property has been
        deprecated. Instead, use the PowerCapabilites
        property in an associated
        PowerManagementCapabilities class. Deprecated
        description: An enumerated array describing the
        power management capabilities of the Device."
    ::= { msvmSerialPortEntry 26 }

msvmspePowerManagementSupported OBJECT-TYPE
    SYNTAX     TruthValue
    MAX-ACCESS read-only
    STATUS     current
    DESCRIPTION
        "Note: The use of this property has been
        deprecated. Instead, the existence of an associated
        PowerManagementCapabilities class (associated using
        the ElementCapabilities relationship) indicates
        that power management is supported. Deprecated
        description: Boolean that indicates that the Device
        can use power management."
    ::= { msvmSerialPortEntry 27 }

msvmspePowerOnHours OBJECT-TYPE
    SYNTAX     Gauge32
    UNITS "Hours"
    MAX-ACCESS read-only
    STATUS     current
    DESCRIPTION
        "Note: The use of this method is deprecated. 
        Deprecated description: The number of consecutive
        hours that this Device has been powered on since
        its last power cycle."
    ::= { msvmSerialPortEntry 28 }

msvmspeRequestedSpeed OBJECT-TYPE
    SYNTAX     Gauge32
    UNITS "Bits per Second"
    MAX-ACCESS read-only
    STATUS     current
    DESCRIPTION
        "The requested bandwidth of the Port in Bits per
        Second. The actual bandwidth is reported in
        LogicalPort.Speed."
    ::= { msvmSerialPortEntry 29 }

msvmspeRequestedState OBJECT-TYPE
    SYNTAX     INTEGER {
        enabled(2),
        disabled(3),
        shutDown(4),
        noChange(5),
        offline(6),
        test(7),
        deferred(8),
        quiesce(9),
        reboot(10),
        reset(11),
        notApplicable(12)
    }
    MAX-ACCESS read-only
    STATUS     current
    DESCRIPTION
        "RequestedState is an integer enumeration that
        indicates the last requested or desired state for
        the element. The actual state of the element is
        represented by EnabledState. This property is
        provided to compare the last requested and current
        enabled or disabled states. Note that when
        EnabledState is set to 5 ('Not Applicable'), then
        this property has no meaning. By default, the
        RequestedState of the element is 5 ('No Change').
        Refer to the EnabledState property description for
        explanations of the values in the RequestedState
        enumeration. 
        
        It should be noted that there are two new values in
        RequestedState that build on the statuses of
        EnabledState. These are 'Reboot' (10) and 'Reset'
        (11). Reboot refers to doing a 'Shut Down' and then
        moving to an 'Enabled' state. Reset indicates that
        the element is first 'Disabled' and then 'Enabled'.
        The distinction between requesting 'Shut Down' and
        'Disabled' should also be noted. Shut Down requests
        an orderly transition to the Disabled state, and
        might involve removing power, to completely erase
        any existing state. The Disabled state requests an
        immediate disabling of the element, such that it
        will not execute or accept any commands or
        processing requests. 
        
        This property is set as the result of a method
        invocation (such as Start or StopService on
        CIM_Service), or can be overridden and defined as
        WRITEable in a subclass. The method approach is
        considered superior to a WRITEable property,
        because it allows an explicit invocation of the
        operation and the return of a result code. 
        
        A particular instance of EnabledLogicalElement
        might not support RequestedStateChange. If this
        occurs, the value 12 ('Not Applicable') is used."
    ::= { msvmSerialPortEntry 30 }

msvmspeSpeed OBJECT-TYPE
    SYNTAX     Gauge32
    UNITS "Bits per Second"
    MAX-ACCESS read-only
    STATUS     current
    DESCRIPTION
        "The bandwidth of the Port in Bits per Second."
    ::= { msvmSerialPortEntry 31 }

msvmspeStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmSerialPortEntry 32 }

msvmspeStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmSerialPortEntry 33 }

msvmspeStatusInfo OBJECT-TYPE
    SYNTAX     INTEGER {
        other(1),
        unknown(2),
        enabled(3),
        disabled(4),
        notApplicable(5)
    }
    MAX-ACCESS read-only
    STATUS     current
    DESCRIPTION
        "Note: The use of this method is deprecated in lieu
        of a more clearly named property (EnabledState)
        that is inherited from ManagedSystemElement and
        that has additional enumerated values. 
        Deprecated description: The StatusInfo property
        indicates whether the Logical Device is in an
        enabled state (value=3), disabled state (value=4),
        some other state (value=1), or an unknown state
        (value=2). If this property does not apply to the
        LogicalDevice, the value 5 ('Not Applicable')
        should be used. If a Device is
        ('Enabled')(value=3), it has been powered up and is
        configured and operational. The Device might or
        might not be functionally active, depending on
        whether its Availability (or
        AdditionalAvailability) indicates that it is
        ('Running/Full Power')(value=3) or ('Off line')
        (value=8). In an enabled but offline mode, a Device
        might be performing out-of-band requests, such as
        running Diagnostics. If StatusInfo is ('Disabled')
        (value=4), a Device can only be 'enabled' or
        powered off. In a personal computer environment,
        ('Disabled') means that the driver of the device is
        not available in the stack. In other environments,
        a Device can be disabled by removing its
        configuration file. A disabled device is physically
        present in a System and consuming resources, but it
        cannot be communicated with until a driver is
        loaded, a configuration file is loaded, or some
        other 'enabling' activity has occurred."
    ::= { msvmSerialPortEntry 34 }

msvmspeSystemCreationClassName OBJECT-TYPE
    SYNTAX     WtcsDisplayString (SIZE (0..256))
    MAX-ACCESS read-only
    STATUS     current
    DESCRIPTION
        "The CreationClassName of the scoping system."
    ::= { msvmSerialPortEntry 35 }

msvmspeSystemName OBJECT-TYPE
    SYNTAX     WtcsDisplayString (SIZE (0..256))
    MAX-ACCESS read-only
    STATUS     current
    DESCRIPTION
        "The System Name of the scoping system."
    ::= { msvmSerialPortEntry 36 }

msvmspeTimeOfLastStateChange OBJECT-TYPE
    SYNTAX     DateAndTime
    MAX-ACCESS read-only
    STATUS     current
    DESCRIPTION
        "The date or time when the EnabledState of the
        element last changed. If the state of the element
        has not changed and this property is populated,
        then it must be set to a 0 interval value. If a
        state change was requested, but rejected or not yet
        processed, the property must not be updated."
    ::= { msvmSerialPortEntry 37 }

msvmspeTotalPowerOnHours OBJECT-TYPE
    SYNTAX     Gauge32
    UNITS "Hours"
    MAX-ACCESS read-only
    STATUS     current
    DESCRIPTION
        "Note: The use of this method is deprecated. 
        Deprecated description: The total number of hours
        that this Device has been powered on."
    ::= { msvmSerialPortEntry 38 }

msvmspeUsageRestriction OBJECT-TYPE
    SYNTAX     INTEGER {
        unknown(0),
        frontendonly(2),
        backendonly(3),
        notrestricted(4)
    }
    MAX-ACCESS read-only
    STATUS     current
    DESCRIPTION
        "In some circumstances, a LogicalPort might be
        identifiable as a front end or back end port. An
        example of this situation would be a storage array
        that might have back end ports to communicate with
        disk drives and front end ports to communicate with
        hosts. If there is no restriction on the use of the
        port, then the value should be set to 'not
        restricted'."
    ::= { msvmSerialPortEntry 39 }

msvmSerialPortOnControllerTable OBJECT-TYPE
    SYNTAX     SEQUENCE OF MsvmSerialPortOnSerialController
    MAX-ACCESS not-accessible
    STATUS     current
    DESCRIPTION
        "Associates a serial port with a serial
        controller."
    ::= { msvmSerialDevices 3 }

msvmSerialPortOnControllerEntry OBJECT-TYPE
    SYNTAX     MsvmSerialPortOnSerialController
    MAX-ACCESS not-accessible
    STATUS     current
    DESCRIPTION
        "None"
    INDEX      { msvmsposcIndex }
    ::= { msvmSerialPortOnControllerTable 1 }

MsvmSerialPortOnSerialController ::= SEQUENCE {
    msvmsposcIndex Integer32,
    msvmsposcAntecedent WtcsDisplayString,
    msvmsposcDependent WtcsDisplayString
}

msvmsposcIndex OBJECT-TYPE
    SYNTAX     Integer32 (1..2147483647)
    MAX-ACCESS read-only
    STATUS     current
    DESCRIPTION
        "The value of this object uniquely identifies the
        instance entry for this class."
    ::= { msvmSerialPortOnControllerEntry 1 }

msvmsposcAntecedent OBJECT-TYPE
    SYNTAX     WtcsDisplayString
    MAX-ACCESS read-only
    STATUS     current
    DESCRIPTION
        "Antecedent represents the independent object in
        this association."
    ::= { msvmSerialPortOnControllerEntry 2 }

msvmsposcDependent OBJECT-TYPE
    SYNTAX     WtcsDisplayString
    MAX-ACCESS read-only
    STATUS     current
    DESCRIPTION
        "Dependent represents the object that is dependent
        on the Antecedent."
    ::= { msvmSerialPortOnControllerEntry 3 }

msvmStorage OBJECT-IDENTITY
    STATUS     current
    DESCRIPTION
        "The storage objects are separated into three
        types: controllers, drives, and media.
        
        There are two controllers, an emulated IDE
        controller and a synthetic SCSI controller. Both
        controllers support the attachment of drives that
        host the physical and virtualized media. The SCSI
        controller also supports a pass-through mode that
        supports the attachment of tape drives."
    ::= { informantHyperV 10 }

msvmControlledByTable OBJECT-TYPE
    SYNTAX     SEQUENCE OF MsvmControlledBy
    MAX-ACCESS not-accessible
    STATUS     current
    DESCRIPTION
        "Associates a storage device with the storage
        controller that owns the device. This association
        is used with both IDE and floppy controllers."
    ::= { msvmStorage 1 }

msvmControlledByEntry OBJECT-TYPE
    SYNTAX     MsvmControlledBy
    MAX-ACCESS not-accessible
    STATUS     current
    DESCRIPTION
        "None"
    INDEX      { msvmcbIndex }
    ::= { msvmControlledByTable 1 }

MsvmControlledBy ::= SEQUENCE {
    msvmcbIndex Integer32,
    msvmcbAccessMode INTEGER,
    msvmcbAccessPriority Integer32,
    msvmcbAccessState INTEGER,
    msvmcbAntecedent WtcsDisplayString,
    msvmcbDependent WtcsDisplayString,
    msvmcbDeviceNumber WtcsDisplayString,
    msvmcbNegotiatedDataWidth Gauge32,
    msvmcbNegotiatedSpeed Gauge32,
    msvmcbNumberOfHardResets Gauge32,
    msvmcbNumberOfSoftResets Gauge32,
    msvmcbTimeOfDeviceReset DateAndTime
}

msvmcbIndex OBJECT-TYPE
    SYNTAX     Integer32 (1..2147483647)
    MAX-ACCESS read-only
    STATUS     current
    DESCRIPTION
        "The value of this object uniquely identifies the
        instance entry for this class."
    ::= { msvmControlledByEntry 1 }

msvmcbAccessMode OBJECT-TYPE
    SYNTAX     INTEGER {
        readWrite(2),
        readOnly(3),
        noAccess(4)
    }
    MAX-ACCESS read-only
    STATUS     current
    DESCRIPTION
        "This property describes the accessibility of the
        device through the antecedent controller."
    ::= { msvmControlledByEntry 2 }

msvmcbAccessPriority OBJECT-TYPE
    SYNTAX     Integer32
    MAX-ACCESS read-only
    STATUS     current
    DESCRIPTION
        "The property describes the priority given to
        accesses of the device through this controller. The
        highest priority path will have the lowest value
        for this parameter."
    ::= { msvmControlledByEntry 3 }

msvmcbAccessState OBJECT-TYPE
    SYNTAX     INTEGER {
        unknown(0),
        active(1),
        inactive(2)
    }
    MAX-ACCESS read-only
    STATUS     current
    DESCRIPTION
        "The State property indicates whether the
        Controller is actively commanding or accessing the
        Device (value=1) or not (value=2). Also, the value,
        'Unknown' (0), can be defined. This information is
        necessary when a LogicalDevice can be commanded by,
        or accessed through, multiple Controllers."
    ::= { msvmControlledByEntry 4 }

msvmcbAntecedent OBJECT-TYPE
    SYNTAX     WtcsDisplayString
    MAX-ACCESS read-only
    STATUS     current
    DESCRIPTION
        "Antecedent represents the independent object in
        this association."
    ::= { msvmControlledByEntry 5 }

msvmcbDependent OBJECT-TYPE
    SYNTAX     WtcsDisplayString
    MAX-ACCESS read-only
    STATUS     current
    DESCRIPTION
        "Dependent represents the object that is dependent
        on the Antecedent."
    ::= { msvmControlledByEntry 6 }

msvmcbDeviceNumber OBJECT-TYPE
    SYNTAX     WtcsDisplayString
    MAX-ACCESS read-only
    STATUS     current
    DESCRIPTION
        "Address of associated Device in context of the
        antecedent Controller."
    ::= { msvmControlledByEntry 7 }

msvmcbNegotiatedDataWidth OBJECT-TYPE
    SYNTAX     Gauge32
    UNITS "Bits"
    MAX-ACCESS read-only
    STATUS     current
    DESCRIPTION
        "When several bus and connection data widths are
        possible, the NegotiatedDataWidth property defines
        the one that is in use between the Devices. Data
        width is specified in bits. If data width is not
        negotiated, or if this information is not available
        or not important to Device management, the property
        should be set to 0."
    ::= { msvmControlledByEntry 8 }

msvmcbNegotiatedSpeed OBJECT-TYPE
    SYNTAX     Gauge32
    UNITS "Bits per Second"
    MAX-ACCESS read-only
    STATUS     current
    DESCRIPTION
        "When several bus and connection speeds are
        possible, the NegotiatedSpeed property defines the
        one that is in use between the Devices. Speed is
        specified in bits per second. If connection or bus
        speeds are not negotiated, or if this information
        is not available or not important to Device
        management, the property should be set to 0."
    ::= { msvmControlledByEntry 9 }

msvmcbNumberOfHardResets OBJECT-TYPE
    SYNTAX     Gauge32
    MAX-ACCESS read-only
    STATUS     current
    DESCRIPTION
        "Number of hard resets issued by the Controller. A
        hard reset returns the Device to its initialization
        or boot-up state. All internal Device state
        information and data are lost."
    ::= { msvmControlledByEntry 10 }

msvmcbNumberOfSoftResets OBJECT-TYPE
    SYNTAX     Gauge32
    MAX-ACCESS read-only
    STATUS     current
    DESCRIPTION
        "Number of soft resets issued by the Controller. A
        soft reset does not completely clear current Device
        state or data. Exact semantics are dependent on the
        Device and on the protocols and mechanisms used to
        communicate with the Device."
    ::= { msvmControlledByEntry 11 }

msvmcbTimeOfDeviceReset OBJECT-TYPE
    SYNTAX     DateAndTime
    MAX-ACCESS read-only
    STATUS     current
    DESCRIPTION
        "The time that the downstream Device was last reset
        by the Controller."
    ::= { msvmControlledByEntry 12 }

msvmDiskDriveTable OBJECT-TYPE
    SYNTAX     SEQUENCE OF MsvmDiskDrive
    MAX-ACCESS not-accessible
    STATUS     current
    DESCRIPTION
        "Represents a hard drive inside of a virtual
        machine."
    ::= { msvmStorage 2 }

msvmDiskDriveEntry OBJECT-TYPE
    SYNTAX     MsvmDiskDrive
    MAX-ACCESS not-accessible
    STATUS     current
    DESCRIPTION
        "None"
    INDEX      { msvmddIndex }
    ::= { msvmDiskDriveTable 1 }

MsvmDiskDrive ::= SEQUENCE {
    msvmddIndex Integer32,
    msvmddAdditionalAvailability INTEGER,
    msvmddAvailability INTEGER,
    msvmddCapabilities INTEGER,
    msvmddCapabilityDescriptions WtcsDisplayString,
    msvmddCaption WtcsDisplayString,
    msvmddCompressionMethod WtcsDisplayString,
    msvmddCreationClassName WtcsDisplayString,
    msvmddDefaultBlockSize Gauge32,
    msvmddDescription WtcsDisplayString,
    msvmddDeviceID WtcsDisplayString,
    msvmddDriveNumber Gauge32,
    msvmddElementName WtcsDisplayString,
    msvmddEnabledDefault INTEGER,
    msvmddEnabledState INTEGER,
    msvmddErrorCleared TruthValue,
    msvmddErrorDescription WtcsDisplayString,
    msvmddErrorMethodology WtcsDisplayString,
    msvmddHealthState INTEGER,
    msvmddIdentifyingDescriptions WtcsDisplayString,
    msvmddInstallDate DateAndTime,
    msvmddLastCleaned DateAndTime,
    msvmddLastErrorCode Gauge32,
    msvmddLoadTime Gauge32,
    msvmddLocationIndicator INTEGER,
    msvmddMaxAccessTime Gauge32,
    msvmddMaxBlockSize Gauge32,
    msvmddMaxMediaSize Gauge32,
    msvmddMaxQuiesceTime Gauge32,
    msvmddMaxUnitsBeforeCleaning Gauge32,
    msvmddMediaIsLocked TruthValue,
    msvmddMinBlockSize Gauge32,
    msvmddMountCount Gauge32,
    msvmddName WtcsDisplayString,
    msvmddNeedsCleaning TruthValue,
    msvmddNumberOfMediaSupported Gauge32,
    msvmddOperationalStatus INTEGER,
    msvmddOtherEnabledState WtcsDisplayString,
    msvmddOtherIdentifyingInfo WtcsDisplayString,
    msvmddPowerManagementCapability INTEGER,
    msvmddPowerManagementSupported TruthValue,
    msvmddPowerOnHours Gauge32,
    msvmddRequestedState INTEGER,
    msvmddSecurity INTEGER,
    msvmddStatus WtcsDisplayString,
    msvmddStatusDescriptions WtcsDisplayString,
    msvmddStatusInfo INTEGER,
    msvmddSystemCreationClassName WtcsDisplayString,
    msvmddSystemName WtcsDisplayString,
    msvmddTimeOfLastMount DateAndTime,
    msvmddTimeOfLastStateChange DateAndTime,
    msvmddTotalMountTime Gauge32,
    msvmddTotalPowerOnHours Gauge32,
    msvmddUncompressedDataRate Gauge32,
    msvmddUnitsDescription WtcsDisplayString,
    msvmddUnitsUsed Gauge32,
    msvmddUnloadTime Gauge32
}

msvmddIndex OBJECT-TYPE
    SYNTAX     Integer32 (1..2147483647)
    MAX-ACCESS read-only
    STATUS     current
    DESCRIPTION
        "The value of this object uniquely identifies the
        instance entry for this class."
    ::= { msvmDiskDriveEntry 1 }

msvmddAdditionalAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Additional availability and status of the Device
        in addition to that specified in the Availability
        property. The Availability property denotes the
        primary status and availability of the Device. In
        some cases, this property will not be sufficient to
        denote the complete status of the Device. In those
        cases, the AdditionalAvailability property can be
        used to provide further information. For example,
        the primary Availability of a device might be 'Off
        line' (value=8) or in a low-power state
        (AdditionalAvailability value=14), or the Device
        could be running Diagnostics
        (AdditionalAvailability value=5, 'In Test')."
    ::= { msvmDiskDriveEntry 2 }

msvmddAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Note: The use of this property has been
        deprecated. 
        Deprecated description: The primary availability
        and status of the Device. (Additional status
        information can be specified using the Additional
        Availability array property.) For example, the
        Availability property indicates that the Device is
        running and has full power (value=3), or is in a
        warning (4), test (5), degraded (10) or power save
        state (values 13-15 and 17). The Power Save states
        are defined as follows: Value 13 ('Power Save -
        Unknown') indicates that the Device is known to be
        in a power save mode, but its exact status in this
        mode is unknown; value 14 ('Power Save - Low Power
        Mode') indicates that the Device is in a power save
        state but still functioning, and might exhibit
        degraded performance; value 15 ('Power Save -
        Standby') indicates that the Device is not
        functioning but could be brought to full power
        'quickly'; and value 17 ('Power Save - Warning')
        indicates that the Device is in a warning state,
        but is also in a power save mode."
    ::= { msvmDiskDriveEntry 3 }

msvmddCapabilities OBJECT-TYPE
    SYNTAX     INTEGER {
        unknown(0),
        other(1),
        sequentialAccess(2),
        randomAccess(3),
        supportsWriting(4),
        encryption(5),
        compression(6),
        supportsRemoveableMedia(7),
        manualCleaning(8),
        automaticCleaning(9),
        smartNotification(10),
        supportsDualSidedMedia(11),
        predismountEjectNotRequired(12)
    }
    MAX-ACCESS read-only
    STATUS     current
    DESCRIPTION
        "Capabilities of the MediaAccessDevice. For
        example, the Device may support 'Random Access',
        removeable media and 'Automatic Cleaning'. In this
        case, the values 3, 7 and 9 would be written to the
        array. 
        Several of the enumerated values require some
        explanation: 1) Value 11, Supports Dual Sided
        Media, distinguishes a Device that can access both
        sides of dual sided Media, from a Device that reads
        only a single side and requires the Media to be
        flipped; and, 2) Value 12, Predismount Eject Not
        Required, indicates that Media does not have to be
        explicitly ejected from the Device before being
        accessed by a PickerElement."
    ::= { msvmDiskDriveEntry 4 }

msvmddCapabilityDescriptions OBJECT-TYPE
    SYNTAX     WtcsDisplayString
    MAX-ACCESS read-only
    STATUS     current
    DESCRIPTION
        "An array of free-form strings providing more
        detailed explanations for any of the AccessDevice
        features indicated in the Capabilities array. Note,
        each entry of this array is related to the entry in
        the Capabilities array that is located at the same
        index."
    ::= { msvmDiskDriveEntry 5 }

msvmddCaption OBJECT-TYPE
    SYNTAX     WtcsDisplayString (SIZE (0..64))
    MAX-ACCESS read-only
    STATUS     current
    DESCRIPTION
        "The Caption property is a short textual
        description (one- line string) of the object."
    ::= { msvmDiskDriveEntry 6 }

msvmddCompressionMethod OBJECT-TYPE
    SYNTAX     WtcsDisplayString
    MAX-ACCESS read-only
    STATUS     current
    DESCRIPTION
        "A free form string indicating the algorithm or
        tool used by the device to support compression. If
        it is not possible or not desired to describe the
        compression scheme (perhaps because it is not
        known), recommend using the following words:
        'Unknown' to represent that it is not known whether
        the device supports compression capabilities or
        not, 'Compressed' to represent that the device
        supports compression capabilities but either its
        compression scheme is not known or not disclosed,
        and 'Not Compressed' to represent that the devices
        does not support compression capabilities."
    ::= { msvmDiskDriveEntry 7 }

msvmddCreationClassName OBJECT-TYPE
    SYNTAX     WtcsDisplayString (SIZE (0..256))
    MAX-ACCESS read-only
    STATUS     current
    DESCRIPTION
        "CreationClassName indicates the name of the class
        or the subclass used in the creation of an
        instance. When used with the other key properties
        of this class, this property allows all instances
        of this class and its subclasses to be uniquely
        identified."
    ::= { msvmDiskDriveEntry 8 }

msvmddDefaultBlockSize OBJECT-TYPE
    SYNTAX     Gauge32
    UNITS "Bytes"
    MAX-ACCESS read-only
    STATUS     current
    DESCRIPTION
        "Default block size, in bytes, for this Device."
    ::= { msvmDiskDriveEntry 9 }

msvmddDescription OBJECT-TYPE
    SYNTAX     WtcsDisplayString
    MAX-ACCESS read-only
    STATUS     current
    DESCRIPTION
        "The Description property provides a textual
        description of the object."
    ::= { msvmDiskDriveEntry 10 }

msvmddDeviceID OBJECT-TYPE
    SYNTAX     WtcsDisplayString (SIZE (0..64))
    MAX-ACCESS read-only
    STATUS     current
    DESCRIPTION
        "An address or other identifying information used
        to uniquely name the LogicalDevice."
    ::= { msvmDiskDriveEntry 11 }

msvmddDriveNumber OBJECT-TYPE
    SYNTAX     Gauge32
    MAX-ACCESS read-only
    STATUS     current
    DESCRIPTION
        "The drive number of the physical drive on the
        host."
    ::= { msvmDiskDriveEntry 12 }

msvmddElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmDiskDriveEntry 13 }

msvmddEnabledDefault OBJECT-TYPE
    SYNTAX     INTEGER {
        enabled(2),
        disabled(3),
        notApplicable(5),
        enabledbutOffline(6),
        noDefault(7)
    }
    MAX-ACCESS read-only
    STATUS     current
    DESCRIPTION
        "An enumerated value indicating an administrator's
        default or startup configuration for the Enabled
        State of an element. By default, the element is
        'Enabled' (value=2)."
    ::= { msvmDiskDriveEntry 14 }

msvmddEnabledState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "EnabledState is an integer enumeration that
        indicates the enabled and disabled states of an
        element. It can also indicate the transitions
        between these requested states. For example,
        shutting down (value=4) and starting (value=10) are
        transient states between enabled and disabled. The
        following text briefly summarizes the various
        enabled and disabled states: 
        Enabled (2) indicates that the element is or could
        be executing commands, will process any queued
        commands, and queues new requests. 
        Disabled (3) indicates that the element will not
        execute commands and will drop any new requests. 
        Shutting Down (4) indicates that the element is in
        the process of going to a Disabled state. 
        Not Applicable (5) indicates the element does not
        support being enabled or disabled. 
        Enabled but Offline (6) indicates that the element
        might be completing commands, and will drop any new
        requests. 
        Test (7) indicates that the element is in a test
        state. 
        Deferred (8) indicates that the element might be
        completing commands, but will queue any new
        requests. 
        Quiesce (9) indicates that the element is enabled
        but in a restricted mode. The behavior of the
        element is similar to the Enabled state, but it
        processes only a restricted set of commands. All
        other requests are queued. 
        Starting (10) indicates that the element is in the
        process of going to an Enabled state. New requests
        are queued."
    ::= { msvmDiskDriveEntry 15 }

msvmddErrorCleared OBJECT-TYPE
    SYNTAX     TruthValue
    MAX-ACCESS read-only
    STATUS     current
    DESCRIPTION
        "Note: The use of this method is deprecated. 
        Deprecated description: ErrorCleared is a Boolean
        property that indicates that the error reported in
        LastErrorCode is now cleared."
    ::= { msvmDiskDriveEntry 16 }

msvmddErrorDescription OBJECT-TYPE
    SYNTAX     WtcsDisplayString
    MAX-ACCESS read-only
    STATUS     current
    DESCRIPTION
        "Note: The use of this method is deprecated. 
        Deprecated description: ErrorDescription is a
        free-form string that supplies more information
        about the error recorded in LastErrorCode and
        information on any corrective actions that can be
        taken."
    ::= { msvmDiskDriveEntry 17 }

msvmddErrorMethodology OBJECT-TYPE
    SYNTAX     WtcsDisplayString
    MAX-ACCESS read-only
    STATUS     current
    DESCRIPTION
        "ErrorMethodology is a free-form string describing
        the type(s) of error detection and correction
        supported by this Device."
    ::= { msvmDiskDriveEntry 18 }

msvmddHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmDiskDriveEntry 19 }

msvmddIdentifyingDescriptions OBJECT-TYPE
    SYNTAX     WtcsDisplayString
    MAX-ACCESS read-only
    STATUS     current
    DESCRIPTION
        "An array of free-form strings providing
        explanations and details behind the entries in the
        OtherIdentifyingInfo array. Note that each entry of
        this array is related to the entry in
        OtherIdentifyingInfo that is located at the same
        index."
    ::= { msvmDiskDriveEntry 20 }

msvmddInstallDate OBJECT-TYPE
    SYNTAX     DateAndTime
    MAX-ACCESS read-only
    STATUS     current
    DESCRIPTION
        "A datetime value that indicates when the object
        was installed. Lack of a value does not indicate
        that the object is not installed."
    ::= { msvmDiskDriveEntry 21 }

msvmddLastCleaned OBJECT-TYPE
    SYNTAX     DateAndTime
    MAX-ACCESS read-only
    STATUS     current
    DESCRIPTION
        "The date and time on which the Device was last
        cleaned."
    ::= { msvmDiskDriveEntry 22 }

msvmddLastErrorCode OBJECT-TYPE
    SYNTAX     Gauge32
    MAX-ACCESS read-only
    STATUS     current
    DESCRIPTION
        "Note: The use of this method is deprecated. 
        Deprecated description: LastErrorCode captures the
        last error code reported by the LogicalDevice."
    ::= { msvmDiskDriveEntry 23 }

msvmddLoadTime OBJECT-TYPE
    SYNTAX     Gauge32
    UNITS "MilliSeconds"
    MAX-ACCESS read-only
    STATUS     current
    DESCRIPTION
        "Time in milliseconds from 'load' to being able to
        read or write a Media. For example, for DiskDrives,
        this is the interval between a disk not spinning to
        the disk reporting that it is ready for read/write
        (ie, the disk spinning at nominal speeds). For
        TapeDrives, this is the time from a Media being
        injected to reporting that it is ready for an
        application. This is usually at the tape's BOT
        area."
    ::= { msvmDiskDriveEntry 24 }

msvmddLocationIndicator OBJECT-TYPE
    SYNTAX     INTEGER {
        unknown(0),
        on(2),
        off(3),
        notSupported(4)
    }
    MAX-ACCESS read-only
    STATUS     current
    DESCRIPTION
        "An integer that reflects the state of an indicator
        (e.g., LED) that is part of a device. Reading the
        value gives the current state. Writing the value
        with 'On'/'Off' turns the indicator on/off, other
        values may not be written."
    ::= { msvmDiskDriveEntry 25 }

msvmddMaxAccessTime OBJECT-TYPE
    SYNTAX     Gauge32
    UNITS "MilliSeconds"
    MAX-ACCESS read-only
    STATUS     current
    DESCRIPTION
        "Time in milliseconds to move from the first
        location on the Media to the location that is
        furthest with respect to time. For a DiskDrive,
        this represents full seek + full rotational delay.
        For TapeDrives, this represents a search from the
        beginning of the tape to the most physically
        distant point. (The end of a tape may be at its
        most physically distant point, but this is not
        necessarily true.)"
    ::= { msvmDiskDriveEntry 26 }

msvmddMaxBlockSize OBJECT-TYPE
    SYNTAX     Gauge32
    UNITS "Bytes"
    MAX-ACCESS read-only
    STATUS     current
    DESCRIPTION
        "Maximum block size, in bytes, for media accessed
        by this Device."
    ::= { msvmDiskDriveEntry 27 }

msvmddMaxMediaSize OBJECT-TYPE
    SYNTAX     Gauge32
    MAX-ACCESS read-only
    STATUS     current
    DESCRIPTION
        "Maximum size, in KBytes, of media supported by
        this Device. KBytes is interpreted as the number of
        bytes multiplied by 1000 (NOT the number of bytes
        multiplied by 1024)."
    ::= { msvmDiskDriveEntry 28 }

msvmddMaxQuiesceTime OBJECT-TYPE
    SYNTAX     Gauge32
    UNITS "MilliSeconds"
    MAX-ACCESS read-only
    STATUS     current
    DESCRIPTION
        "Note: The use of this property has been
        deprecated. When evaluating the use of Quiesce, it
        was determined that this single property is not
        adequate for describing when a device will
        automatically exit a quiescent state. In fact, the
        most likely scenario for a device to exit a
        quiescent state was determined to be based on the
        number of outstanding requests queued rather than
        on a maximum time. This decision will be
        re-evaluated and repositioned later. 
        Deprecated description: Maximum time, in
        milliseconds, that a Device can run in a 'Quiesced'
        state. The state is defined in its Availability and
        AdditionalAvailability properties, where 'Quiesced'
        is conveyed by the value 21. What occurs at the end
        of the time limit is device-specific. The Device
        can unquiesce, can be offline, or can take other
        actions. A value of 0 indicates that a Device can
        remain quiesced indefinitely."
    ::= { msvmDiskDriveEntry 29 }

msvmddMaxUnitsBeforeCleaning OBJECT-TYPE
    SYNTAX     Gauge32
    MAX-ACCESS read-only
    STATUS     current
    DESCRIPTION
        "An unsigned integer indicating the maximum 'units'
        that can be used, with respect to the AccessDevice,
        before the Device should be cleaned. The property,
        UnitsDescription, defines how 'units' should be
        interpreted."
    ::= { msvmDiskDriveEntry 30 }

msvmddMediaIsLocked OBJECT-TYPE
    SYNTAX     TruthValue
    MAX-ACCESS read-only
    STATUS     current
    DESCRIPTION
        "True indicates that the media is locked in the
        Device and can not be ejected. For non-removeable
        Devices, this value should be true."
    ::= { msvmDiskDriveEntry 31 }

msvmddMinBlockSize OBJECT-TYPE
    SYNTAX     Gauge32
    UNITS "Bytes"
    MAX-ACCESS read-only
    STATUS     current
    DESCRIPTION
        "Minimum block size, in bytes, for media accessed
        by this Device."
    ::= { msvmDiskDriveEntry 32 }

msvmddMountCount OBJECT-TYPE
    SYNTAX     Gauge32
    MAX-ACCESS read-only
    STATUS     current
    DESCRIPTION
        "For a MediaAccessDevice that supports removable
        Media, the number of times that Media have been
        mounted for data transfer or to clean the Device.
        For Devices accessing nonremovable Media, such as
        hard disks, this property is not applicable and
        should be set to 0."
    ::= { msvmDiskDriveEntry 33 }

msvmddName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmDiskDriveEntry 34 }

msvmddNeedsCleaning OBJECT-TYPE
    SYNTAX     TruthValue
    MAX-ACCESS read-only
    STATUS     current
    DESCRIPTION
        "Boolean indicating that the MediaAccessDevice
        needs cleaning. Whether manual or automatic
        cleaning is possible is indicated in the
        Capabilities array property."
    ::= { msvmDiskDriveEntry 35 }

msvmddNumberOfMediaSupported OBJECT-TYPE
    SYNTAX     Gauge32
    MAX-ACCESS read-only
    STATUS     current
    DESCRIPTION
        "When the MediaAccessDevice supports multiple
        individual Media, this property defines the maximum
        number which can be supported or inserted."
    ::= { msvmDiskDriveEntry 36 }

msvmddOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmDiskDriveEntry 37 }

msvmddOtherEnabledState OBJECT-TYPE
    SYNTAX     WtcsDisplayString
    MAX-ACCESS read-only
    STATUS     current
    DESCRIPTION
        "A string that describes the enabled or disabled
        state of the element when the EnabledState property
        is set to 1 ('Other'). This property must be set to
        null when EnabledState is any value other than 1."
    ::= { msvmDiskDriveEntry 38 }

msvmddOtherIdentifyingInfo OBJECT-TYPE
    SYNTAX     WtcsDisplayString (SIZE (0..256))
    MAX-ACCESS read-only
    STATUS     current
    DESCRIPTION
        "OtherIdentifyingInfo captures data, in addition to
        DeviceID information, that could be used to
        identify a LogicalDevice. For example, you could
        use this property to hold the operating system's
        user-friendly name for the Device."
    ::= { msvmDiskDriveEntry 39 }

msvmddPowerManagementCapability OBJECT-TYPE
    SYNTAX     INTEGER {
        unknown(0),
        notSupported(1),
        disabled(2),
        enabled(3),
        powerSavingModesEnteredAutomatic(4),
        powerStateSettable(5),
        powerCyclingSupported(6),
        timedPowerOnSupported(7)
    }
    MAX-ACCESS read-only
    STATUS     current
    DESCRIPTION
        "Note: The use of this property has been
        deprecated. Instead, use the PowerCapabilites
        property in an associated
        PowerManagementCapabilities class. Deprecated
        description: An enumerated array describing the
        power management capabilities of the Device."
    ::= { msvmDiskDriveEntry 40 }

msvmddPowerManagementSupported OBJECT-TYPE
    SYNTAX     TruthValue
    MAX-ACCESS read-only
    STATUS     current
    DESCRIPTION
        "Note: The use of this property has been
        deprecated. Instead, the existence of an associated
        PowerManagementCapabilities class (associated using
        the ElementCapabilities relationship) indicates
        that power management is supported. Deprecated
        description: Boolean that indicates that the Device
        can use power management."
    ::= { msvmDiskDriveEntry 41 }

msvmddPowerOnHours OBJECT-TYPE
    SYNTAX     Gauge32
    UNITS "Hours"
    MAX-ACCESS read-only
    STATUS     current
    DESCRIPTION
        "Note: The use of this method is deprecated. 
        Deprecated description: The number of consecutive
        hours that this Device has been powered on since
        its last power cycle."
    ::= { msvmDiskDriveEntry 42 }

msvmddRequestedState OBJECT-TYPE
    SYNTAX     INTEGER {
        enabled(2),
        disabled(3),
        shutDown(4),
        noChange(5),
        offline(6),
        test(7),
        deferred(8),
        quiesce(9),
        reboot(10),
        reset(11),
        notApplicable(12)
    }
    MAX-ACCESS read-only
    STATUS     current
    DESCRIPTION
        "RequestedState is an integer enumeration that
        indicates the last requested or desired state for
        the element. The actual state of the element is
        represented by EnabledState. This property is
        provided to compare the last requested and current
        enabled or disabled states. Note that when
        EnabledState is set to 5 ('Not Applicable'), then
        this property has no meaning. By default, the
        RequestedState of the element is 5 ('No Change').
        Refer to the EnabledState property description for
        explanations of the values in the RequestedState
        enumeration. 
        
        It should be noted that there are two new values in
        RequestedState that build on the statuses of
        EnabledState. These are 'Reboot' (10) and 'Reset'
        (11). Reboot refers to doing a 'Shut Down' and then
        moving to an 'Enabled' state. Reset indicates that
        the element is first 'Disabled' and then 'Enabled'.
        The distinction between requesting 'Shut Down' and
        'Disabled' should also be noted. Shut Down requests
        an orderly transition to the Disabled state, and
        might involve removing power, to completely erase
        any existing state. The Disabled state requests an
        immediate disabling of the element, such that it
        will not execute or accept any commands or
        processing requests. 
        
        This property is set as the result of a method
        invocation (such as Start or StopService on
        CIM_Service), or can be overridden and defined as
        WRITEable in a subclass. The method approach is
        considered superior to a WRITEable property,
        because it allows an explicit invocation of the
        operation and the return of a result code. 
        
        A particular instance of EnabledLogicalElement
        might not support RequestedStateChange. If this
        occurs, the value 12 ('Not Applicable') is used."
    ::= { msvmDiskDriveEntry 43 }

msvmddSecurity OBJECT-TYPE
    SYNTAX     INTEGER {
        other(1),
        unknown(2),
        none(3),
        readOnly(4),
        lockedOut(5),
        bootBypass(6),
        bootBypassandReadOnly(7)
    }
    MAX-ACCESS read-only
    STATUS     current
    DESCRIPTION
        "An enumeration indicating the operational security
        defined for the MediaAccessDevice. For example,
        information that the Device is 'Read Only'
        (value=4) or 'Boot Bypass' (value=6) can be
        described using this property."
    ::= { msvmDiskDriveEntry 44 }

msvmddStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmDiskDriveEntry 45 }

msvmddStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmDiskDriveEntry 46 }

msvmddStatusInfo OBJECT-TYPE
    SYNTAX     INTEGER {
        other(1),
        unknown(2),
        enabled(3),
        disabled(4),
        notApplicable(5)
    }
    MAX-ACCESS read-only
    STATUS     current
    DESCRIPTION
        "Note: The use of this method is deprecated in lieu
        of a more clearly named property (EnabledState)
        that is inherited from ManagedSystemElement and
        that has additional enumerated values. 
        Deprecated description: The StatusInfo property
        indicates whether the Logical Device is in an
        enabled state (value=3), disabled state (value=4),
        some other state (value=1), or an unknown state
        (value=2). If this property does not apply to the
        LogicalDevice, the value 5 ('Not Applicable')
        should be used. If a Device is
        ('Enabled')(value=3), it has been powered up and is
        configured and operational. The Device might or
        might not be functionally active, depending on
        whether its Availability (or
        AdditionalAvailability) indicates that it is
        ('Running/Full Power')(value=3) or ('Off line')
        (value=8). In an enabled but offline mode, a Device
        might be performing out-of-band requests, such as
        running Diagnostics. If StatusInfo is ('Disabled')
        (value=4), a Device can only be 'enabled' or
        powered off. In a personal computer environment,
        ('Disabled') means that the driver of the device is
        not available in the stack. In other environments,
        a Device can be disabled by removing its
        configuration file. A disabled device is physically
        present in a System and consuming resources, but it
        cannot be communicated with until a driver is
        loaded, a configuration file is loaded, or some
        other 'enabling' activity has occurred."
    ::= { msvmDiskDriveEntry 47 }

msvmddSystemCreationClassName OBJECT-TYPE
    SYNTAX     WtcsDisplayString (SIZE (0..256))
    MAX-ACCESS read-only
    STATUS     current
    DESCRIPTION
        "The CreationClassName of the scoping system."
    ::= { msvmDiskDriveEntry 48 }

msvmddSystemName OBJECT-TYPE
    SYNTAX     WtcsDisplayString (SIZE (0..256))
    MAX-ACCESS read-only
    STATUS     current
    DESCRIPTION
        "The System Name of the scoping system."
    ::= { msvmDiskDriveEntry 49 }

msvmddTimeOfLastMount OBJECT-TYPE
    SYNTAX     DateAndTime
    MAX-ACCESS read-only
    STATUS     current
    DESCRIPTION
        "For a MediaAccessDevice that supports removable
        Media, the most recent date and time that Media was
        mounted on the Device. For Devices accessing
        nonremovable Media, such as hard disks, this
        property has no meaning and is not applicable."
    ::= { msvmDiskDriveEntry 50 }

msvmddTimeOfLastStateChange OBJECT-TYPE
    SYNTAX     DateAndTime
    MAX-ACCESS read-only
    STATUS     current
    DESCRIPTION
        "The date or time when the EnabledState of the
        element last changed. If the state of the element
        has not changed and this property is populated,
        then it must be set to a 0 interval value. If a
        state change was requested, but rejected or not yet
        processed, the property must not be updated."
    ::= { msvmDiskDriveEntry 51 }

msvmddTotalMountTime OBJECT-TYPE
    SYNTAX     Gauge32
    MAX-ACCESS read-only
    STATUS     current
    DESCRIPTION
        "For a MediaAccessDevice that supports removable
        Media, the total time (in seconds) that Media have
        been mounted for data transfer or to clean the
        Device. For Devices accessing nonremovable Media,
        such as hard disks, this property is not applicable
        and should be set to 0."
    ::= { msvmDiskDriveEntry 52 }

msvmddTotalPowerOnHours OBJECT-TYPE
    SYNTAX     Gauge32
    UNITS "Hours"
    MAX-ACCESS read-only
    STATUS     current
    DESCRIPTION
        "Note: The use of this method is deprecated. 
        Deprecated description: The total number of hours
        that this Device has been powered on."
    ::= { msvmDiskDriveEntry 53 }

msvmddUncompressedDataRate OBJECT-TYPE
    SYNTAX     Gauge32
    UNITS "KiloBytes per Second"
    MAX-ACCESS read-only
    STATUS     current
    DESCRIPTION
        "The sustained data transfer rate in KB/sec that
        the Device can read from and write to a Media. This
        is a sustained, raw data rate. Maximum rates or
        rates assuming compression should not be reported
        in this property."
    ::= { msvmDiskDriveEntry 54 }

msvmddUnitsDescription OBJECT-TYPE
    SYNTAX     WtcsDisplayString
    MAX-ACCESS read-only
    STATUS     current
    DESCRIPTION
        "Defines 'Units' relative to its use in the
        property, MaxUnitsBeforeCleaning. This describes
        the criteria used to determine when the
        MediaAccessDevice should be cleaned."
    ::= { msvmDiskDriveEntry 55 }

msvmddUnitsUsed OBJECT-TYPE
    SYNTAX     Gauge32
    MAX-ACCESS read-only
    STATUS     current
    DESCRIPTION
        "An unsigned integer indicating the currently used
        'units' of the AccessDevice, helpful to describe
        when the Device may require cleaning. The property,
        UnitsDescription, defines how 'units' should be
        interpreted."
    ::= { msvmDiskDriveEntry 56 }

msvmddUnloadTime OBJECT-TYPE
    SYNTAX     Gauge32
    UNITS "MilliSeconds"
    MAX-ACCESS read-only
    STATUS     current
    DESCRIPTION
        "Time in milliseconds from being able to read or
        write a Media to its 'unload'. For example, for
        DiskDrives, this is the interval between a disk
        spinning at nominal speeds and a disk not spinning.
        For TapeDrives, this is the time for a Media to go
        from its BOT to being fully ejected and accessible
        to a PickerElement or human operator."
    ::= { msvmDiskDriveEntry 57 }

msvmDisketteControllerTable OBJECT-TYPE
    SYNTAX     SEQUENCE OF MsvmDisketteController
    MAX-ACCESS not-accessible
    STATUS     current
    DESCRIPTION
        "Represents the floppy controller in the virtual
        machine."
    ::= { msvmStorage 3 }

msvmDisketteControllerEntry OBJECT-TYPE
    SYNTAX     MsvmDisketteController
    MAX-ACCESS not-accessible
    STATUS     current
    DESCRIPTION
        "None"
    INDEX      { msvmdcIndex }
    ::= { msvmDisketteControllerTable 1 }

MsvmDisketteController ::= SEQUENCE {
    msvmdcIndex Integer32,
    msvmdcAdditionalAvailability INTEGER,
    msvmdcAvailability INTEGER,
    msvmdcCaption WtcsDisplayString,
    msvmdcCreationClassName WtcsDisplayString,
    msvmdcDescription WtcsDisplayString,
    msvmdcDeviceID WtcsDisplayString,
    msvmdcElementName WtcsDisplayString,
    msvmdcEnabledDefault INTEGER,
    msvmdcEnabledState INTEGER,
    msvmdcErrorCleared TruthValue,
    msvmdcErrorDescription WtcsDisplayString,
    msvmdcHealthState INTEGER,
    msvmdcIdentifyingDescriptions WtcsDisplayString,
    msvmdcInstallDate DateAndTime,
    msvmdcLastErrorCode Gauge32,
    msvmdcLocationIndicator INTEGER,
    msvmdcMaxNumberControlled Gauge32,
    msvmdcMaxQuiesceTime Gauge32,
    msvmdcName WtcsDisplayString,
    msvmdcOperationalStatus INTEGER,
    msvmdcOtherEnabledState WtcsDisplayString,
    msvmdcOtherIdentifyingInfo WtcsDisplayString,
    msvmdcPowerManagementCapability INTEGER,
    msvmdcPowerManagementSupported TruthValue,
    msvmdcPowerOnHours Gauge32,
    msvmdcProtocolDescription WtcsDisplayString,
    msvmdcProtocolSupported Integer32,
    msvmdcRequestedState INTEGER,
    msvmdcStatus WtcsDisplayString,
    msvmdcStatusDescriptions WtcsDisplayString,
    msvmdcStatusInfo INTEGER,
    msvmdcSystemCreationClassName WtcsDisplayString,
    msvmdcSystemName WtcsDisplayString,
    msvmdcTimeOfLastReset DateAndTime,
    msvmdcTimeOfLastStateChange DateAndTime,
    msvmdcTotalPowerOnHours Gauge32
}

msvmdcIndex OBJECT-TYPE
    SYNTAX     Integer32 (1..2147483647)
    MAX-ACCESS read-only
    STATUS     current
    DESCRIPTION
        "The value of this object uniquely identifies the
        instance entry for this class."
    ::= { msvmDisketteControllerEntry 1 }

msvmdcAdditionalAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Additional availability and status of the Device
        in addition to that specified in the Availability
        property. The Availability property denotes the
        primary status and availability of the Device. In
        some cases, this property will not be sufficient to
        denote the complete status of the Device. In those
        cases, the AdditionalAvailability property can be
        used to provide further information. For example,
        the primary Availability of a device might be 'Off
        line' (value=8) or in a low-power state
        (AdditionalAvailability value=14), or the Device
        could be running Diagnostics
        (AdditionalAvailability value=5, 'In Test')."
    ::= { msvmDisketteControllerEntry 2 }

msvmdcAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Note: The use of this property has been
        deprecated. 
        Deprecated description: The primary availability
        and status of the Device. (Additional status
        information can be specified using the Additional
        Availability array property.) For example, the
        Availability property indicates that the Device is
        running and has full power (value=3), or is in a
        warning (4), test (5), degraded (10) or power save
        state (values 13-15 and 17). The Power Save states
        are defined as follows: Value 13 ('Power Save -
        Unknown') indicates that the Device is known to be
        in a power save mode, but its exact status in this
        mode is unknown; value 14 ('Power Save - Low Power
        Mode') indicates that the Device is in a power save
        state but still functioning, and might exhibit
        degraded performance; value 15 ('Power Save -
        Standby') indicates that the Device is not
        functioning but could be brought to full power
        'quickly'; and value 17 ('Power Save - Warning')
        indicates that the Device is in a warning state,
        but is also in a power save mode."
    ::= { msvmDisketteControllerEntry 3 }

msvmdcCaption OBJECT-TYPE
    SYNTAX     WtcsDisplayString (SIZE (0..64))
    MAX-ACCESS read-only
    STATUS     current
    DESCRIPTION
        "The Caption property is a short textual
        description (one- line string) of the object."
    ::= { msvmDisketteControllerEntry 4 }

msvmdcCreationClassName OBJECT-TYPE
    SYNTAX     WtcsDisplayString (SIZE (0..256))
    MAX-ACCESS read-only
    STATUS     current
    DESCRIPTION
        "CreationClassName indicates the name of the class
        or the subclass used in the creation of an
        instance. When used with the other key properties
        of this class, this property allows all instances
        of this class and its subclasses to be uniquely
        identified."
    ::= { msvmDisketteControllerEntry 5 }

msvmdcDescription OBJECT-TYPE
    SYNTAX     WtcsDisplayString
    MAX-ACCESS read-only
    STATUS     current
    DESCRIPTION
        "The Description property provides a textual
        description of the object."
    ::= { msvmDisketteControllerEntry 6 }

msvmdcDeviceID OBJECT-TYPE
    SYNTAX     WtcsDisplayString (SIZE (0..64))
    MAX-ACCESS read-only
    STATUS     current
    DESCRIPTION
        "An address or other identifying information used
        to uniquely name the LogicalDevice."
    ::= { msvmDisketteControllerEntry 7 }

msvmdcElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmDisketteControllerEntry 8 }

msvmdcEnabledDefault OBJECT-TYPE
    SYNTAX     INTEGER {
        enabled(2),
        disabled(3),
        notApplicable(5),
        enabledbutOffline(6),
        noDefault(7)
    }
    MAX-ACCESS read-only
    STATUS     current
    DESCRIPTION
        "An enumerated value indicating an administrator's
        default or startup configuration for the Enabled
        State of an element. By default, the element is
        'Enabled' (value=2)."
    ::= { msvmDisketteControllerEntry 9 }

msvmdcEnabledState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "EnabledState is an integer enumeration that
        indicates the enabled and disabled states of an
        element. It can also indicate the transitions
        between these requested states. For example,
        shutting down (value=4) and starting (value=10) are
        transient states between enabled and disabled. The
        following text briefly summarizes the various
        enabled and disabled states: 
        Enabled (2) indicates that the element is or could
        be executing commands, will process any queued
        commands, and queues new requests. 
        Disabled (3) indicates that the element will not
        execute commands and will drop any new requests. 
        Shutting Down (4) indicates that the element is in
        the process of going to a Disabled state. 
        Not Applicable (5) indicates the element does not
        support being enabled or disabled. 
        Enabled but Offline (6) indicates that the element
        might be completing commands, and will drop any new
        requests. 
        Test (7) indicates that the element is in a test
        state. 
        Deferred (8) indicates that the element might be
        completing commands, but will queue any new
        requests. 
        Quiesce (9) indicates that the element is enabled
        but in a restricted mode. The behavior of the
        element is similar to the Enabled state, but it
        processes only a restricted set of commands. All
        other requests are queued. 
        Starting (10) indicates that the element is in the
        process of going to an Enabled state. New requests
        are queued."
    ::= { msvmDisketteControllerEntry 10 }

msvmdcErrorCleared OBJECT-TYPE
    SYNTAX     TruthValue
    MAX-ACCESS read-only
    STATUS     current
    DESCRIPTION
        "Note: The use of this method is deprecated. 
        Deprecated description: ErrorCleared is a Boolean
        property that indicates that the error reported in
        LastErrorCode is now cleared."
    ::= { msvmDisketteControllerEntry 11 }

msvmdcErrorDescription OBJECT-TYPE
    SYNTAX     WtcsDisplayString
    MAX-ACCESS read-only
    STATUS     current
    DESCRIPTION
        "Note: The use of this method is deprecated. 
        Deprecated description: ErrorDescription is a
        free-form string that supplies more information
        about the error recorded in LastErrorCode and
        information on any corrective actions that can be
        taken."
    ::= { msvmDisketteControllerEntry 12 }

msvmdcHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmDisketteControllerEntry 13 }

msvmdcIdentifyingDescriptions OBJECT-TYPE
    SYNTAX     WtcsDisplayString
    MAX-ACCESS read-only
    STATUS     current
    DESCRIPTION
        "An array of free-form strings providing
        explanations and details behind the entries in the
        OtherIdentifyingInfo array. Note that each entry of
        this array is related to the entry in
        OtherIdentifyingInfo that is located at the same
        index."
    ::= { msvmDisketteControllerEntry 14 }

msvmdcInstallDate OBJECT-TYPE
    SYNTAX     DateAndTime
    MAX-ACCESS read-only
    STATUS     current
    DESCRIPTION
        "A datetime value that indicates when the object
        was installed. Lack of a value does not indicate
        that the object is not installed."
    ::= { msvmDisketteControllerEntry 15 }

msvmdcLastErrorCode OBJECT-TYPE
    SYNTAX     Gauge32
    MAX-ACCESS read-only
    STATUS     current
    DESCRIPTION
        "Note: The use of this method is deprecated. 
        Deprecated description: LastErrorCode captures the
        last error code reported by the LogicalDevice."
    ::= { msvmDisketteControllerEntry 16 }

msvmdcLocationIndicator OBJECT-TYPE
    SYNTAX     INTEGER {
        unknown(0),
        on(2),
        off(3),
        notSupported(4)
    }
    MAX-ACCESS read-only
    STATUS     current
    DESCRIPTION
        "An integer that reflects the state of an indicator
        (e.g., LED) that is part of a device. Reading the
        value gives the current state. Writing the value
        with 'On'/'Off' turns the indicator on/off, other
        values may not be written."
    ::= { msvmDisketteControllerEntry 17 }

msvmdcMaxNumberControlled OBJECT-TYPE
    SYNTAX     Gauge32
    MAX-ACCESS read-only
    STATUS     current
    DESCRIPTION
        "Maximum number of directly addressable entities
        that are supported by this Controller. A value of 0
        should be used if the number is unknown or
        unlimited."
    ::= { msvmDisketteControllerEntry 18 }

msvmdcMaxQuiesceTime OBJECT-TYPE
    SYNTAX     Gauge32
    UNITS "MilliSeconds"
    MAX-ACCESS read-only
    STATUS     current
    DESCRIPTION
        "Note: The use of this property has been
        deprecated. When evaluating the use of Quiesce, it
        was determined that this single property is not
        adequate for describing when a device will
        automatically exit a quiescent state. In fact, the
        most likely scenario for a device to exit a
        quiescent state was determined to be based on the
        number of outstanding requests queued rather than
        on a maximum time. This decision will be
        re-evaluated and repositioned later. 
        Deprecated description: Maximum time, in
        milliseconds, that a Device can run in a 'Quiesced'
        state. The state is defined in its Availability and
        AdditionalAvailability properties, where 'Quiesced'
        is conveyed by the value 21. What occurs at the end
        of the time limit is device-specific. The Device
        can unquiesce, can be offline, or can take other
        actions. A value of 0 indicates that a Device can
        remain quiesced indefinitely."
    ::= { msvmDisketteControllerEntry 19 }

msvmdcName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmDisketteControllerEntry 20 }

msvmdcOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmDisketteControllerEntry 21 }

msvmdcOtherEnabledState OBJECT-TYPE
    SYNTAX     WtcsDisplayString
    MAX-ACCESS read-only
    STATUS     current
    DESCRIPTION
        "A string that describes the enabled or disabled
        state of the element when the EnabledState property
        is set to 1 ('Other'). This property must be set to
        null when EnabledState is any value other than 1."
    ::= { msvmDisketteControllerEntry 22 }

msvmdcOtherIdentifyingInfo OBJECT-TYPE
    SYNTAX     WtcsDisplayString (SIZE (0..256))
    MAX-ACCESS read-only
    STATUS     current
    DESCRIPTION
        "OtherIdentifyingInfo captures data, in addition to
        DeviceID information, that could be used to
        identify a LogicalDevice. For example, you could
        use this property to hold the operating system's
        user-friendly name for the Device."
    ::= { msvmDisketteControllerEntry 23 }

msvmdcPowerManagementCapability OBJECT-TYPE
    SYNTAX     INTEGER {
        unknown(0),
        notSupported(1),
        disabled(2),
        enabled(3),
        powerSavingModesEnteredAutomatic(4),
        powerStateSettable(5),
        powerCyclingSupported(6),
        timedPowerOnSupported(7)
    }
    MAX-ACCESS read-only
    STATUS     current
    DESCRIPTION
        "Note: The use of this property has been
        deprecated. Instead, use the PowerCapabilites
        property in an associated
        PowerManagementCapabilities class. Deprecated
        description: An enumerated array describing the
        power management capabilities of the Device."
    ::= { msvmDisketteControllerEntry 24 }

msvmdcPowerManagementSupported OBJECT-TYPE
    SYNTAX     TruthValue
    MAX-ACCESS read-only
    STATUS     current
    DESCRIPTION
        "Note: The use of this property has been
        deprecated. Instead, the existence of an associated
        PowerManagementCapabilities class (associated using
        the ElementCapabilities relationship) indicates
        that power management is supported. Deprecated
        description: Boolean that indicates that the Device
        can use power management."
    ::= { msvmDisketteControllerEntry 25 }

msvmdcPowerOnHours OBJECT-TYPE
    SYNTAX     Gauge32
    UNITS "Hours"
    MAX-ACCESS read-only
    STATUS     current
    DESCRIPTION
        "Note: The use of this method is deprecated. 
        Deprecated description: The number of consecutive
        hours that this Device has been powered on since
        its last power cycle."
    ::= { msvmDisketteControllerEntry 26 }

msvmdcProtocolDescription OBJECT-TYPE
    SYNTAX     WtcsDisplayString
    MAX-ACCESS read-only
    STATUS     current
    DESCRIPTION
        "A free-form string that provides more information
        that is related to the ProtocolSupported by the
        Controller."
    ::= { msvmDisketteControllerEntry 27 }

msvmdcProtocolSupported OBJECT-TYPE
    SYNTAX     Integer32
    MAX-ACCESS read-only
    STATUS     current
    DESCRIPTION
        "The protocol used by the Controller to access
        controlled Devices."
    ::= { msvmDisketteControllerEntry 28 }

msvmdcRequestedState OBJECT-TYPE
    SYNTAX     INTEGER {
        enabled(2),
        disabled(3),
        shutDown(4),
        noChange(5),
        offline(6),
        test(7),
        deferred(8),
        quiesce(9),
        reboot(10),
        reset(11),
        notApplicable(12)
    }
    MAX-ACCESS read-only
    STATUS     current
    DESCRIPTION
        "RequestedState is an integer enumeration that
        indicates the last requested or desired state for
        the element. The actual state of the element is
        represented by EnabledState. This property is
        provided to compare the last requested and current
        enabled or disabled states. Note that when
        EnabledState is set to 5 ('Not Applicable'), then
        this property has no meaning. By default, the
        RequestedState of the element is 5 ('No Change').
        Refer to the EnabledState property description for
        explanations of the values in the RequestedState
        enumeration. 
        
        It should be noted that there are two new values in
        RequestedState that build on the statuses of
        EnabledState. These are 'Reboot' (10) and 'Reset'
        (11). Reboot refers to doing a 'Shut Down' and then
        moving to an 'Enabled' state. Reset indicates that
        the element is first 'Disabled' and then 'Enabled'.
        The distinction between requesting 'Shut Down' and
        'Disabled' should also be noted. Shut Down requests
        an orderly transition to the Disabled state, and
        might involve removing power, to completely erase
        any existing state. The Disabled state requests an
        immediate disabling of the element, such that it
        will not execute or accept any commands or
        processing requests. 
        
        This property is set as the result of a method
        invocation (such as Start or StopService on
        CIM_Service), or can be overridden and defined as
        WRITEable in a subclass. The method approach is
        considered superior to a WRITEable property,
        because it allows an explicit invocation of the
        operation and the return of a result code. 
        
        A particular instance of EnabledLogicalElement
        might not support RequestedStateChange. If this
        occurs, the value 12 ('Not Applicable') is used."
    ::= { msvmDisketteControllerEntry 29 }

msvmdcStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmDisketteControllerEntry 30 }

msvmdcStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmDisketteControllerEntry 31 }

msvmdcStatusInfo OBJECT-TYPE
    SYNTAX     INTEGER {
        other(1),
        unknown(2),
        enabled(3),
        disabled(4),
        notApplicable(5)
    }
    MAX-ACCESS read-only
    STATUS     current
    DESCRIPTION
        "Note: The use of this method is deprecated in lieu
        of a more clearly named property (EnabledState)
        that is inherited from ManagedSystemElement and
        that has additional enumerated values. 
        Deprecated description: The StatusInfo property
        indicates whether the Logical Device is in an
        enabled state (value=3), disabled state (value=4),
        some other state (value=1), or an unknown state
        (value=2). If this property does not apply to the
        LogicalDevice, the value 5 ('Not Applicable')
        should be used. If a Device is
        ('Enabled')(value=3), it has been powered up and is
        configured and operational. The Device might or
        might not be functionally active, depending on
        whether its Availability (or
        AdditionalAvailability) indicates that it is
        ('Running/Full Power')(value=3) or ('Off line')
        (value=8). In an enabled but offline mode, a Device
        might be performing out-of-band requests, such as
        running Diagnostics. If StatusInfo is ('Disabled')
        (value=4), a Device can only be 'enabled' or
        powered off. In a personal computer environment,
        ('Disabled') means that the driver of the device is
        not available in the stack. In other environments,
        a Device can be disabled by removing its
        configuration file. A disabled device is physically
        present in a System and consuming resources, but it
        cannot be communicated with until a driver is
        loaded, a configuration file is loaded, or some
        other 'enabling' activity has occurred."
    ::= { msvmDisketteControllerEntry 32 }

msvmdcSystemCreationClassName OBJECT-TYPE
    SYNTAX     WtcsDisplayString (SIZE (0..256))
    MAX-ACCESS read-only
    STATUS     current
    DESCRIPTION
        "The CreationClassName of the scoping system."
    ::= { msvmDisketteControllerEntry 33 }

msvmdcSystemName OBJECT-TYPE
    SYNTAX     WtcsDisplayString (SIZE (0..256))
    MAX-ACCESS read-only
    STATUS     current
    DESCRIPTION
        "The System Name of the scoping system."
    ::= { msvmDisketteControllerEntry 34 }

msvmdcTimeOfLastReset OBJECT-TYPE
    SYNTAX     DateAndTime
    MAX-ACCESS read-only
    STATUS     current
    DESCRIPTION
        "Time of last reset of the Controller."
    ::= { msvmDisketteControllerEntry 35 }

msvmdcTimeOfLastStateChange OBJECT-TYPE
    SYNTAX     DateAndTime
    MAX-ACCESS read-only
    STATUS     current
    DESCRIPTION
        "The date or time when the EnabledState of the
        element last changed. If the state of the element
        has not changed and this property is populated,
        then it must be set to a 0 interval value. If a
        state change was requested, but rejected or not yet
        processed, the property must not be updated."
    ::= { msvmDisketteControllerEntry 36 }

msvmdcTotalPowerOnHours OBJECT-TYPE
    SYNTAX     Gauge32
    UNITS "Hours"
    MAX-ACCESS read-only
    STATUS     current
    DESCRIPTION
        "Note: The use of this method is deprecated. 
        Deprecated description: The total number of hours
        that this Device has been powered on."
    ::= { msvmDisketteControllerEntry 37 }

msvmDisketteDriveTable OBJECT-TYPE
    SYNTAX     SEQUENCE OF MsvmDisketteDrive
    MAX-ACCESS not-accessible
    STATUS     current
    DESCRIPTION
        "Represents a floppy drive inside the virtual
        machine."
    ::= { msvmStorage 4 }

msvmDisketteDriveEntry OBJECT-TYPE
    SYNTAX     MsvmDisketteDrive
    MAX-ACCESS not-accessible
    STATUS     current
    DESCRIPTION
        "None"
    INDEX      { msvmdskdvIndex }
    ::= { msvmDisketteDriveTable 1 }

MsvmDisketteDrive ::= SEQUENCE {
    msvmdskdvIndex Integer32,
    msvmdskdvAdditionalAvailability INTEGER,
    msvmdskdvAvailability INTEGER,
    msvmdskdvCapabilities INTEGER,
    msvmdskdvCapabilityDescriptions WtcsDisplayString,
    msvmdskdvCaption WtcsDisplayString,
    msvmdskdvCompressionMethod WtcsDisplayString,
    msvmdskdvCreationClassName WtcsDisplayString,
    msvmdskdvDefaultBlockSize Gauge32,
    msvmdskdvDescription WtcsDisplayString,
    msvmdskdvDeviceID WtcsDisplayString,
    msvmdskdvElementName WtcsDisplayString,
    msvmdskdvEnabledDefault INTEGER,
    msvmdskdvEnabledState INTEGER,
    msvmdskdvErrorCleared TruthValue,
    msvmdskdvErrorDescription WtcsDisplayString,
    msvmdskdvErrorMethodology WtcsDisplayString,
    msvmdskdvHealthState INTEGER,
    msvmdskdvIdentifyingDescriptions WtcsDisplayString,
    msvmdskdvInstallDate DateAndTime,
    msvmdskdvLastCleaned DateAndTime,
    msvmdskdvLastErrorCode Gauge32,
    msvmdskdvLoadTime Gauge32,
    msvmdskdvLocationIndicator INTEGER,
    msvmdskdvMaxAccessTime Gauge32,
    msvmdskdvMaxBlockSize Gauge32,
    msvmdskdvMaxMediaSize Gauge32,
    msvmdskdvMaxQuiesceTime Gauge32,
    msvmdskdvMaxUnitsBeforeCleaning Gauge32,
    msvmdskdvMediaIsLocked TruthValue,
    msvmdskdvMinBlockSize Gauge32,
    msvmdskdvMountCount Gauge32,
    msvmdskdvName WtcsDisplayString,
    msvmdskdvNeedsCleaning TruthValue,
    msvmdskdvNumberOfMediaSupported Gauge32,
    msvmdskdvOperationalStatus INTEGER,
    msvmdskdvOtherEnabledState WtcsDisplayString,
    msvmdskdvOtherIdentifyingInfo WtcsDisplayString,
    msvmdskdvPowerMgtCapability INTEGER,
    msvmdskdvPowerManagementSupport TruthValue,
    msvmdskdvPowerOnHours Gauge32,
    msvmdskdvRequestedState INTEGER,
    msvmdskdvSecurity INTEGER,
    msvmdskdvStatus WtcsDisplayString,
    msvmdskdvStatusDescriptions WtcsDisplayString,
    msvmdskdvStatusInfo INTEGER,
    msvmdskdvSystemCreationClassName WtcsDisplayString,
    msvmdskdvSystemName WtcsDisplayString,
    msvmdskdvTimeOfLastMount DateAndTime,
    msvmdskdvTimeOfLastStateChange DateAndTime,
    msvmdskdvTotalMountTime Gauge32,
    msvmdskdvTotalPowerOnHours Gauge32,
    msvmdskdvUncompressedDataRate Gauge32,
    msvmdskdvUnitsDescription WtcsDisplayString,
    msvmdskdvUnitsUsed Gauge32,
    msvmdskdvUnloadTime Gauge32
}

msvmdskdvIndex OBJECT-TYPE
    SYNTAX     Integer32 (1..2147483647)
    MAX-ACCESS read-only
    STATUS     current
    DESCRIPTION
        "The value of this object uniquely identifies the
        instance entry for this class."
    ::= { msvmDisketteDriveEntry 1 }

msvmdskdvAdditionalAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Additional availability and status of the Device
        in addition to that specified in the Availability
        property. The Availability property denotes the
        primary status and availability of the Device. In
        some cases, this property will not be sufficient to
        denote the complete status of the Device. In those
        cases, the AdditionalAvailability property can be
        used to provide further information. For example,
        the primary Availability of a device might be 'Off
        line' (value=8) or in a low-power state
        (AdditionalAvailability value=14), or the Device
        could be running Diagnostics
        (AdditionalAvailability value=5, 'In Test')."
    ::= { msvmDisketteDriveEntry 2 }

msvmdskdvAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Note: The use of this property has been
        deprecated. 
        Deprecated description: The primary availability
        and status of the Device. (Additional status
        information can be specified using the Additional
        Availability array property.) For example, the
        Availability property indicates that the Device is
        running and has full power (value=3), or is in a
        warning (4), test (5), degraded (10) or power save
        state (values 13-15 and 17). The Power Save states
        are defined as follows: Value 13 ('Power Save -
        Unknown') indicates that the Device is known to be
        in a power save mode, but its exact status in this
        mode is unknown; value 14 ('Power Save - Low Power
        Mode') indicates that the Device is in a power save
        state but still functioning, and might exhibit
        degraded performance; value 15 ('Power Save -
        Standby') indicates that the Device is not
        functioning but could be brought to full power
        'quickly'; and value 17 ('Power Save - Warning')
        indicates that the Device is in a warning state,
        but is also in a power save mode."
    ::= { msvmDisketteDriveEntry 3 }

msvmdskdvCapabilities OBJECT-TYPE
    SYNTAX     INTEGER {
        unknown(0),
        other(1),
        sequentialAccess(2),
        randomAccess(3),
        supportsWriting(4),
        encryption(5),
        compression(6),
        supportsRemoveableMedia(7),
        manualCleaning(8),
        automaticCleaning(9),
        smartNotification(10),
        supportsDualSidedMedia(11),
        predismountEjectNotRequired(12)
    }
    MAX-ACCESS read-only
    STATUS     current
    DESCRIPTION
        "Capabilities of the MediaAccessDevice. For
        example, the Device may support 'Random Access',
        removeable media and 'Automatic Cleaning'. In this
        case, the values 3, 7 and 9 would be written to the
        array. 
        Several of the enumerated values require some
        explanation: 1) Value 11, Supports Dual Sided
        Media, distinguishes a Device that can access both
        sides of dual sided Media, from a Device that reads
        only a single side and requires the Media to be
        flipped; and, 2) Value 12, Predismount Eject Not
        Required, indicates that Media does not have to be
        explicitly ejected from the Device before being
        accessed by a PickerElement."
    ::= { msvmDisketteDriveEntry 4 }

msvmdskdvCapabilityDescriptions OBJECT-TYPE
    SYNTAX     WtcsDisplayString
    MAX-ACCESS read-only
    STATUS     current
    DESCRIPTION
        "An array of free-form strings providing more
        detailed explanations for any of the AccessDevice
        features indicated in the Capabilities array. Note,
        each entry of this array is related to the entry in
        the Capabilities array that is located at the same
        index."
    ::= { msvmDisketteDriveEntry 5 }

msvmdskdvCaption OBJECT-TYPE
    SYNTAX     WtcsDisplayString (SIZE (0..64))
    MAX-ACCESS read-only
    STATUS     current
    DESCRIPTION
        "The Caption property is a short textual
        description (one- line string) of the object."
    ::= { msvmDisketteDriveEntry 6 }

msvmdskdvCompressionMethod OBJECT-TYPE
    SYNTAX     WtcsDisplayString
    MAX-ACCESS read-only
    STATUS     current
    DESCRIPTION
        "A free form string indicating the algorithm or
        tool used by the device to support compression. If
        it is not possible or not desired to describe the
        compression scheme (perhaps because it is not
        known), recommend using the following words:
        'Unknown' to represent that it is not known whether
        the device supports compression capabilities or
        not, 'Compressed' to represent that the device
        supports compression capabilities but either its
        compression scheme is not known or not disclosed,
        and 'Not Compressed' to represent that the devices
        does not support compression capabilities."
    ::= { msvmDisketteDriveEntry 7 }

msvmdskdvCreationClassName OBJECT-TYPE
    SYNTAX     WtcsDisplayString (SIZE (0..256))
    MAX-ACCESS read-only
    STATUS     current
    DESCRIPTION
        "CreationClassName indicates the name of the class
        or the subclass used in the creation of an
        instance. When used with the other key properties
        of this class, this property allows all instances
        of this class and its subclasses to be uniquely
        identified."
    ::= { msvmDisketteDriveEntry 8 }

msvmdskdvDefaultBlockSize OBJECT-TYPE
    SYNTAX     Gauge32
    UNITS "Bytes"
    MAX-ACCESS read-only
    STATUS     current
    DESCRIPTION
        "Default block size, in bytes, for this Device."
    ::= { msvmDisketteDriveEntry 9 }

msvmdskdvDescription OBJECT-TYPE
    SYNTAX     WtcsDisplayString
    MAX-ACCESS read-only
    STATUS     current
    DESCRIPTION
        "The Description property provides a textual
        description of the object."
    ::= { msvmDisketteDriveEntry 10 }

msvmdskdvDeviceID OBJECT-TYPE
    SYNTAX     WtcsDisplayString (SIZE (0..64))
    MAX-ACCESS read-only
    STATUS     current
    DESCRIPTION
        "An address or other identifying information used
        to uniquely name the LogicalDevice."
    ::= { msvmDisketteDriveEntry 11 }

msvmdskdvElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmDisketteDriveEntry 12 }

msvmdskdvEnabledDefault OBJECT-TYPE
    SYNTAX     INTEGER {
        enabled(2),
        disabled(3),
        notApplicable(5),
        enabledbutOffline(6),
        noDefault(7)
    }
    MAX-ACCESS read-only
    STATUS     current
    DESCRIPTION
        "An enumerated value indicating an administrator's
        default or startup configuration for the Enabled
        State of an element. By default, the element is
        'Enabled' (value=2)."
    ::= { msvmDisketteDriveEntry 13 }

msvmdskdvEnabledState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "EnabledState is an integer enumeration that
        indicates the enabled and disabled states of an
        element. It can also indicate the transitions
        between these requested states. For example,
        shutting down (value=4) and starting (value=10) are
        transient states between enabled and disabled. The
        following text briefly summarizes the various
        enabled and disabled states: 
        Enabled (2) indicates that the element is or could
        be executing commands, will process any queued
        commands, and queues new requests. 
        Disabled (3) indicates that the element will not
        execute commands and will drop any new requests. 
        Shutting Down (4) indicates that the element is in
        the process of going to a Disabled state. 
        Not Applicable (5) indicates the element does not
        support being enabled or disabled. 
        Enabled but Offline (6) indicates that the element
        might be completing commands, and will drop any new
        requests. 
        Test (7) indicates that the element is in a test
        state. 
        Deferred (8) indicates that the element might be
        completing commands, but will queue any new
        requests. 
        Quiesce (9) indicates that the element is enabled
        but in a restricted mode. The behavior of the
        element is similar to the Enabled state, but it
        processes only a restricted set of commands. All
        other requests are queued. 
        Starting (10) indicates that the element is in the
        process of going to an Enabled state. New requests
        are queued."
    ::= { msvmDisketteDriveEntry 14 }

msvmdskdvErrorCleared OBJECT-TYPE
    SYNTAX     TruthValue
    MAX-ACCESS read-only
    STATUS     current
    DESCRIPTION
        "Note: The use of this method is deprecated. 
        Deprecated description: ErrorCleared is a Boolean
        property that indicates that the error reported in
        LastErrorCode is now cleared."
    ::= { msvmDisketteDriveEntry 15 }

msvmdskdvErrorDescription OBJECT-TYPE
    SYNTAX     WtcsDisplayString
    MAX-ACCESS read-only
    STATUS     current
    DESCRIPTION
        "Note: The use of this method is deprecated. 
        Deprecated description: ErrorDescription is a
        free-form string that supplies more information
        about the error recorded in LastErrorCode and
        information on any corrective actions that can be
        taken."
    ::= { msvmDisketteDriveEntry 16 }

msvmdskdvErrorMethodology OBJECT-TYPE
    SYNTAX     WtcsDisplayString
    MAX-ACCESS read-only
    STATUS     current
    DESCRIPTION
        "ErrorMethodology is a free-form string describing
        the type(s) of error detection and correction
        supported by this Device."
    ::= { msvmDisketteDriveEntry 17 }

msvmdskdvHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmDisketteDriveEntry 18 }

msvmdskdvIdentifyingDescriptions OBJECT-TYPE
    SYNTAX     WtcsDisplayString
    MAX-ACCESS read-only
    STATUS     current
    DESCRIPTION
        "An array of free-form strings providing
        explanations and details behind the entries in the
        OtherIdentifyingInfo array. Note that each entry of
        this array is related to the entry in
        OtherIdentifyingInfo that is located at the same
        index."
    ::= { msvmDisketteDriveEntry 19 }

msvmdskdvInstallDate OBJECT-TYPE
    SYNTAX     DateAndTime
    MAX-ACCESS read-only
    STATUS     current
    DESCRIPTION
        "A datetime value that indicates when the object
        was installed. Lack of a value does not indicate
        that the object is not installed."
    ::= { msvmDisketteDriveEntry 20 }

msvmdskdvLastCleaned OBJECT-TYPE
    SYNTAX     DateAndTime
    MAX-ACCESS read-only
    STATUS     current
    DESCRIPTION
        "The date and time on which the Device was last
        cleaned."
    ::= { msvmDisketteDriveEntry 21 }

msvmdskdvLastErrorCode OBJECT-TYPE
    SYNTAX     Gauge32
    MAX-ACCESS read-only
    STATUS     current
    DESCRIPTION
        "Note: The use of this method is deprecated. 
        Deprecated description: LastErrorCode captures the
        last error code reported by the LogicalDevice."
    ::= { msvmDisketteDriveEntry 22 }

msvmdskdvLoadTime OBJECT-TYPE
    SYNTAX     Gauge32
    UNITS "MilliSeconds"
    MAX-ACCESS read-only
    STATUS     current
    DESCRIPTION
        "Time in milliseconds from 'load' to being able to
        read or write a Media. For example, for DiskDrives,
        this is the interval between a disk not spinning to
        the disk reporting that it is ready for read/write
        (ie, the disk spinning at nominal speeds). For
        TapeDrives, this is the time from a Media being
        injected to reporting that it is ready for an
        application. This is usually at the tape's BOT
        area."
    ::= { msvmDisketteDriveEntry 23 }

msvmdskdvLocationIndicator OBJECT-TYPE
    SYNTAX     INTEGER {
        unknown(0),
        on(2),
        off(3),
        notSupported(4)
    }
    MAX-ACCESS read-only
    STATUS     current
    DESCRIPTION
        "An integer that reflects the state of an indicator
        (e.g., LED) that is part of a device. Reading the
        value gives the current state. Writing the value
        with 'On'/'Off' turns the indicator on/off, other
        values may not be written."
    ::= { msvmDisketteDriveEntry 24 }

msvmdskdvMaxAccessTime OBJECT-TYPE
    SYNTAX     Gauge32
    UNITS "MilliSeconds"
    MAX-ACCESS read-only
    STATUS     current
    DESCRIPTION
        "Time in milliseconds to move from the first
        location on the Media to the location that is
        furthest with respect to time. For a DiskDrive,
        this represents full seek + full rotational delay.
        For TapeDrives, this represents a search from the
        beginning of the tape to the most physically
        distant point. (The end of a tape may be at its
        most physically distant point, but this is not
        necessarily true.)"
    ::= { msvmDisketteDriveEntry 25 }

msvmdskdvMaxBlockSize OBJECT-TYPE
    SYNTAX     Gauge32
    UNITS "Bytes"
    MAX-ACCESS read-only
    STATUS     current
    DESCRIPTION
        "Maximum block size, in bytes, for media accessed
        by this Device."
    ::= { msvmDisketteDriveEntry 26 }

msvmdskdvMaxMediaSize OBJECT-TYPE
    SYNTAX     Gauge32
    MAX-ACCESS read-only
    STATUS     current
    DESCRIPTION
        "Maximum size, in KBytes, of media supported by
        this Device. KBytes is interpreted as the number of
        bytes multiplied by 1000 (NOT the number of bytes
        multiplied by 1024)."
    ::= { msvmDisketteDriveEntry 27 }

msvmdskdvMaxQuiesceTime OBJECT-TYPE
    SYNTAX     Gauge32
    UNITS "MilliSeconds"
    MAX-ACCESS read-only
    STATUS     current
    DESCRIPTION
        "Note: The use of this property has been
        deprecated. When evaluating the use of Quiesce, it
        was determined that this single property is not
        adequate for describing when a device will
        automatically exit a quiescent state. In fact, the
        most likely scenario for a device to exit a
        quiescent state was determined to be based on the
        number of outstanding requests queued rather than
        on a maximum time. This decision will be
        re-evaluated and repositioned later. 
        Deprecated description: Maximum time, in
        milliseconds, that a Device can run in a 'Quiesced'
        state. The state is defined in its Availability and
        AdditionalAvailability properties, where 'Quiesced'
        is conveyed by the value 21. What occurs at the end
        of the time limit is device-specific. The Device
        can unquiesce, can be offline, or can take other
        actions. A value of 0 indicates that a Device can
        remain quiesced indefinitely."
    ::= { msvmDisketteDriveEntry 28 }

msvmdskdvMaxUnitsBeforeCleaning OBJECT-TYPE
    SYNTAX     Gauge32
    MAX-ACCESS read-only
    STATUS     current
    DESCRIPTION
        "An unsigned integer indicating the maximum 'units'
        that can be used, with respect to the AccessDevice,
        before the Device should be cleaned. The property,
        UnitsDescription, defines how 'units' should be
        interpreted."
    ::= { msvmDisketteDriveEntry 29 }

msvmdskdvMediaIsLocked OBJECT-TYPE
    SYNTAX     TruthValue
    MAX-ACCESS read-only
    STATUS     current
    DESCRIPTION
        "True indicates that the media is locked in the
        Device and can not be ejected. For non-removeable
        Devices, this value should be true."
    ::= { msvmDisketteDriveEntry 30 }

msvmdskdvMinBlockSize OBJECT-TYPE
    SYNTAX     Gauge32
    UNITS "Bytes"
    MAX-ACCESS read-only
    STATUS     current
    DESCRIPTION
        "Minimum block size, in bytes, for media accessed
        by this Device."
    ::= { msvmDisketteDriveEntry 31 }

msvmdskdvMountCount OBJECT-TYPE
    SYNTAX     Gauge32
    MAX-ACCESS read-only
    STATUS     current
    DESCRIPTION
        "For a MediaAccessDevice that supports removable
        Media, the number of times that Media have been
        mounted for data transfer or to clean the Device.
        For Devices accessing nonremovable Media, such as
        hard disks, this property is not applicable and
        should be set to 0."
    ::= { msvmDisketteDriveEntry 32 }

msvmdskdvName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmDisketteDriveEntry 33 }

msvmdskdvNeedsCleaning OBJECT-TYPE
    SYNTAX     TruthValue
    MAX-ACCESS read-only
    STATUS     current
    DESCRIPTION
        "Boolean indicating that the MediaAccessDevice
        needs cleaning. Whether manual or automatic
        cleaning is possible is indicated in the
        Capabilities array property."
    ::= { msvmDisketteDriveEntry 34 }

msvmdskdvNumberOfMediaSupported OBJECT-TYPE
    SYNTAX     Gauge32
    MAX-ACCESS read-only
    STATUS     current
    DESCRIPTION
        "When the MediaAccessDevice supports multiple
        individual Media, this property defines the maximum
        number which can be supported or inserted."
    ::= { msvmDisketteDriveEntry 35 }

msvmdskdvOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmDisketteDriveEntry 36 }

msvmdskdvOtherEnabledState OBJECT-TYPE
    SYNTAX     WtcsDisplayString
    MAX-ACCESS read-only
    STATUS     current
    DESCRIPTION
        "A string that describes the enabled or disabled
        state of the element when the EnabledState property
        is set to 1 ('Other'). This property must be set to
        null when EnabledState is any value other than 1."
    ::= { msvmDisketteDriveEntry 37 }

msvmdskdvOtherIdentifyingInfo OBJECT-TYPE
    SYNTAX     WtcsDisplayString (SIZE (0..256))
    MAX-ACCESS read-only
    STATUS     current
    DESCRIPTION
        "OtherIdentifyingInfo captures data, in addition to
        DeviceID information, that could be used to
        identify a LogicalDevice. For example, you could
        use this property to hold the operating system's
        user-friendly name for the Device."
    ::= { msvmDisketteDriveEntry 38 }

msvmdskdvPowerMgtCapability OBJECT-TYPE
    SYNTAX     INTEGER {
        unknown(0),
        notSupported(1),
        disabled(2),
        enabled(3),
        powerSavingModesEnteredAutomatic(4),
        powerStateSettable(5),
        powerCyclingSupported(6),
        timedPowerOnSupported(7)
    }
    MAX-ACCESS read-only
    STATUS     current
    DESCRIPTION
        "Note: The use of this property has been
        deprecated. Instead, use the PowerCapabilites
        property in an associated
        PowerManagementCapabilities class. Deprecated
        description: An enumerated array describing the
        power management capabilities of the Device."
    ::= { msvmDisketteDriveEntry 39 }

msvmdskdvPowerManagementSupport OBJECT-TYPE
    SYNTAX     TruthValue
    MAX-ACCESS read-only
    STATUS     current
    DESCRIPTION
        "Note: The use of this property has been
        deprecated. Instead, the existence of an associated
        PowerManagementCapabilities class (associated using
        the ElementCapabilities relationship) indicates
        that power management is supported. Deprecated
        description: Boolean that indicates that the Device
        can use power management."
    ::= { msvmDisketteDriveEntry 40 }

msvmdskdvPowerOnHours OBJECT-TYPE
    SYNTAX     Gauge32
    UNITS "Hours"
    MAX-ACCESS read-only
    STATUS     current
    DESCRIPTION
        "Note: The use of this method is deprecated. 
        Deprecated description: The number of consecutive
        hours that this Device has been powered on since
        its last power cycle."
    ::= { msvmDisketteDriveEntry 41 }

msvmdskdvRequestedState OBJECT-TYPE
    SYNTAX     INTEGER {
        enabled(2),
        disabled(3),
        shutDown(4),
        noChange(5),
        offline(6),
        test(7),
        deferred(8),
        quiesce(9),
        reboot(10),
        reset(11),
        notApplicable(12)
    }
    MAX-ACCESS read-only
    STATUS     current
    DESCRIPTION
        "RequestedState is an integer enumeration that
        indicates the last requested or desired state for
        the element. The actual state of the element is
        represented by EnabledState. This property is
        provided to compare the last requested and current
        enabled or disabled states. Note that when
        EnabledState is set to 5 ('Not Applicable'), then
        this property has no meaning. By default, the
        RequestedState of the element is 5 ('No Change').
        Refer to the EnabledState property description for
        explanations of the values in the RequestedState
        enumeration. 
        
        It should be noted that there are two new values in
        RequestedState that build on the statuses of
        EnabledState. These are 'Reboot' (10) and 'Reset'
        (11). Reboot refers to doing a 'Shut Down' and then
        moving to an 'Enabled' state. Reset indicates that
        the element is first 'Disabled' and then 'Enabled'.
        The distinction between requesting 'Shut Down' and
        'Disabled' should also be noted. Shut Down requests
        an orderly transition to the Disabled state, and
        might involve removing power, to completely erase
        any existing state. The Disabled state requests an
        immediate disabling of the element, such that it
        will not execute or accept any commands or
        processing requests. 
        
        This property is set as the result of a method
        invocation (such as Start or StopService on
        CIM_Service), or can be overridden and defined as
        WRITEable in a subclass. The method approach is
        considered superior to a WRITEable property,
        because it allows an explicit invocation of the
        operation and the return of a result code. 
        
        A particular instance of EnabledLogicalElement
        might not support RequestedStateChange. If this
        occurs, the value 12 ('Not Applicable') is used."
    ::= { msvmDisketteDriveEntry 42 }

msvmdskdvSecurity OBJECT-TYPE
    SYNTAX     INTEGER {
        other(1),
        unknown(2),
        none(3),
        readOnly(4),
        lockedOut(5),
        bootBypass(6),
        bootBypassandReadOnly(7)
    }
    MAX-ACCESS read-only
    STATUS     current
    DESCRIPTION
        "An enumeration indicating the operational security
        defined for the MediaAccessDevice. For example,
        information that the Device is 'Read Only'
        (value=4) or 'Boot Bypass' (value=6) can be
        described using this property."
    ::= { msvmDisketteDriveEntry 43 }

msvmdskdvStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmDisketteDriveEntry 44 }

msvmdskdvStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmDisketteDriveEntry 45 }

msvmdskdvStatusInfo OBJECT-TYPE
    SYNTAX     INTEGER {
        other(1),
        unknown(2),
        enabled(3),
        disabled(4),
        notApplicable(5)
    }
    MAX-ACCESS read-only
    STATUS     current
    DESCRIPTION
        "Note: The use of this method is deprecated in lieu
        of a more clearly named property (EnabledState)
        that is inherited from ManagedSystemElement and
        that has additional enumerated values. 
        Deprecated description: The StatusInfo property
        indicates whether the Logical Device is in an
        enabled state (value=3), disabled state (value=4),
        some other state (value=1), or an unknown state
        (value=2). If this property does not apply to the
        LogicalDevice, the value 5 ('Not Applicable')
        should be used. If a Device is
        ('Enabled')(value=3), it has been powered up and is
        configured and operational. The Device might or
        might not be functionally active, depending on
        whether its Availability (or
        AdditionalAvailability) indicates that it is
        ('Running/Full Power')(value=3) or ('Off line')
        (value=8). In an enabled but offline mode, a Device
        might be performing out-of-band requests, such as
        running Diagnostics. If StatusInfo is ('Disabled')
        (value=4), a Device can only be 'enabled' or
        powered off. In a personal computer environment,
        ('Disabled') means that the driver of the device is
        not available in the stack. In other environments,
        a Device can be disabled by removing its
        configuration file. A disabled device is physically
        present in a System and consuming resources, but it
        cannot be communicated with until a driver is
        loaded, a configuration file is loaded, or some
        other 'enabling' activity has occurred."
    ::= { msvmDisketteDriveEntry 46 }

msvmdskdvSystemCreationClassName OBJECT-TYPE
    SYNTAX     WtcsDisplayString (SIZE (0..256))
    MAX-ACCESS read-only
    STATUS     current
    DESCRIPTION
        "The CreationClassName of the scoping system."
    ::= { msvmDisketteDriveEntry 47 }

msvmdskdvSystemName OBJECT-TYPE
    SYNTAX     WtcsDisplayString (SIZE (0..256))
    MAX-ACCESS read-only
    STATUS     current
    DESCRIPTION
        "The System Name of the scoping system."
    ::= { msvmDisketteDriveEntry 48 }

msvmdskdvTimeOfLastMount OBJECT-TYPE
    SYNTAX     DateAndTime
    MAX-ACCESS read-only
    STATUS     current
    DESCRIPTION
        "For a MediaAccessDevice that supports removable
        Media, the most recent date and time that Media was
        mounted on the Device. For Devices accessing
        nonremovable Media, such as hard disks, this
        property has no meaning and is not applicable."
    ::= { msvmDisketteDriveEntry 49 }

msvmdskdvTimeOfLastStateChange OBJECT-TYPE
    SYNTAX     DateAndTime
    MAX-ACCESS read-only
    STATUS     current
    DESCRIPTION
        "The date or time when the EnabledState of the
        element last changed. If the state of the element
        has not changed and this property is populated,
        then it must be set to a 0 interval value. If a
        state change was requested, but rejected or not yet
        processed, the property must not be updated."
    ::= { msvmDisketteDriveEntry 50 }

msvmdskdvTotalMountTime OBJECT-TYPE
    SYNTAX     Gauge32
    MAX-ACCESS read-only
    STATUS     current
    DESCRIPTION
        "For a MediaAccessDevice that supports removable
        Media, the total time (in seconds) that Media have
        been mounted for data transfer or to clean the
        Device. For Devices accessing nonremovable Media,
        such as hard disks, this property is not applicable
        and should be set to 0."
    ::= { msvmDisketteDriveEntry 51 }

msvmdskdvTotalPowerOnHours OBJECT-TYPE
    SYNTAX     Gauge32
    UNITS "Hours"
    MAX-ACCESS read-only
    STATUS     current
    DESCRIPTION
        "Note: The use of this method is deprecated. 
        Deprecated description: The total number of hours
        that this Device has been powered on."
    ::= { msvmDisketteDriveEntry 52 }

msvmdskdvUncompressedDataRate OBJECT-TYPE
    SYNTAX     Gauge32
    UNITS "KiloBytes per Second"
    MAX-ACCESS read-only
    STATUS     current
    DESCRIPTION
        "The sustained data transfer rate in KB/sec that
        the Device can read from and write to a Media. This
        is a sustained, raw data rate. Maximum rates or
        rates assuming compression should not be reported
        in this property."
    ::= { msvmDisketteDriveEntry 53 }

msvmdskdvUnitsDescription OBJECT-TYPE
    SYNTAX     WtcsDisplayString
    MAX-ACCESS read-only
    STATUS     current
    DESCRIPTION
        "Defines 'Units' relative to its use in the
        property, MaxUnitsBeforeCleaning. This describes
        the criteria used to determine when the
        MediaAccessDevice should be cleaned."
    ::= { msvmDisketteDriveEntry 54 }

msvmdskdvUnitsUsed OBJECT-TYPE
    SYNTAX     Gauge32
    MAX-ACCESS read-only
    STATUS     current
    DESCRIPTION
        "An unsigned integer indicating the currently used
        'units' of the AccessDevice, helpful to describe
        when the Device may require cleaning. The property,
        UnitsDescription, defines how 'units' should be
        interpreted."
    ::= { msvmDisketteDriveEntry 55 }

msvmdskdvUnloadTime OBJECT-TYPE
    SYNTAX     Gauge32
    UNITS "MilliSeconds"
    MAX-ACCESS read-only
    STATUS     current
    DESCRIPTION
        "Time in milliseconds from being able to read or
        write a Media to its 'unload'. For example, for
        DiskDrives, this is the interval between a disk
        spinning at nominal speeds and a disk not spinning.
        For TapeDrives, this is the time for a Media to go
        from its BOT to being fully ejected and accessible
        to a PickerElement or human operator."
    ::= { msvmDisketteDriveEntry 56 }

msvmDVDDriveTable OBJECT-TYPE
    SYNTAX     SEQUENCE OF MsvmDVDDrive
    MAX-ACCESS not-accessible
    STATUS     current
    DESCRIPTION
        "Represents a DVD drive inside of a virtual
        machine."
    ::= { msvmStorage 5 }

msvmDVDDriveEntry OBJECT-TYPE
    SYNTAX     MsvmDVDDrive
    MAX-ACCESS not-accessible
    STATUS     current
    DESCRIPTION
        "None"
    INDEX      { msvmdvddvIndex }
    ::= { msvmDVDDriveTable 1 }

MsvmDVDDrive ::= SEQUENCE {
    msvmdvddvIndex Integer32,
    msvmdvddvAdditionalAvailability INTEGER,
    msvmdvddvAvailability INTEGER,
    msvmdvddvCapabilities INTEGER,
    msvmdvddvCapabilityDescriptions WtcsDisplayString,
    msvmdvddvCaption WtcsDisplayString,
    msvmdvddvCompressionMethod WtcsDisplayString,
    msvmdvddvCreationClassName WtcsDisplayString,
    msvmdvddvDefaultBlockSize Gauge32,
    msvmdvddvDescription WtcsDisplayString,
    msvmdvddvDeviceID WtcsDisplayString,
    msvmdvddvElementName WtcsDisplayString,
    msvmdvddvEnabledDefault INTEGER,
    msvmdvddvEnabledState INTEGER,
    msvmdvddvErrorCleared TruthValue,
    msvmdvddvErrorDescription WtcsDisplayString,
    msvmdvddvErrorMethodology WtcsDisplayString,
    msvmdvddvFormatsSupported INTEGER,
    msvmdvddvHealthState INTEGER,
    msvmdvddvIdentifyingDescriptions WtcsDisplayString,
    msvmdvddvInstallDate DateAndTime,
    msvmdvddvLastCleaned DateAndTime,
    msvmdvddvLastErrorCode Gauge32,
    msvmdvddvLoadTime Gauge32,
    msvmdvddvLocationIndicator INTEGER,
    msvmdvddvMaxAccessTime Gauge32,
    msvmdvddvMaxBlockSize Gauge32,
    msvmdvddvMaxMediaSize Gauge32,
    msvmdvddvMaxQuiesceTime Gauge32,
    msvmdvddvMaxUnitsBeforeCleaning Gauge32,
    msvmdvddvMediaIsLocked TruthValue,
    msvmdvddvMinBlockSize Gauge32,
    msvmdvddvMountCount Gauge32,
    msvmdvddvName WtcsDisplayString,
    msvmdvddvNeedsCleaning TruthValue,
    msvmdvddvNumberOfMediaSupported Gauge32,
    msvmdvddvOperationalStatus INTEGER,
    msvmdvddvOtherEnabledState WtcsDisplayString,
    msvmdvddvOtherIdentifyingInfo WtcsDisplayString,
    msvmdvddvPowerMgtCapability INTEGER,
    msvmdvddvPowerManagementSupport TruthValue,
    msvmdvddvPowerOnHours Gauge32,
    msvmdvddvRequestedState INTEGER,
    msvmdvddvSecurity INTEGER,
    msvmdvddvStatus WtcsDisplayString,
    msvmdvddvStatusDescriptions WtcsDisplayString,
    msvmdvddvStatusInfo INTEGER,
    msvmdvddvSystemCreationClassName WtcsDisplayString,
    msvmdvddvSystemName WtcsDisplayString,
    msvmdvddvTimeOfLastMount DateAndTime,
    msvmdvddvTimeOfLastStateChange DateAndTime,
    msvmdvddvTotalMountTime Gauge32,
    msvmdvddvTotalPowerOnHours Gauge32,
    msvmdvddvUncompressedDataRate Gauge32,
    msvmdvddvUnitsDescription WtcsDisplayString,
    msvmdvddvUnitsUsed Gauge32,
    msvmdvddvUnloadTime Gauge32
}

msvmdvddvIndex OBJECT-TYPE
    SYNTAX     Integer32 (1..2147483647)
    MAX-ACCESS read-only
    STATUS     current
    DESCRIPTION
        "The value of this object uniquely identifies the
        instance entry for this class."
    ::= { msvmDVDDriveEntry 1 }

msvmdvddvAdditionalAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Additional availability and status of the Device
        in addition to that specified in the Availability
        property. The Availability property denotes the
        primary status and availability of the Device. In
        some cases, this property will not be sufficient to
        denote the complete status of the Device. In those
        cases, the AdditionalAvailability property can be
        used to provide further information. For example,
        the primary Availability of a device might be 'Off
        line' (value=8) or in a low-power state
        (AdditionalAvailability value=14), or the Device
        could be running Diagnostics
        (AdditionalAvailability value=5, 'In Test')."
    ::= { msvmDVDDriveEntry 2 }

msvmdvddvAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Note: The use of this property has been
        deprecated. 
        Deprecated description: The primary availability
        and status of the Device. (Additional status
        information can be specified using the Additional
        Availability array property.) For example, the
        Availability property indicates that the Device is
        running and has full power (value=3), or is in a
        warning (4), test (5), degraded (10) or power save
        state (values 13-15 and 17). The Power Save states
        are defined as follows: Value 13 ('Power Save -
        Unknown') indicates that the Device is known to be
        in a power save mode, but its exact status in this
        mode is unknown; value 14 ('Power Save - Low Power
        Mode') indicates that the Device is in a power save
        state but still functioning, and might exhibit
        degraded performance; value 15 ('Power Save -
        Standby') indicates that the Device is not
        functioning but could be brought to full power
        'quickly'; and value 17 ('Power Save - Warning')
        indicates that the Device is in a warning state,
        but is also in a power save mode."
    ::= { msvmDVDDriveEntry 3 }

msvmdvddvCapabilities OBJECT-TYPE
    SYNTAX     INTEGER {
        unknown(0),
        other(1),
        sequentialAccess(2),
        randomAccess(3),
        supportsWriting(4),
        encryption(5),
        compression(6),
        supportsRemoveableMedia(7),
        manualCleaning(8),
        automaticCleaning(9),
        smartNotification(10),
        supportsDualSidedMedia(11),
        predismountEjectNotRequired(12)
    }
    MAX-ACCESS read-only
    STATUS     current
    DESCRIPTION
        "Capabilities of the MediaAccessDevice. For
        example, the Device may support 'Random Access',
        removeable media and 'Automatic Cleaning'. In this
        case, the values 3, 7 and 9 would be written to the
        array. 
        Several of the enumerated values require some
        explanation: 1) Value 11, Supports Dual Sided
        Media, distinguishes a Device that can access both
        sides of dual sided Media, from a Device that reads
        only a single side and requires the Media to be
        flipped; and, 2) Value 12, Predismount Eject Not
        Required, indicates that Media does not have to be
        explicitly ejected from the Device before being
        accessed by a PickerElement."
    ::= { msvmDVDDriveEntry 4 }

msvmdvddvCapabilityDescriptions OBJECT-TYPE
    SYNTAX     WtcsDisplayString
    MAX-ACCESS read-only
    STATUS     current
    DESCRIPTION
        "An array of free-form strings providing more
        detailed explanations for any of the AccessDevice
        features indicated in the Capabilities array. Note,
        each entry of this array is related to the entry in
        the Capabilities array that is located at the same
        index."
    ::= { msvmDVDDriveEntry 5 }

msvmdvddvCaption OBJECT-TYPE
    SYNTAX     WtcsDisplayString (SIZE (0..64))
    MAX-ACCESS read-only
    STATUS     current
    DESCRIPTION
        "The Caption property is a short textual
        description (one- line string) of the object."
    ::= { msvmDVDDriveEntry 6 }

msvmdvddvCompressionMethod OBJECT-TYPE
    SYNTAX     WtcsDisplayString
    MAX-ACCESS read-only
    STATUS     current
    DESCRIPTION
        "A free form string indicating the algorithm or
        tool used by the device to support compression. If
        it is not possible or not desired to describe the
        compression scheme (perhaps because it is not
        known), recommend using the following words:
        'Unknown' to represent that it is not known whether
        the device supports compression capabilities or
        not, 'Compressed' to represent that the device
        supports compression capabilities but either its
        compression scheme is not known or not disclosed,
        and 'Not Compressed' to represent that the devices
        does not support compression capabilities."
    ::= { msvmDVDDriveEntry 7 }

msvmdvddvCreationClassName OBJECT-TYPE
    SYNTAX     WtcsDisplayString (SIZE (0..256))
    MAX-ACCESS read-only
    STATUS     current
    DESCRIPTION
        "CreationClassName indicates the name of the class
        or the subclass used in the creation of an
        instance. When used with the other key properties
        of this class, this property allows all instances
        of this class and its subclasses to be uniquely
        identified."
    ::= { msvmDVDDriveEntry 8 }

msvmdvddvDefaultBlockSize OBJECT-TYPE
    SYNTAX     Gauge32
    UNITS "Bytes"
    MAX-ACCESS read-only
    STATUS     current
    DESCRIPTION
        "Default block size, in bytes, for this Device."
    ::= { msvmDVDDriveEntry 9 }

msvmdvddvDescription OBJECT-TYPE
    SYNTAX     WtcsDisplayString
    MAX-ACCESS read-only
    STATUS     current
    DESCRIPTION
        "The Description property provides a textual
        description of the object."
    ::= { msvmDVDDriveEntry 10 }

msvmdvddvDeviceID OBJECT-TYPE
    SYNTAX     WtcsDisplayString (SIZE (0..64))
    MAX-ACCESS read-only
    STATUS     current
    DESCRIPTION
        "An address or other identifying information used
        to uniquely name the LogicalDevice."
    ::= { msvmDVDDriveEntry 11 }

msvmdvddvElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmDVDDriveEntry 12 }

msvmdvddvEnabledDefault OBJECT-TYPE
    SYNTAX     INTEGER {
        enabled(2),
        disabled(3),
        notApplicable(5),
        enabledbutOffline(6),
        noDefault(7)
    }
    MAX-ACCESS read-only
    STATUS     current
    DESCRIPTION
        "An enumerated value indicating an administrator's
        default or startup configuration for the Enabled
        State of an element. By default, the element is
        'Enabled' (value=2)."
    ::= { msvmDVDDriveEntry 13 }

msvmdvddvEnabledState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "EnabledState is an integer enumeration that
        indicates the enabled and disabled states of an
        element. It can also indicate the transitions
        between these requested states. For example,
        shutting down (value=4) and starting (value=10) are
        transient states between enabled and disabled. The
        following text briefly summarizes the various
        enabled and disabled states: 
        Enabled (2) indicates that the element is or could
        be executing commands, will process any queued
        commands, and queues new requests. 
        Disabled (3) indicates that the element will not
        execute commands and will drop any new requests. 
        Shutting Down (4) indicates that the element is in
        the process of going to a Disabled state. 
        Not Applicable (5) indicates the element does not
        support being enabled or disabled. 
        Enabled but Offline (6) indicates that the element
        might be completing commands, and will drop any new
        requests. 
        Test (7) indicates that the element is in a test
        state. 
        Deferred (8) indicates that the element might be
        completing commands, but will queue any new
        requests. 
        Quiesce (9) indicates that the element is enabled
        but in a restricted mode. The behavior of the
        element is similar to the Enabled state, but it
        processes only a restricted set of commands. All
        other requests are queued. 
        Starting (10) indicates that the element is in the
        process of going to an Enabled state. New requests
        are queued."
    ::= { msvmDVDDriveEntry 14 }

msvmdvddvErrorCleared OBJECT-TYPE
    SYNTAX     TruthValue
    MAX-ACCESS read-only
    STATUS     current
    DESCRIPTION
        "Note: The use of this method is deprecated. 
        Deprecated description: ErrorCleared is a Boolean
        property that indicates that the error reported in
        LastErrorCode is now cleared."
    ::= { msvmDVDDriveEntry 15 }

msvmdvddvErrorDescription OBJECT-TYPE
    SYNTAX     WtcsDisplayString
    MAX-ACCESS read-only
    STATUS     current
    DESCRIPTION
        "Note: The use of this method is deprecated. 
        Deprecated description: ErrorDescription is a
        free-form string that supplies more information
        about the error recorded in LastErrorCode and
        information on any corrective actions that can be
        taken."
    ::= { msvmDVDDriveEntry 16 }

msvmdvddvErrorMethodology OBJECT-TYPE
    SYNTAX     WtcsDisplayString
    MAX-ACCESS read-only
    STATUS     current
    DESCRIPTION
        "ErrorMethodology is a free-form string describing
        the type(s) of error detection and correction
        supported by this Device."
    ::= { msvmDVDDriveEntry 17 }

msvmdvddvFormatsSupported OBJECT-TYPE
    SYNTAX     INTEGER {
        unknown(0),
        other(1),
        cdROM(16),
        cdROMXA(17),
        cdI(18),
        cdRecordable(19),
        dvd(22),
        dvdRW(23),
        dvdRAM(24),
        dvdROM(25),
        dvdVideo(26),
        divx(27),
        cdRW(33),
        cdDA(34),
        cd(35),
        dvdRecordable(36),
        dvdRW2(37),
        dvdAudio(38),
        dvd5(39),
        dvd9(40),
        dvd10(41),
        dvd18(42)
    }
    MAX-ACCESS read-only
    STATUS     current
    DESCRIPTION
        "The CD and DVD formats that are supported by this
        Device. For example, the Drive may support 'CD-ROM'
        and 'DVD-RAM'. In this case, the values 16 and 24
        would be written to the array. This property's
        values align with those defined in
        PhysicalMedia.MediaType."
    ::= { msvmDVDDriveEntry 18 }

msvmdvddvHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmDVDDriveEntry 19 }

msvmdvddvIdentifyingDescriptions OBJECT-TYPE
    SYNTAX     WtcsDisplayString
    MAX-ACCESS read-only
    STATUS     current
    DESCRIPTION
        "An array of free-form strings providing
        explanations and details behind the entries in the
        OtherIdentifyingInfo array. Note that each entry of
        this array is related to the entry in
        OtherIdentifyingInfo that is located at the same
        index."
    ::= { msvmDVDDriveEntry 20 }

msvmdvddvInstallDate OBJECT-TYPE
    SYNTAX     DateAndTime
    MAX-ACCESS read-only
    STATUS     current
    DESCRIPTION
        "A datetime value that indicates when the object
        was installed. Lack of a value does not indicate
        that the object is not installed."
    ::= { msvmDVDDriveEntry 21 }

msvmdvddvLastCleaned OBJECT-TYPE
    SYNTAX     DateAndTime
    MAX-ACCESS read-only
    STATUS     current
    DESCRIPTION
        "The date and time on which the Device was last
        cleaned."
    ::= { msvmDVDDriveEntry 22 }

msvmdvddvLastErrorCode OBJECT-TYPE
    SYNTAX     Gauge32
    MAX-ACCESS read-only
    STATUS     current
    DESCRIPTION
        "Note: The use of this method is deprecated. 
        Deprecated description: LastErrorCode captures the
        last error code reported by the LogicalDevice."
    ::= { msvmDVDDriveEntry 23 }

msvmdvddvLoadTime OBJECT-TYPE
    SYNTAX     Gauge32
    UNITS "MilliSeconds"
    MAX-ACCESS read-only
    STATUS     current
    DESCRIPTION
        "Time in milliseconds from 'load' to being able to
        read or write a Media. For example, for DiskDrives,
        this is the interval between a disk not spinning to
        the disk reporting that it is ready for read/write
        (ie, the disk spinning at nominal speeds). For
        TapeDrives, this is the time from a Media being
        injected to reporting that it is ready for an
        application. This is usually at the tape's BOT
        area."
    ::= { msvmDVDDriveEntry 24 }

msvmdvddvLocationIndicator OBJECT-TYPE
    SYNTAX     INTEGER {
        unknown(0),
        on(2),
        off(3),
        notSupported(4)
    }
    MAX-ACCESS read-only
    STATUS     current
    DESCRIPTION
        "An integer that reflects the state of an indicator
        (e.g., LED) that is part of a device. Reading the
        value gives the current state. Writing the value
        with 'On'/'Off' turns the indicator on/off, other
        values may not be written."
    ::= { msvmDVDDriveEntry 25 }

msvmdvddvMaxAccessTime OBJECT-TYPE
    SYNTAX     Gauge32
    UNITS "MilliSeconds"
    MAX-ACCESS read-only
    STATUS     current
    DESCRIPTION
        "Time in milliseconds to move from the first
        location on the Media to the location that is
        furthest with respect to time. For a DiskDrive,
        this represents full seek + full rotational delay.
        For TapeDrives, this represents a search from the
        beginning of the tape to the most physically
        distant point. (The end of a tape may be at its
        most physically distant point, but this is not
        necessarily true.)"
    ::= { msvmDVDDriveEntry 26 }

msvmdvddvMaxBlockSize OBJECT-TYPE
    SYNTAX     Gauge32
    UNITS "Bytes"
    MAX-ACCESS read-only
    STATUS     current
    DESCRIPTION
        "Maximum block size, in bytes, for media accessed
        by this Device."
    ::= { msvmDVDDriveEntry 27 }

msvmdvddvMaxMediaSize OBJECT-TYPE
    SYNTAX     Gauge32
    MAX-ACCESS read-only
    STATUS     current
    DESCRIPTION
        "Maximum size, in KBytes, of media supported by
        this Device. KBytes is interpreted as the number of
        bytes multiplied by 1000 (NOT the number of bytes
        multiplied by 1024)."
    ::= { msvmDVDDriveEntry 28 }

msvmdvddvMaxQuiesceTime OBJECT-TYPE
    SYNTAX     Gauge32
    UNITS "MilliSeconds"
    MAX-ACCESS read-only
    STATUS     current
    DESCRIPTION
        "Note: The use of this property has been
        deprecated. When evaluating the use of Quiesce, it
        was determined that this single property is not
        adequate for describing when a device will
        automatically exit a quiescent state. In fact, the
        most likely scenario for a device to exit a
        quiescent state was determined to be based on the
        number of outstanding requests queued rather than
        on a maximum time. This decision will be
        re-evaluated and repositioned later. 
        Deprecated description: Maximum time, in
        milliseconds, that a Device can run in a 'Quiesced'
        state. The state is defined in its Availability and
        AdditionalAvailability properties, where 'Quiesced'
        is conveyed by the value 21. What occurs at the end
        of the time limit is device-specific. The Device
        can unquiesce, can be offline, or can take other
        actions. A value of 0 indicates that a Device can
        remain quiesced indefinitely."
    ::= { msvmDVDDriveEntry 29 }

msvmdvddvMaxUnitsBeforeCleaning OBJECT-TYPE
    SYNTAX     Gauge32
    MAX-ACCESS read-only
    STATUS     current
    DESCRIPTION
        "An unsigned integer indicating the maximum 'units'
        that can be used, with respect to the AccessDevice,
        before the Device should be cleaned. The property,
        UnitsDescription, defines how 'units' should be
        interpreted."
    ::= { msvmDVDDriveEntry 30 }

msvmdvddvMediaIsLocked OBJECT-TYPE
    SYNTAX     TruthValue
    MAX-ACCESS read-only
    STATUS     current
    DESCRIPTION
        "True indicates that the media is locked in the
        Device and can not be ejected. For non-removeable
        Devices, this value should be true."
    ::= { msvmDVDDriveEntry 31 }

msvmdvddvMinBlockSize OBJECT-TYPE
    SYNTAX     Gauge32
    UNITS "Bytes"
    MAX-ACCESS read-only
    STATUS     current
    DESCRIPTION
        "Minimum block size, in bytes, for media accessed
        by this Device."
    ::= { msvmDVDDriveEntry 32 }

msvmdvddvMountCount OBJECT-TYPE
    SYNTAX     Gauge32
    MAX-ACCESS read-only
    STATUS     current
    DESCRIPTION
        "For a MediaAccessDevice that supports removable
        Media, the number of times that Media have been
        mounted for data transfer or to clean the Device.
        For Devices accessing nonremovable Media, such as
        hard disks, this property is not applicable and
        should be set to 0."
    ::= { msvmDVDDriveEntry 33 }

msvmdvddvName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmDVDDriveEntry 34 }

msvmdvddvNeedsCleaning OBJECT-TYPE
    SYNTAX     TruthValue
    MAX-ACCESS read-only
    STATUS     current
    DESCRIPTION
        "Boolean indicating that the MediaAccessDevice
        needs cleaning. Whether manual or automatic
        cleaning is possible is indicated in the
        Capabilities array property."
    ::= { msvmDVDDriveEntry 35 }

msvmdvddvNumberOfMediaSupported OBJECT-TYPE
    SYNTAX     Gauge32
    MAX-ACCESS read-only
    STATUS     current
    DESCRIPTION
        "When the MediaAccessDevice supports multiple
        individual Media, this property defines the maximum
        number which can be supported or inserted."
    ::= { msvmDVDDriveEntry 36 }

msvmdvddvOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmDVDDriveEntry 37 }

msvmdvddvOtherEnabledState OBJECT-TYPE
    SYNTAX     WtcsDisplayString
    MAX-ACCESS read-only
    STATUS     current
    DESCRIPTION
        "A string that describes the enabled or disabled
        state of the element when the EnabledState property
        is set to 1 ('Other'). This property must be set to
        null when EnabledState is any value other than 1."
    ::= { msvmDVDDriveEntry 38 }

msvmdvddvOtherIdentifyingInfo OBJECT-TYPE
    SYNTAX     WtcsDisplayString (SIZE (0..256))
    MAX-ACCESS read-only
    STATUS     current
    DESCRIPTION
        "OtherIdentifyingInfo captures data, in addition to
        DeviceID information, that could be used to
        identify a LogicalDevice. For example, you could
        use this property to hold the operating system's
        user-friendly name for the Device."
    ::= { msvmDVDDriveEntry 39 }

msvmdvddvPowerMgtCapability OBJECT-TYPE
    SYNTAX     INTEGER {
        unknown(0),
        notSupported(1),
        disabled(2),
        enabled(3),
        powerSavingModesEnteredAutomatic(4),
        powerStateSettable(5),
        powerCyclingSupported(6),
        timedPowerOnSupported(7)
    }
    MAX-ACCESS read-only
    STATUS     current
    DESCRIPTION
        "Note: The use of this property has been
        deprecated. Instead, use the PowerCapabilites
        property in an associated
        PowerManagementCapabilities class. Deprecated
        description: An enumerated array describing the
        power management capabilities of the Device."
    ::= { msvmDVDDriveEntry 40 }

msvmdvddvPowerManagementSupport OBJECT-TYPE
    SYNTAX     TruthValue
    MAX-ACCESS read-only
    STATUS     current
    DESCRIPTION
        "Note: The use of this property has been
        deprecated. Instead, the existence of an associated
        PowerManagementCapabilities class (associated using
        the ElementCapabilities relationship) indicates
        that power management is supported. Deprecated
        description: Boolean that indicates that the Device
        can use power management."
    ::= { msvmDVDDriveEntry 41 }

msvmdvddvPowerOnHours OBJECT-TYPE
    SYNTAX     Gauge32
    UNITS "Hours"
    MAX-ACCESS read-only
    STATUS     current
    DESCRIPTION
        "Note: The use of this method is deprecated. 
        Deprecated description: The number of consecutive
        hours that this Device has been powered on since
        its last power cycle."
    ::= { msvmDVDDriveEntry 42 }

msvmdvddvRequestedState OBJECT-TYPE
    SYNTAX     INTEGER {
        enabled(2),
        disabled(3),
        shutDown(4),
        noChange(5),
        offline(6),
        test(7),
        deferred(8),
        quiesce(9),
        reboot(10),
        reset(11),
        notApplicable(12)
    }
    MAX-ACCESS read-only
    STATUS     current
    DESCRIPTION
        "RequestedState is an integer enumeration that
        indicates the last requested or desired state for
        the element. The actual state of the element is
        represented by EnabledState. This property is
        provided to compare the last requested and current
        enabled or disabled states. Note that when
        EnabledState is set to 5 ('Not Applicable'), then
        this property has no meaning. By default, the
        RequestedState of the element is 5 ('No Change').
        Refer to the EnabledState property description for
        explanations of the values in the RequestedState
        enumeration. 
        
        It should be noted that there are two new values in
        RequestedState that build on the statuses of
        EnabledState. These are 'Reboot' (10) and 'Reset'
        (11). Reboot refers to doing a 'Shut Down' and then
        moving to an 'Enabled' state. Reset indicates that
        the element is first 'Disabled' and then 'Enabled'.
        The distinction between requesting 'Shut Down' and
        'Disabled' should also be noted. Shut Down requests
        an orderly transition to the Disabled state, and
        might involve removing power, to completely erase
        any existing state. The Disabled state requests an
        immediate disabling of the element, such that it
        will not execute or accept any commands or
        processing requests. 
        
        This property is set as the result of a method
        invocation (such as Start or StopService on
        CIM_Service), or can be overridden and defined as
        WRITEable in a subclass. The method approach is
        considered superior to a WRITEable property,
        because it allows an explicit invocation of the
        operation and the return of a result code. 
        
        A particular instance of EnabledLogicalElement
        might not support RequestedStateChange. If this
        occurs, the value 12 ('Not Applicable') is used."
    ::= { msvmDVDDriveEntry 43 }

msvmdvddvSecurity OBJECT-TYPE
    SYNTAX     INTEGER {
        other(1),
        unknown(2),
        none(3),
        readOnly(4),
        lockedOut(5),
        bootBypass(6),
        bootBypassandReadOnly(7)
    }
    MAX-ACCESS read-only
    STATUS     current
    DESCRIPTION
        "An enumeration indicating the operational security
        defined for the MediaAccessDevice. For example,
        information that the Device is 'Read Only'
        (value=4) or 'Boot Bypass' (value=6) can be
        described using this property."
    ::= { msvmDVDDriveEntry 44 }

msvmdvddvStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmDVDDriveEntry 45 }

msvmdvddvStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmDVDDriveEntry 46 }

msvmdvddvStatusInfo OBJECT-TYPE
    SYNTAX     INTEGER {
        other(1),
        unknown(2),
        enabled(3),
        disabled(4),
        notApplicable(5)
    }
    MAX-ACCESS read-only
    STATUS     current
    DESCRIPTION
        "Note: The use of this method is deprecated in lieu
        of a more clearly named property (EnabledState)
        that is inherited from ManagedSystemElement and
        that has additional enumerated values. 
        Deprecated description: The StatusInfo property
        indicates whether the Logical Device is in an
        enabled state (value=3), disabled state (value=4),
        some other state (value=1), or an unknown state
        (value=2). If this property does not apply to the
        LogicalDevice, the value 5 ('Not Applicable')
        should be used. If a Device is
        ('Enabled')(value=3), it has been powered up and is
        configured and operational. The Device might or
        might not be functionally active, depending on
        whether its Availability (or
        AdditionalAvailability) indicates that it is
        ('Running/Full Power')(value=3) or ('Off line')
        (value=8). In an enabled but offline mode, a Device
        might be performing out-of-band requests, such as
        running Diagnostics. If StatusInfo is ('Disabled')
        (value=4), a Device can only be 'enabled' or
        powered off. In a personal computer environment,
        ('Disabled') means that the driver of the device is
        not available in the stack. In other environments,
        a Device can be disabled by removing its
        configuration file. A disabled device is physically
        present in a System and consuming resources, but it
        cannot be communicated with until a driver is
        loaded, a configuration file is loaded, or some
        other 'enabling' activity has occurred."
    ::= { msvmDVDDriveEntry 47 }

msvmdvddvSystemCreationClassName OBJECT-TYPE
    SYNTAX     WtcsDisplayString (SIZE (0..256))
    MAX-ACCESS read-only
    STATUS     current
    DESCRIPTION
        "The CreationClassName of the scoping system."
    ::= { msvmDVDDriveEntry 48 }

msvmdvddvSystemName OBJECT-TYPE
    SYNTAX     WtcsDisplayString (SIZE (0..256))
    MAX-ACCESS read-only
    STATUS     current
    DESCRIPTION
        "The System Name of the scoping system."
    ::= { msvmDVDDriveEntry 49 }

msvmdvddvTimeOfLastMount OBJECT-TYPE
    SYNTAX     DateAndTime
    MAX-ACCESS read-only
    STATUS     current
    DESCRIPTION
        "For a MediaAccessDevice that supports removable
        Media, the most recent date and time that Media was
        mounted on the Device. For Devices accessing
        nonremovable Media, such as hard disks, this
        property has no meaning and is not applicable."
    ::= { msvmDVDDriveEntry 50 }

msvmdvddvTimeOfLastStateChange OBJECT-TYPE
    SYNTAX     DateAndTime
    MAX-ACCESS read-only
    STATUS     current
    DESCRIPTION
        "The date or time when the EnabledState of the
        element last changed. If the state of the element
        has not changed and this property is populated,
        then it must be set to a 0 interval value. If a
        state change was requested, but rejected or not yet
        processed, the property must not be updated."
    ::= { msvmDVDDriveEntry 51 }

msvmdvddvTotalMountTime OBJECT-TYPE
    SYNTAX     Gauge32
    MAX-ACCESS read-only
    STATUS     current
    DESCRIPTION
        "For a MediaAccessDevice that supports removable
        Media, the total time (in seconds) that Media have
        been mounted for data transfer or to clean the
        Device. For Devices accessing nonremovable Media,
        such as hard disks, this property is not applicable
        and should be set to 0."
    ::= { msvmDVDDriveEntry 52 }

msvmdvddvTotalPowerOnHours OBJECT-TYPE
    SYNTAX     Gauge32
    UNITS "Hours"
    MAX-ACCESS read-only
    STATUS     current
    DESCRIPTION
        "Note: The use of this method is deprecated. 
        Deprecated description: The total number of hours
        that this Device has been powered on."
    ::= { msvmDVDDriveEntry 53 }

msvmdvddvUncompressedDataRate OBJECT-TYPE
    SYNTAX     Gauge32
    UNITS "KiloBytes per Second"
    MAX-ACCESS read-only
    STATUS     current
    DESCRIPTION
        "The sustained data transfer rate in KB/sec that
        the Device can read from and write to a Media. This
        is a sustained, raw data rate. Maximum rates or
        rates assuming compression should not be reported
        in this property."
    ::= { msvmDVDDriveEntry 54 }

msvmdvddvUnitsDescription OBJECT-TYPE
    SYNTAX     WtcsDisplayString
    MAX-ACCESS read-only
    STATUS     current
    DESCRIPTION
        "Defines 'Units' relative to its use in the
        property, MaxUnitsBeforeCleaning. This describes
        the criteria used to determine when the
        MediaAccessDevice should be cleaned."
    ::= { msvmDVDDriveEntry 55 }

msvmdvddvUnitsUsed OBJECT-TYPE
    SYNTAX     Gauge32
    MAX-ACCESS read-only
    STATUS     current
    DESCRIPTION
        "An unsigned integer indicating the currently used
        'units' of the AccessDevice, helpful to describe
        when the Device may require cleaning. The property,
        UnitsDescription, defines how 'units' should be
        interpreted."
    ::= { msvmDVDDriveEntry 56 }

msvmdvddvUnloadTime OBJECT-TYPE
    SYNTAX     Gauge32
    UNITS "MilliSeconds"
    MAX-ACCESS read-only
    STATUS     current
    DESCRIPTION
        "Time in milliseconds from being able to read or
        write a Media to its 'unload'. For example, for
        DiskDrives, this is the interval between a disk
        spinning at nominal speeds and a disk not spinning.
        For TapeDrives, this is the time for a Media to go
        from its BOT to being fully ejected and accessible
        to a PickerElement or human operator."
    ::= { msvmDVDDriveEntry 57 }

msvmIDEControllerTable OBJECT-TYPE
    SYNTAX     SEQUENCE OF MsvmIDEController
    MAX-ACCESS not-accessible
    STATUS     current
    DESCRIPTION
        "Represents an IDE controller."
    ::= { msvmStorage 6 }

msvmIDEControllerEntry OBJECT-TYPE
    SYNTAX     MsvmIDEController
    MAX-ACCESS not-accessible
    STATUS     current
    DESCRIPTION
        "None"
    INDEX      { msvmidecIndex }
    ::= { msvmIDEControllerTable 1 }

MsvmIDEController ::= SEQUENCE {
    msvmidecIndex Integer32,
    msvmidecAdditionalAvailability INTEGER,
    msvmidecAvailability INTEGER,
    msvmidecCaption WtcsDisplayString,
    msvmidecCreationClassName WtcsDisplayString,
    msvmidecDescription WtcsDisplayString,
    msvmidecDeviceID WtcsDisplayString,
    msvmidecElementName WtcsDisplayString,
    msvmidecEnabledDefault INTEGER,
    msvmidecEnabledState INTEGER,
    msvmidecErrorCleared TruthValue,
    msvmidecErrorDescription WtcsDisplayString,
    msvmidecHealthState INTEGER,
    msvmidecIdentifyingDescriptions WtcsDisplayString,
    msvmidecInstallDate DateAndTime,
    msvmidecLastErrorCode Gauge32,
    msvmidecLocationIndicator INTEGER,
    msvmidecMaxNumberControlled Gauge32,
    msvmidecMaxQuiesceTime Gauge32,
    msvmidecName WtcsDisplayString,
    msvmidecOperationalStatus INTEGER,
    msvmidecOtherEnabledState WtcsDisplayString,
    msvmidecOtherIdentifyingInfo WtcsDisplayString,
    msvmidecPowerMgtCapability INTEGER,
    msvmidecPowerManagementSupported TruthValue,
    msvmidecPowerOnHours Gauge32,
    msvmidecProtocolDescription WtcsDisplayString,
    msvmidecProtocolSupported Integer32,
    msvmidecRequestedState INTEGER,
    msvmidecStatus WtcsDisplayString,
    msvmidecStatusDescriptions WtcsDisplayString,
    msvmidecStatusInfo INTEGER,
    msvmidecSystemCreationClassName WtcsDisplayString,
    msvmidecSystemName WtcsDisplayString,
    msvmidecTimeOfLastReset DateAndTime,
    msvmidecTimeOfLastStateChange DateAndTime,
    msvmidecTotalPowerOnHours Gauge32
}

msvmidecIndex OBJECT-TYPE
    SYNTAX     Integer32 (1..2147483647)
    MAX-ACCESS read-only
    STATUS     current
    DESCRIPTION
        "The value of this object uniquely identifies the
        instance entry for this class."
    ::= { msvmIDEControllerEntry 1 }

msvmidecAdditionalAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Additional availability and status of the Device
        in addition to that specified in the Availability
        property. The Availability property denotes the
        primary status and availability of the Device. In
        some cases, this property will not be sufficient to
        denote the complete status of the Device. In those
        cases, the AdditionalAvailability property can be
        used to provide further information. For example,
        the primary Availability of a device might be 'Off
        line' (value=8) or in a low-power state
        (AdditionalAvailability value=14), or the Device
        could be running Diagnostics
        (AdditionalAvailability value=5, 'In Test')."
    ::= { msvmIDEControllerEntry 2 }

msvmidecAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Note: The use of this property has been
        deprecated. 
        Deprecated description: The primary availability
        and status of the Device. (Additional status
        information can be specified using the Additional
        Availability array property.) For example, the
        Availability property indicates that the Device is
        running and has full power (value=3), or is in a
        warning (4), test (5), degraded (10) or power save
        state (values 13-15 and 17). The Power Save states
        are defined as follows: Value 13 ('Power Save -
        Unknown') indicates that the Device is known to be
        in a power save mode, but its exact status in this
        mode is unknown; value 14 ('Power Save - Low Power
        Mode') indicates that the Device is in a power save
        state but still functioning, and might exhibit
        degraded performance; value 15 ('Power Save -
        Standby') indicates that the Device is not
        functioning but could be brought to full power
        'quickly'; and value 17 ('Power Save - Warning')
        indicates that the Device is in a warning state,
        but is also in a power save mode."
    ::= { msvmIDEControllerEntry 3 }

msvmidecCaption OBJECT-TYPE
    SYNTAX     WtcsDisplayString (SIZE (0..64))
    MAX-ACCESS read-only
    STATUS     current
    DESCRIPTION
        "The Caption property is a short textual
        description (one- line string) of the object."
    ::= { msvmIDEControllerEntry 4 }

msvmidecCreationClassName OBJECT-TYPE
    SYNTAX     WtcsDisplayString (SIZE (0..256))
    MAX-ACCESS read-only
    STATUS     current
    DESCRIPTION
        "CreationClassName indicates the name of the class
        or the subclass used in the creation of an
        instance. When used with the other key properties
        of this class, this property allows all instances
        of this class and its subclasses to be uniquely
        identified."
    ::= { msvmIDEControllerEntry 5 }

msvmidecDescription OBJECT-TYPE
    SYNTAX     WtcsDisplayString
    MAX-ACCESS read-only
    STATUS     current
    DESCRIPTION
        "The Description property provides a textual
        description of the object."
    ::= { msvmIDEControllerEntry 6 }

msvmidecDeviceID OBJECT-TYPE
    SYNTAX     WtcsDisplayString (SIZE (0..64))
    MAX-ACCESS read-only
    STATUS     current
    DESCRIPTION
        "An address or other identifying information used
        to uniquely name the LogicalDevice."
    ::= { msvmIDEControllerEntry 7 }

msvmidecElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmIDEControllerEntry 8 }

msvmidecEnabledDefault OBJECT-TYPE
    SYNTAX     INTEGER {
        enabled(2),
        disabled(3),
        notApplicable(5),
        enabledbutOffline(6),
        noDefault(7)
    }
    MAX-ACCESS read-only
    STATUS     current
    DESCRIPTION
        "An enumerated value indicating an administrator's
        default or startup configuration for the Enabled
        State of an element. By default, the element is
        'Enabled' (value=2)."
    ::= { msvmIDEControllerEntry 9 }

msvmidecEnabledState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "EnabledState is an integer enumeration that
        indicates the enabled and disabled states of an
        element. It can also indicate the transitions
        between these requested states. For example,
        shutting down (value=4) and starting (value=10) are
        transient states between enabled and disabled. The
        following text briefly summarizes the various
        enabled and disabled states: 
        Enabled (2) indicates that the element is or could
        be executing commands, will process any queued
        commands, and queues new requests. 
        Disabled (3) indicates that the element will not
        execute commands and will drop any new requests. 
        Shutting Down (4) indicates that the element is in
        the process of going to a Disabled state. 
        Not Applicable (5) indicates the element does not
        support being enabled or disabled. 
        Enabled but Offline (6) indicates that the element
        might be completing commands, and will drop any new
        requests. 
        Test (7) indicates that the element is in a test
        state. 
        Deferred (8) indicates that the element might be
        completing commands, but will queue any new
        requests. 
        Quiesce (9) indicates that the element is enabled
        but in a restricted mode. The behavior of the
        element is similar to the Enabled state, but it
        processes only a restricted set of commands. All
        other requests are queued. 
        Starting (10) indicates that the element is in the
        process of going to an Enabled state. New requests
        are queued."
    ::= { msvmIDEControllerEntry 10 }

msvmidecErrorCleared OBJECT-TYPE
    SYNTAX     TruthValue
    MAX-ACCESS read-only
    STATUS     current
    DESCRIPTION
        "Note: The use of this method is deprecated. 
        Deprecated description: ErrorCleared is a Boolean
        property that indicates that the error reported in
        LastErrorCode is now cleared."
    ::= { msvmIDEControllerEntry 11 }

msvmidecErrorDescription OBJECT-TYPE
    SYNTAX     WtcsDisplayString
    MAX-ACCESS read-only
    STATUS     current
    DESCRIPTION
        "Note: The use of this method is deprecated. 
        Deprecated description: ErrorDescription is a
        free-form string that supplies more information
        about the error recorded in LastErrorCode and
        information on any corrective actions that can be
        taken."
    ::= { msvmIDEControllerEntry 12 }

msvmidecHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmIDEControllerEntry 13 }

msvmidecIdentifyingDescriptions OBJECT-TYPE
    SYNTAX     WtcsDisplayString
    MAX-ACCESS read-only
    STATUS     current
    DESCRIPTION
        "An array of free-form strings providing
        explanations and details behind the entries in the
        OtherIdentifyingInfo array. Note that each entry of
        this array is related to the entry in
        OtherIdentifyingInfo that is located at the same
        index."
    ::= { msvmIDEControllerEntry 14 }

msvmidecInstallDate OBJECT-TYPE
    SYNTAX     DateAndTime
    MAX-ACCESS read-only
    STATUS     current
    DESCRIPTION
        "A datetime value that indicates when the object
        was installed. Lack of a value does not indicate
        that the object is not installed."
    ::= { msvmIDEControllerEntry 15 }

msvmidecLastErrorCode OBJECT-TYPE
    SYNTAX     Gauge32
    MAX-ACCESS read-only
    STATUS     current
    DESCRIPTION
        "Note: The use of this method is deprecated. 
        Deprecated description: LastErrorCode captures the
        last error code reported by the LogicalDevice."
    ::= { msvmIDEControllerEntry 16 }

msvmidecLocationIndicator OBJECT-TYPE
    SYNTAX     INTEGER {
        unknown(0),
        on(2),
        off(3),
        notSupported(4)
    }
    MAX-ACCESS read-only
    STATUS     current
    DESCRIPTION
        "An integer that reflects the state of an indicator
        (e.g., LED) that is part of a device. Reading the
        value gives the current state. Writing the value
        with 'On'/'Off' turns the indicator on/off, other
        values may not be written."
    ::= { msvmIDEControllerEntry 17 }

msvmidecMaxNumberControlled OBJECT-TYPE
    SYNTAX     Gauge32
    MAX-ACCESS read-only
    STATUS     current
    DESCRIPTION
        "Maximum number of directly addressable entities
        that are supported by this Controller. A value of 0
        should be used if the number is unknown or
        unlimited."
    ::= { msvmIDEControllerEntry 18 }

msvmidecMaxQuiesceTime OBJECT-TYPE
    SYNTAX     Gauge32
    UNITS "MilliSeconds"
    MAX-ACCESS read-only
    STATUS     current
    DESCRIPTION
        "Note: The use of this property has been
        deprecated. When evaluating the use of Quiesce, it
        was determined that this single property is not
        adequate for describing when a device will
        automatically exit a quiescent state. In fact, the
        most likely scenario for a device to exit a
        quiescent state was determined to be based on the
        number of outstanding requests queued rather than
        on a maximum time. This decision will be
        re-evaluated and repositioned later. 
        Deprecated description: Maximum time, in
        milliseconds, that a Device can run in a 'Quiesced'
        state. The state is defined in its Availability and
        AdditionalAvailability properties, where 'Quiesced'
        is conveyed by the value 21. What occurs at the end
        of the time limit is device-specific. The Device
        can unquiesce, can be offline, or can take other
        actions. A value of 0 indicates that a Device can
        remain quiesced indefinitely."
    ::= { msvmIDEControllerEntry 19 }

msvmidecName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmIDEControllerEntry 20 }

msvmidecOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmIDEControllerEntry 21 }

msvmidecOtherEnabledState OBJECT-TYPE
    SYNTAX     WtcsDisplayString
    MAX-ACCESS read-only
    STATUS     current
    DESCRIPTION
        "A string that describes the enabled or disabled
        state of the element when the EnabledState property
        is set to 1 ('Other'). This property must be set to
        null when EnabledState is any value other than 1."
    ::= { msvmIDEControllerEntry 22 }

msvmidecOtherIdentifyingInfo OBJECT-TYPE
    SYNTAX     WtcsDisplayString (SIZE (0..256))
    MAX-ACCESS read-only
    STATUS     current
    DESCRIPTION
        "OtherIdentifyingInfo captures data, in addition to
        DeviceID information, that could be used to
        identify a LogicalDevice. For example, you could
        use this property to hold the operating system's
        user-friendly name for the Device."
    ::= { msvmIDEControllerEntry 23 }

msvmidecPowerMgtCapability OBJECT-TYPE
    SYNTAX     INTEGER {
        unknown(0),
        notSupported(1),
        disabled(2),
        enabled(3),
        powerSavingModesEnteredAutomatic(4),
        powerStateSettable(5),
        powerCyclingSupported(6),
        timedPowerOnSupported(7)
    }
    MAX-ACCESS read-only
    STATUS     current
    DESCRIPTION
        "Note: The use of this property has been
        deprecated. Instead, use the PowerCapabilites
        property in an associated
        PowerManagementCapabilities class. Deprecated
        description: An enumerated array describing the
        power management capabilities of the Device."
    ::= { msvmIDEControllerEntry 24 }

msvmidecPowerManagementSupported OBJECT-TYPE
    SYNTAX     TruthValue
    MAX-ACCESS read-only
    STATUS     current
    DESCRIPTION
        "Note: The use of this property has been
        deprecated. Instead, the existence of an associated
        PowerManagementCapabilities class (associated using
        the ElementCapabilities relationship) indicates
        that power management is supported. Deprecated
        description: Boolean that indicates that the Device
        can use power management."
    ::= { msvmIDEControllerEntry 25 }

msvmidecPowerOnHours OBJECT-TYPE
    SYNTAX     Gauge32
    UNITS "Hours"
    MAX-ACCESS read-only
    STATUS     current
    DESCRIPTION
        "Note: The use of this method is deprecated. 
        Deprecated description: The number of consecutive
        hours that this Device has been powered on since
        its last power cycle."
    ::= { msvmIDEControllerEntry 26 }

msvmidecProtocolDescription OBJECT-TYPE
    SYNTAX     WtcsDisplayString
    MAX-ACCESS read-only
    STATUS     current
    DESCRIPTION
        "A free-form string that provides more information
        that is related to the ProtocolSupported by the
        Controller."
    ::= { msvmIDEControllerEntry 27 }

msvmidecProtocolSupported OBJECT-TYPE
    SYNTAX     Integer32
    MAX-ACCESS read-only
    STATUS     current
    DESCRIPTION
        "The protocol used by the Controller to access
        controlled Devices."
    ::= { msvmIDEControllerEntry 28 }

msvmidecRequestedState OBJECT-TYPE
    SYNTAX     INTEGER {
        enabled(2),
        disabled(3),
        shutDown(4),
        noChange(5),
        offline(6),
        test(7),
        deferred(8),
        quiesce(9),
        reboot(10),
        reset(11),
        notApplicable(12)
    }
    MAX-ACCESS read-only
    STATUS     current
    DESCRIPTION
        "RequestedState is an integer enumeration that
        indicates the last requested or desired state for
        the element. The actual state of the element is
        represented by EnabledState. This property is
        provided to compare the last requested and current
        enabled or disabled states. Note that when
        EnabledState is set to 5 ('Not Applicable'), then
        this property has no meaning. By default, the
        RequestedState of the element is 5 ('No Change').
        Refer to the EnabledState property description for
        explanations of the values in the RequestedState
        enumeration. 
        
        It should be noted that there are two new values in
        RequestedState that build on the statuses of
        EnabledState. These are 'Reboot' (10) and 'Reset'
        (11). Reboot refers to doing a 'Shut Down' and then
        moving to an 'Enabled' state. Reset indicates that
        the element is first 'Disabled' and then 'Enabled'.
        The distinction between requesting 'Shut Down' and
        'Disabled' should also be noted. Shut Down requests
        an orderly transition to the Disabled state, and
        might involve removing power, to completely erase
        any existing state. The Disabled state requests an
        immediate disabling of the element, such that it
        will not execute or accept any commands or
        processing requests. 
        
        This property is set as the result of a method
        invocation (such as Start or StopService on
        CIM_Service), or can be overridden and defined as
        WRITEable in a subclass. The method approach is
        considered superior to a WRITEable property,
        because it allows an explicit invocation of the
        operation and the return of a result code. 
        
        A particular instance of EnabledLogicalElement
        might not support RequestedStateChange. If this
        occurs, the value 12 ('Not Applicable') is used."
    ::= { msvmIDEControllerEntry 29 }

msvmidecStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmIDEControllerEntry 30 }

msvmidecStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmIDEControllerEntry 31 }

msvmidecStatusInfo OBJECT-TYPE
    SYNTAX     INTEGER {
        other(1),
        unknown(2),
        enabled(3),
        disabled(4),
        notApplicable(5)
    }
    MAX-ACCESS read-only
    STATUS     current
    DESCRIPTION
        "Note: The use of this method is deprecated in lieu
        of a more clearly named property (EnabledState)
        that is inherited from ManagedSystemElement and
        that has additional enumerated values. 
        Deprecated description: The StatusInfo property
        indicates whether the Logical Device is in an
        enabled state (value=3), disabled state (value=4),
        some other state (value=1), or an unknown state
        (value=2). If this property does not apply to the
        LogicalDevice, the value 5 ('Not Applicable')
        should be used. If a Device is
        ('Enabled')(value=3), it has been powered up and is
        configured and operational. The Device might or
        might not be functionally active, depending on
        whether its Availability (or
        AdditionalAvailability) indicates that it is
        ('Running/Full Power')(value=3) or ('Off line')
        (value=8). In an enabled but offline mode, a Device
        might be performing out-of-band requests, such as
        running Diagnostics. If StatusInfo is ('Disabled')
        (value=4), a Device can only be 'enabled' or
        powered off. In a personal computer environment,
        ('Disabled') means that the driver of the device is
        not available in the stack. In other environments,
        a Device can be disabled by removing its
        configuration file. A disabled device is physically
        present in a System and consuming resources, but it
        cannot be communicated with until a driver is
        loaded, a configuration file is loaded, or some
        other 'enabling' activity has occurred."
    ::= { msvmIDEControllerEntry 32 }

msvmidecSystemCreationClassName OBJECT-TYPE
    SYNTAX     WtcsDisplayString (SIZE (0..256))
    MAX-ACCESS read-only
    STATUS     current
    DESCRIPTION
        "The CreationClassName of the scoping system."
    ::= { msvmIDEControllerEntry 33 }

msvmidecSystemName OBJECT-TYPE
    SYNTAX     WtcsDisplayString (SIZE (0..256))
    MAX-ACCESS read-only
    STATUS     current
    DESCRIPTION
        "The System Name of the scoping system."
    ::= { msvmIDEControllerEntry 34 }

msvmidecTimeOfLastReset OBJECT-TYPE
    SYNTAX     DateAndTime
    MAX-ACCESS read-only
    STATUS     current
    DESCRIPTION
        "Time of last reset of the Controller."
    ::= { msvmIDEControllerEntry 35 }

msvmidecTimeOfLastStateChange OBJECT-TYPE
    SYNTAX     DateAndTime
    MAX-ACCESS read-only
    STATUS     current
    DESCRIPTION
        "The date or time when the EnabledState of the
        element last changed. If the state of the element
        has not changed and this property is populated,
        then it must be set to a 0 interval value. If a
        state change was requested, but rejected or not yet
        processed, the property must not be updated."
    ::= { msvmIDEControllerEntry 36 }

msvmidecTotalPowerOnHours OBJECT-TYPE
    SYNTAX     Gauge32
    UNITS "Hours"
    MAX-ACCESS read-only
    STATUS     current
    DESCRIPTION
        "Note: The use of this method is deprecated. 
        Deprecated description: The total number of hours
        that this Device has been powered on."
    ::= { msvmIDEControllerEntry 37 }

msvmImageManagementServiceTable OBJECT-TYPE
    SYNTAX     SEQUENCE OF MsvmImageManagementService
    MAX-ACCESS not-accessible
    STATUS     current
    DESCRIPTION
        "Manages the virtual media (.vhd, .iso, or .vfd
        files) for a virtual machine."
    ::= { msvmStorage 7 }

msvmImageManagementServiceEntry OBJECT-TYPE
    SYNTAX     MsvmImageManagementService
    MAX-ACCESS not-accessible
    STATUS     current
    DESCRIPTION
        "None"
    INDEX      { msvmimsIndex }
    ::= { msvmImageManagementServiceTable 1 }

MsvmImageManagementService ::= SEQUENCE {
    msvmimsIndex Integer32,
    msvmimsCaption WtcsDisplayString,
    msvmimsCreationClassName WtcsDisplayString,
    msvmimsDescription WtcsDisplayString,
    msvmimsElementName WtcsDisplayString,
    msvmimsEnabledDefault INTEGER,
    msvmimsEnabledState INTEGER,
    msvmimsHealthState INTEGER,
    msvmimsInstallDate DateAndTime,
    msvmimsName WtcsDisplayString,
    msvmimsOperationalStatus INTEGER,
    msvmimsOtherEnabledState WtcsDisplayString,
    msvmimsPrimaryOwnerContact WtcsDisplayString,
    msvmimsPrimaryOwnerName WtcsDisplayString,
    msvmimsRequestedState INTEGER,
    msvmimsStartMode WtcsDisplayString,
    msvmimsStarted TruthValue,
    msvmimsStatus WtcsDisplayString,
    msvmimsStatusDescriptions WtcsDisplayString,
    msvmimsSystemCreationClassName WtcsDisplayString,
    msvmimsSystemName WtcsDisplayString,
    msvmimsTimeOfLastStateChange DateAndTime
}

msvmimsIndex OBJECT-TYPE
    SYNTAX     Integer32 (1..2147483647)
    MAX-ACCESS read-only
    STATUS     current
    DESCRIPTION
        "The value of this object uniquely identifies the
        instance entry for this class."
    ::= { msvmImageManagementServiceEntry 1 }

msvmimsCaption OBJECT-TYPE
    SYNTAX     WtcsDisplayString (SIZE (0..64))
    MAX-ACCESS read-only
    STATUS     current
    DESCRIPTION
        "The Caption property is a short textual
        description (one- line string) of the object."
    ::= { msvmImageManagementServiceEntry 2 }

msvmimsCreationClassName OBJECT-TYPE
    SYNTAX     WtcsDisplayString (SIZE (0..256))
    MAX-ACCESS read-only
    STATUS     current
    DESCRIPTION
        "CreationClassName indicates the name of the class
        or the subclass that is used in the creation of an
        instance. When used with the other key properties
        of this class, this property allows all instances
        of this class and its subclasses to be uniquely
        identified."
    ::= { msvmImageManagementServiceEntry 3 }

msvmimsDescription OBJECT-TYPE
    SYNTAX     WtcsDisplayString
    MAX-ACCESS read-only
    STATUS     current
    DESCRIPTION
        "The Description property provides a textual
        description of the object."
    ::= { msvmImageManagementServiceEntry 4 }

msvmimsElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmImageManagementServiceEntry 5 }

msvmimsEnabledDefault OBJECT-TYPE
    SYNTAX     INTEGER {
        enabled(2),
        disabled(3),
        notApplicable(5),
        enabledbutOffline(6),
        noDefault(7)
    }
    MAX-ACCESS read-only
    STATUS     current
    DESCRIPTION
        "An enumerated value indicating an administrator's
        default or startup configuration for the Enabled
        State of an element. By default, the element is
        'Enabled' (value=2)."
    ::= { msvmImageManagementServiceEntry 6 }

msvmimsEnabledState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "EnabledState is an integer enumeration that
        indicates the enabled and disabled states of an
        element. It can also indicate the transitions
        between these requested states. For example,
        shutting down (value=4) and starting (value=10) are
        transient states between enabled and disabled. The
        following text briefly summarizes the various
        enabled and disabled states: 
        Enabled (2) indicates that the element is or could
        be executing commands, will process any queued
        commands, and queues new requests. 
        Disabled (3) indicates that the element will not
        execute commands and will drop any new requests. 
        Shutting Down (4) indicates that the element is in
        the process of going to a Disabled state. 
        Not Applicable (5) indicates the element does not
        support being enabled or disabled. 
        Enabled but Offline (6) indicates that the element
        might be completing commands, and will drop any new
        requests. 
        Test (7) indicates that the element is in a test
        state. 
        Deferred (8) indicates that the element might be
        completing commands, but will queue any new
        requests. 
        Quiesce (9) indicates that the element is enabled
        but in a restricted mode. The behavior of the
        element is similar to the Enabled state, but it
        processes only a restricted set of commands. All
        other requests are queued. 
        Starting (10) indicates that the element is in the
        process of going to an Enabled state. New requests
        are queued."
    ::= { msvmImageManagementServiceEntry 7 }

msvmimsHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmImageManagementServiceEntry 8 }

msvmimsInstallDate OBJECT-TYPE
    SYNTAX     DateAndTime
    MAX-ACCESS read-only
    STATUS     current
    DESCRIPTION
        "A datetime value that indicates when the object
        was installed. Lack of a value does not indicate
        that the object is not installed."
    ::= { msvmImageManagementServiceEntry 9 }

msvmimsName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmImageManagementServiceEntry 10 }

msvmimsOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmImageManagementServiceEntry 11 }

msvmimsOtherEnabledState OBJECT-TYPE
    SYNTAX     WtcsDisplayString
    MAX-ACCESS read-only
    STATUS     current
    DESCRIPTION
        "A string that describes the enabled or disabled
        state of the element when the EnabledState property
        is set to 1 ('Other'). This property must be set to
        null when EnabledState is any value other than 1."
    ::= { msvmImageManagementServiceEntry 12 }

msvmimsPrimaryOwnerContact OBJECT-TYPE
    SYNTAX     WtcsDisplayString (SIZE (0..256))
    MAX-ACCESS read-only
    STATUS     current
    DESCRIPTION
        "A string that provides information on how the
        primary owner of the Service can be reached (for
        example, phone number, e-mail address, and so on)."
    ::= { msvmImageManagementServiceEntry 13 }

msvmimsPrimaryOwnerName OBJECT-TYPE
    SYNTAX     WtcsDisplayString (SIZE (0..64))
    MAX-ACCESS read-only
    STATUS     current
    DESCRIPTION
        "The name of the primary owner for the service, if
        one is defined. The primary owner is the initial
        support contact for the Service."
    ::= { msvmImageManagementServiceEntry 14 }

msvmimsRequestedState OBJECT-TYPE
    SYNTAX     INTEGER {
        enabled(2),
        disabled(3),
        shutDown(4),
        noChange(5),
        offline(6),
        test(7),
        deferred(8),
        quiesce(9),
        reboot(10),
        reset(11),
        notApplicable(12)
    }
    MAX-ACCESS read-only
    STATUS     current
    DESCRIPTION
        "RequestedState is an integer enumeration that
        indicates the last requested or desired state for
        the element. The actual state of the element is
        represented by EnabledState. This property is
        provided to compare the last requested and current
        enabled or disabled states. Note that when
        EnabledState is set to 5 ('Not Applicable'), then
        this property has no meaning. By default, the
        RequestedState of the element is 5 ('No Change').
        Refer to the EnabledState property description for
        explanations of the values in the RequestedState
        enumeration. 
        
        It should be noted that there are two new values in
        RequestedState that build on the statuses of
        EnabledState. These are 'Reboot' (10) and 'Reset'
        (11). Reboot refers to doing a 'Shut Down' and then
        moving to an 'Enabled' state. Reset indicates that
        the element is first 'Disabled' and then 'Enabled'.
        The distinction between requesting 'Shut Down' and
        'Disabled' should also be noted. Shut Down requests
        an orderly transition to the Disabled state, and
        might involve removing power, to completely erase
        any existing state. The Disabled state requests an
        immediate disabling of the element, such that it
        will not execute or accept any commands or
        processing requests. 
        
        This property is set as the result of a method
        invocation (such as Start or StopService on
        CIM_Service), or can be overridden and defined as
        WRITEable in a subclass. The method approach is
        considered superior to a WRITEable property,
        because it allows an explicit invocation of the
        operation and the return of a result code. 
        
        A particular instance of EnabledLogicalElement
        might not support RequestedStateChange. If this
        occurs, the value 12 ('Not Applicable') is used."
    ::= { msvmImageManagementServiceEntry 15 }

msvmimsStartMode OBJECT-TYPE
    SYNTAX     WtcsDisplayString (SIZE (0..10))
    MAX-ACCESS read-only
    STATUS     current
    DESCRIPTION
        "Note: The use of this element is deprecated in
        lieu of the EnabledDefault property that is
        inherited from EnabledLogicalElement. The
        EnabledLogicalElement addresses the same semantics.
        The change to a uint16 data type was discussed when
        CIM V2.0 was defined. However, existing V1.0
        implementations used the string property. To remain
        compatible with those implementations, StartMode
        was grandfathered into the schema. Use of the
        deprecated qualifier allows the maintenance of the
        existing property but also permits an improved,
        clarified definition using EnabledDefault. 
        Deprecated description: StartMode is a string value
        that indicates whether the Service is automatically
        started by a System, an Operating System, and so
        on, or is started only upon request."
    ::= { msvmImageManagementServiceEntry 16 }

msvmimsStarted OBJECT-TYPE
    SYNTAX     TruthValue
    MAX-ACCESS read-only
    STATUS     current
    DESCRIPTION
        "Started is a Boolean that indicates whether the
        Service has been started (TRUE), or stopped
        (FALSE)."
    ::= { msvmImageManagementServiceEntry 17 }

msvmimsStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmImageManagementServiceEntry 18 }

msvmimsStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmImageManagementServiceEntry 19 }

msvmimsSystemCreationClassName OBJECT-TYPE
    SYNTAX     WtcsDisplayString (SIZE (0..256))
    MAX-ACCESS read-only
    STATUS     current
    DESCRIPTION
        "The CreationClassName of the scoping System."
    ::= { msvmImageManagementServiceEntry 20 }

msvmimsSystemName OBJECT-TYPE
    SYNTAX     WtcsDisplayString (SIZE (0..256))
    MAX-ACCESS read-only
    STATUS     current
    DESCRIPTION
        "The Name of the scoping System."
    ::= { msvmImageManagementServiceEntry 21 }

msvmimsTimeOfLastStateChange OBJECT-TYPE
    SYNTAX     DateAndTime
    MAX-ACCESS read-only
    STATUS     current
    DESCRIPTION
        "The date or time when the EnabledState of the
        element last changed. If the state of the element
        has not changed and this property is populated,
        then it must be set to a 0 interval value. If a
        state change was requested, but rejected or not yet
        processed, the property must not be updated."
    ::= { msvmImageManagementServiceEntry 22 }

msvmLogicalDiskTable OBJECT-TYPE
    SYNTAX     SEQUENCE OF MsvmLogicalDisk
    MAX-ACCESS not-accessible
    STATUS     current
    DESCRIPTION
        "Represents storage drive media and is used to
        populate the storage drives. The media types
        supported include virtual hard files, virtual
        floppy files, ISO files, and physical device
        media."
    ::= { msvmStorage 8 }

msvmLogicalDiskEntry OBJECT-TYPE
    SYNTAX     MsvmLogicalDisk
    MAX-ACCESS not-accessible
    STATUS     current
    DESCRIPTION
        "None"
    INDEX      { msvmldIndex }
    ::= { msvmLogicalDiskTable 1 }

MsvmLogicalDisk ::= SEQUENCE {
    msvmldIndex Integer32,
    msvmldAccess INTEGER,
    msvmldAdditionalAvailability INTEGER,
    msvmldAvailability INTEGER,
    msvmldBlockSize Gauge32,
    msvmldCaption WtcsDisplayString,
    msvmldConsumableBlocks Gauge32,
    msvmldCreationClassName WtcsDisplayString,
    msvmldDataOrganization INTEGER,
    msvmldDataRedundancy Integer32,
    msvmldDeltaReservation Integer32,
    msvmldDescription WtcsDisplayString,
    msvmldDeviceID WtcsDisplayString,
    msvmldElementName WtcsDisplayString,
    msvmldEnabledDefault INTEGER,
    msvmldEnabledState INTEGER,
    msvmldErrorCleared TruthValue,
    msvmldErrorDescription WtcsDisplayString,
    msvmldErrorMethodology WtcsDisplayString,
    msvmldExtentStatus INTEGER,
    msvmldHealthState INTEGER,
    msvmldIdentifyingDescriptions WtcsDisplayString,
    msvmldInstallDate DateAndTime,
    msvmldIsBasedOnUnderlyingRedund TruthValue,
    msvmldLastErrorCode Gauge32,
    msvmldLocationIndicator INTEGER,
    msvmldMaxQuiesceTime Gauge32,
    msvmldName WtcsDisplayString,
    msvmldNameFormat INTEGER,
    msvmldNameNamespace INTEGER,
    msvmldNoSinglePointOfFailure TruthValue,
    msvmldNumberOfBlocks Gauge32,
    msvmldOperationalStatus INTEGER,
    msvmldOtherEnabledState WtcsDisplayString,
    msvmldOtherIdentifyingInfo WtcsDisplayString,
    msvmldOtherNameFormat WtcsDisplayString,
    msvmldOtherNameNamespace WtcsDisplayString,
    msvmldPackageRedundancy Integer32,
    msvmldPowerManagementCapability INTEGER,
    msvmldPowerManagementSupported TruthValue,
    msvmldPowerOnHours Gauge32,
    msvmldPrimordial TruthValue,
    msvmldPurpose WtcsDisplayString,
    msvmldRequestedState INTEGER,
    msvmldSequentialAccess TruthValue,
    msvmldStatus WtcsDisplayString,
    msvmldStatusDescriptions WtcsDisplayString,
    msvmldStatusInfo INTEGER,
    msvmldSystemCreationClassName WtcsDisplayString,
    msvmldSystemName WtcsDisplayString,
    msvmldTimeOfLastStateChange DateAndTime,
    msvmldTotalPowerOnHours Gauge32
}

msvmldIndex OBJECT-TYPE
    SYNTAX     Integer32 (1..2147483647)
    MAX-ACCESS read-only
    STATUS     current
    DESCRIPTION
        "The value of this object uniquely identifies the
        instance entry for this class."
    ::= { msvmLogicalDiskEntry 1 }

msvmldAccess OBJECT-TYPE
    SYNTAX     INTEGER {
        unknown(0),
        readable(1),
        writeable(2),
        readWriteSupported(3),
        writeOnce(4)
    }
    MAX-ACCESS read-only
    STATUS     current
    DESCRIPTION
        "Access describes whether the media is readable
        (value=1), writeable (value=2), or both (value=3).
        'Unknown' (0) and 'Write Once' (4) can also be
        defined."
    ::= { msvmLogicalDiskEntry 2 }

msvmldAdditionalAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Additional availability and status of the Device
        in addition to that specified in the Availability
        property. The Availability property denotes the
        primary status and availability of the Device. In
        some cases, this property will not be sufficient to
        denote the complete status of the Device. In those
        cases, the AdditionalAvailability property can be
        used to provide further information. For example,
        the primary Availability of a device might be 'Off
        line' (value=8) or in a low-power state
        (AdditionalAvailability value=14), or the Device
        could be running Diagnostics
        (AdditionalAvailability value=5, 'In Test')."
    ::= { msvmLogicalDiskEntry 3 }

msvmldAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Note: The use of this property has been
        deprecated. 
        Deprecated description: The primary availability
        and status of the Device. (Additional status
        information can be specified using the Additional
        Availability array property.) For example, the
        Availability property indicates that the Device is
        running and has full power (value=3), or is in a
        warning (4), test (5), degraded (10) or power save
        state (values 13-15 and 17). The Power Save states
        are defined as follows: Value 13 ('Power Save -
        Unknown') indicates that the Device is known to be
        in a power save mode, but its exact status in this
        mode is unknown; value 14 ('Power Save - Low Power
        Mode') indicates that the Device is in a power save
        state but still functioning, and might exhibit
        degraded performance; value 15 ('Power Save -
        Standby') indicates that the Device is not
        functioning but could be brought to full power
        'quickly'; and value 17 ('Power Save - Warning')
        indicates that the Device is in a warning state,
        but is also in a power save mode."
    ::= { msvmLogicalDiskEntry 4 }

msvmldBlockSize OBJECT-TYPE
    SYNTAX     Gauge32
    UNITS "Bytes"
    MAX-ACCESS read-only
    STATUS     current
    DESCRIPTION
        "Size in bytes of the blocks which form this
        StorageExtent. If variable block size, then the
        maximum block size in bytes should be specified. If
        the block size is unknown or if a block concept is
        not valid (for example, for AggregateExtents,
        Memory or LogicalDisks), enter a 1."
    ::= { msvmLogicalDiskEntry 5 }

msvmldCaption OBJECT-TYPE
    SYNTAX     WtcsDisplayString (SIZE (0..64))
    MAX-ACCESS read-only
    STATUS     current
    DESCRIPTION
        "The Caption property is a short textual
        description (one- line string) of the object."
    ::= { msvmLogicalDiskEntry 6 }

msvmldConsumableBlocks OBJECT-TYPE
    SYNTAX     Gauge32
    MAX-ACCESS read-only
    STATUS     current
    DESCRIPTION
        "The maximum number of blocks, of size BlockSize,
        which are available for consumption when layering
        StorageExtents using the BasedOn association. This
        property only has meaning when this StorageExtent
        is an Antecedent reference in a BasedOn
        relationship. For example, a StorageExtent could be
        composed of 120 blocks. However, the Extent itself
        may use 20 blocks for redundancy data. If another
        StorageExtent is BasedOn this Extent, only 100
        blocks would be available to it. This information
        ('100 blocks is available for consumption') is
        indicated in the ConsumableBlocks property."
    ::= { msvmLogicalDiskEntry 7 }

msvmldCreationClassName OBJECT-TYPE
    SYNTAX     WtcsDisplayString (SIZE (0..256))
    MAX-ACCESS read-only
    STATUS     current
    DESCRIPTION
        "CreationClassName indicates the name of the class
        or the subclass used in the creation of an
        instance. When used with the other key properties
        of this class, this property allows all instances
        of this class and its subclasses to be uniquely
        identified."
    ::= { msvmLogicalDiskEntry 8 }

msvmldDataOrganization OBJECT-TYPE
    SYNTAX     INTEGER {
        other(0),
        unknown(1),
        fixedBlock(2),
        variableBlock(3),
        countKeyData(4)
    }
    MAX-ACCESS read-only
    STATUS     current
    DESCRIPTION
        "Type of data organization used."
    ::= { msvmLogicalDiskEntry 9 }

msvmldDataRedundancy OBJECT-TYPE
    SYNTAX     Integer32
    MAX-ACCESS read-only
    STATUS     current
    DESCRIPTION
        "Number of complete copies of data currently
        maintained."
    ::= { msvmLogicalDiskEntry 10 }

msvmldDeltaReservation OBJECT-TYPE
    SYNTAX     Integer32
    UNITS "Percentage"
    MAX-ACCESS read-only
    STATUS     current
    DESCRIPTION
        "Current value for Delta reservation. This is a
        percentage that specifies the amount of space that
        should be reserved in a replica for caching
        changes."
    ::= { msvmLogicalDiskEntry 11 }

msvmldDescription OBJECT-TYPE
    SYNTAX     WtcsDisplayString
    MAX-ACCESS read-only
    STATUS     current
    DESCRIPTION
        "The Description property provides a textual
        description of the object."
    ::= { msvmLogicalDiskEntry 12 }

msvmldDeviceID OBJECT-TYPE
    SYNTAX     WtcsDisplayString (SIZE (0..64))
    MAX-ACCESS read-only
    STATUS     current
    DESCRIPTION
        "An address or other identifying information used
        to uniquely name the LogicalDevice."
    ::= { msvmLogicalDiskEntry 13 }

msvmldElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmLogicalDiskEntry 14 }

msvmldEnabledDefault OBJECT-TYPE
    SYNTAX     INTEGER {
        enabled(2),
        disabled(3),
        notApplicable(5),
        enabledbutOffline(6),
        noDefault(7)
    }
    MAX-ACCESS read-only
    STATUS     current
    DESCRIPTION
        "An enumerated value indicating an administrator's
        default or startup configuration for the Enabled
        State of an element. By default, the element is
        'Enabled' (value=2)."
    ::= { msvmLogicalDiskEntry 15 }

msvmldEnabledState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "EnabledState is an integer enumeration that
        indicates the enabled and disabled states of an
        element. It can also indicate the transitions
        between these requested states. For example,
        shutting down (value=4) and starting (value=10) are
        transient states between enabled and disabled. The
        following text briefly summarizes the various
        enabled and disabled states: 
        Enabled (2) indicates that the element is or could
        be executing commands, will process any queued
        commands, and queues new requests. 
        Disabled (3) indicates that the element will not
        execute commands and will drop any new requests. 
        Shutting Down (4) indicates that the element is in
        the process of going to a Disabled state. 
        Not Applicable (5) indicates the element does not
        support being enabled or disabled. 
        Enabled but Offline (6) indicates that the element
        might be completing commands, and will drop any new
        requests. 
        Test (7) indicates that the element is in a test
        state. 
        Deferred (8) indicates that the element might be
        completing commands, but will queue any new
        requests. 
        Quiesce (9) indicates that the element is enabled
        but in a restricted mode. The behavior of the
        element is similar to the Enabled state, but it
        processes only a restricted set of commands. All
        other requests are queued. 
        Starting (10) indicates that the element is in the
        process of going to an Enabled state. New requests
        are queued."
    ::= { msvmLogicalDiskEntry 16 }

msvmldErrorCleared OBJECT-TYPE
    SYNTAX     TruthValue
    MAX-ACCESS read-only
    STATUS     current
    DESCRIPTION
        "Note: The use of this method is deprecated. 
        Deprecated description: ErrorCleared is a Boolean
        property that indicates that the error reported in
        LastErrorCode is now cleared."
    ::= { msvmLogicalDiskEntry 17 }

msvmldErrorDescription OBJECT-TYPE
    SYNTAX     WtcsDisplayString
    MAX-ACCESS read-only
    STATUS     current
    DESCRIPTION
        "Note: The use of this method is deprecated. 
        Deprecated description: ErrorDescription is a
        free-form string that supplies more information
        about the error recorded in LastErrorCode and
        information on any corrective actions that can be
        taken."
    ::= { msvmLogicalDiskEntry 18 }

msvmldErrorMethodology OBJECT-TYPE
    SYNTAX     WtcsDisplayString
    MAX-ACCESS read-only
    STATUS     current
    DESCRIPTION
        "ErrorMethodology is a free-form string describing
        the type of error detection and correction
        supported by this StorageExtent."
    ::= { msvmLogicalDiskEntry 19 }

msvmldExtentStatus OBJECT-TYPE
    SYNTAX     INTEGER {
        other(0),
        unknown(1),
        noneNotApplicable(2),
        broken(3),
        dataLost(4),
        dynamicReconfig(5),
        exposed(6),
        fractionallyExposed(7),
        partiallyExposed(8),
        protectionDisabled(9),
        readying(10),
        rebuild(11),
        recalculate(12),
        spareinUse(13),
        verifyInProgress(14),
        inBandAccessGranted(15),
        imported(16),
        exported(17)
    }
    MAX-ACCESS read-only
    STATUS     current
    DESCRIPTION
        "StorageExtents have additional status information
        beyond that captured in the OperationalStatus and
        other properties, inherited from
        ManagedSystemElement. This additional information
        (for example, 'Protection Disabled', value=9) is
        captured in the ExtentStatus property. 
        'In-Band Access Granted' says that access to data
        on an extent is granted to some consumer and is
        only valid when 'Exported' is also set. It is set
        as a side effect of
        PrivilegeManagementService.ChangeAccess or
        equivalent interfaces. 
        'Imported' indicates that the extent is used in the
        current system, but known to be managed by some
        other system. For example, a server imports volumes
        from a disk array. 
        'Exported' indicates the extent is meant to be used
        by some comsumer. A disk array's logical units are
        exported. 
        Intermediate composite extents may be neither
        imported nor exported."
    ::= { msvmLogicalDiskEntry 20 }

msvmldHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmLogicalDiskEntry 21 }

msvmldIdentifyingDescriptions OBJECT-TYPE
    SYNTAX     WtcsDisplayString
    MAX-ACCESS read-only
    STATUS     current
    DESCRIPTION
        "An array of free-form strings providing
        explanations and details behind the entries in the
        OtherIdentifyingInfo array. Note that each entry of
        this array is related to the entry in
        OtherIdentifyingInfo that is located at the same
        index."
    ::= { msvmLogicalDiskEntry 22 }

msvmldInstallDate OBJECT-TYPE
    SYNTAX     DateAndTime
    MAX-ACCESS read-only
    STATUS     current
    DESCRIPTION
        "A datetime value that indicates when the object
        was installed. Lack of a value does not indicate
        that the object is not installed."
    ::= { msvmLogicalDiskEntry 23 }

msvmldIsBasedOnUnderlyingRedund OBJECT-TYPE
    SYNTAX     TruthValue
    MAX-ACCESS read-only
    STATUS     current
    DESCRIPTION
        "True indicates that the underlying
        StorageExtent(s) participate in a
        StorageRedundancyGroup."
    ::= { msvmLogicalDiskEntry 24 }

msvmldLastErrorCode OBJECT-TYPE
    SYNTAX     Gauge32
    MAX-ACCESS read-only
    STATUS     current
    DESCRIPTION
        "Note: The use of this method is deprecated. 
        Deprecated description: LastErrorCode captures the
        last error code reported by the LogicalDevice."
    ::= { msvmLogicalDiskEntry 25 }

msvmldLocationIndicator OBJECT-TYPE
    SYNTAX     INTEGER {
        unknown(0),
        on(2),
        off(3),
        notSupported(4)
    }
    MAX-ACCESS read-only
    STATUS     current
    DESCRIPTION
        "An integer that reflects the state of an indicator
        (e.g., LED) that is part of a device. Reading the
        value gives the current state. Writing the value
        with 'On'/'Off' turns the indicator on/off, other
        values may not be written."
    ::= { msvmLogicalDiskEntry 26 }

msvmldMaxQuiesceTime OBJECT-TYPE
    SYNTAX     Gauge32
    UNITS "MilliSeconds"
    MAX-ACCESS read-only
    STATUS     current
    DESCRIPTION
        "Note: The use of this property has been
        deprecated. When evaluating the use of Quiesce, it
        was determined that this single property is not
        adequate for describing when a device will
        automatically exit a quiescent state. In fact, the
        most likely scenario for a device to exit a
        quiescent state was determined to be based on the
        number of outstanding requests queued rather than
        on a maximum time. This decision will be
        re-evaluated and repositioned later. 
        Deprecated description: Maximum time, in
        milliseconds, that a Device can run in a 'Quiesced'
        state. The state is defined in its Availability and
        AdditionalAvailability properties, where 'Quiesced'
        is conveyed by the value 21. What occurs at the end
        of the time limit is device-specific. The Device
        can unquiesce, can be offline, or can take other
        actions. A value of 0 indicates that a Device can
        remain quiesced indefinitely."
    ::= { msvmLogicalDiskEntry 27 }

msvmldName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmLogicalDiskEntry 28 }

msvmldNameFormat OBJECT-TYPE
    SYNTAX     INTEGER {
        unknown(0),
        other(1),
        vpd83NAA6(2),
        vpd83NAA5(3),
        vpd83Type2(4),
        vpd83Type1(5),
        vpd83Type0(6),
        snvm(7),
        nodeWWN(8),
        naa(9),
        eui64(10),
        t10VID(11),
        osDeviceName(12)
    }
    MAX-ACCESS read-only
    STATUS     current
    DESCRIPTION
        "The list here applies to all StorageExtent
        subclasses. Please look at the Description in each
        subclass for guidelines on the approriate values
        for that subclass. Note that any of these formats
        could apply to a CompositeExtent. 
        
        Note - this property originally touched on two
        concepts that are now separated into this property
        and NameNamespace. Values 2,3,4,5,6, and 8 are
        retained for backwards compatibility but are
        deprecated in lieu of the corresponding values in
        CIM_StorageExtent.NameNamespace. 
        
        For example, the preferred source for SCSI virtual
        (RAID) disk names is from Inquiry VPD page 83
        response, type 3 identifiers. These will have
        NameFormat set to 'NAA' and NameNamespace to
        'VPD83Type3'. 
        
        Format of the Name property. Values for extents
        representing SCSI volumes are (per SCSI SPC-3): 
        2 = VPD Page 83, NAA IEEE Registered Extended
        (VPD83NAA6) 
        (DEPRECATED) 
        3 = VPD Page 83, NAA IEEE Registered (VPD83NAA5) 
        (DEPRECATED) 
        4 = VPD Page 83, (VPD83Type2) (DEPRECATED) 
        5 = VPD Page 83, 
        T10 Vendor Identification (VPD83Type1) (DEPRECATED)
        
        6 = VPD Page 83, Vendor Specific (VPD83Type0)
        (DEPRECATED) 
        7 = Serial Number/Vendor/Model (SNVM) SNVM is 3
        strings representing the vendor name, product name
        within the vendor namespace, and the serial number
        within the model namespace. Strings are delimited
        with a '+'. Spaces may be included and are
        significant. The serial number is the text
        representation of the serial number in hexadecimal
        upper case. This represents the vendor and model ID
        from SCSI Inquiry data; the vendor field MUST be 8
        characters wide and the product field MUST be 16
        characters wide. For example, 
        'ACME____+SUPER DISK______+124437458' (_ is a space
        character) 
        8 = Node WWN (for single LUN/controller) (NodeWWN) 
        (DEPRECATED) 
        9 = NAA as a generic format. See 
        http://standards.ieee.org/regauth/oui/tutorials/fib
        recomp_id.html. Formatted as 16 or 32 unseparated
        uppercase hex characters (2 per binary byte). For
        example '21000020372D3C73' 
        10 = EUI as a generic format (EUI64) See 
        http://standards.ieee.org/regauth/oui/tutorials/EUI
        64.html. 
        Formatted as 16 unseparated uppercase hex
        characters (2 per binary byte) 
        11 = T10 vendor identifier format as returned by
        SCSI Inquiry VPD page 83, identifier type 1. See
        T10 SPC-3 specification. This is the 8-byte ASCII
        vendor ID from the T10 registry followed by a
        vendor specific ASCII identifier; spaces are
        permitted. For non SCSI volumes, 'SNVM' may be the
        most appropriate choice. 12 = OS Device Name (for
        LogicalDisks). See LogicalDisk Name description for
        details."
    ::= { msvmLogicalDiskEntry 29 }

msvmldNameNamespace OBJECT-TYPE
    SYNTAX     INTEGER {
        unknown(0),
        other(1),
        vpd83Type3(2),
        vpd83Type2(3),
        vpd83Type1(4),
        vpd80(5),
        nodeWWN(6),
        snvm(7),
        osDeviceNamespace(8)
    }
    MAX-ACCESS read-only
    STATUS     current
    DESCRIPTION
        "The preferred source SCSI for volume names is SCSI
        VPD Page 83 responses. Page 83 returns a list of
        identifiers for various device elements. The
        metadata for each identifier includes an
        Association field, identifiers with association of
        0 apply to volumes. Page 83 supports several
        namespaces specified in the Type field in the
        identifier metadata. See SCSI SPC-3 specification. 
        2 = VPD Page 83, Type 3 NAA (NameFormat SHOULD be
        NAA) 
        3 = VPD Page 83, Type 2 EUI64 (NameFormat EUI) 
        4 = VPD Page 83, Type 1 T10 Vendor Identification 
        (NameFormat T10) 
        Less preferred volume namespaces from other
        interfaces: 
        5 = VPD page 80, Serial number (NameFormat SHOULD
        be Other) 
        6 = FC NodeWWN (NameFormat SHOULD be NAA or EUI) 
        7 = Serial Number/Vendor/Model (NameFormat SHOULD
        be SNVM) 
        The preferred namespace for LogigicalDisk names is
        platform specific device namespace; see
        LogigicalDIsk Description. 
        8 = OS Device Namespace."
    ::= { msvmLogicalDiskEntry 30 }

msvmldNoSinglePointOfFailure OBJECT-TYPE
    SYNTAX     TruthValue
    MAX-ACCESS read-only
    STATUS     current
    DESCRIPTION
        "Indicates whether or not there exists no single
        point of failure."
    ::= { msvmLogicalDiskEntry 31 }

msvmldNumberOfBlocks OBJECT-TYPE
    SYNTAX     Gauge32
    MAX-ACCESS read-only
    STATUS     current
    DESCRIPTION
        "Total number of logically contiguous blocks, of
        size Block Size, which form this Extent. The total
        size of the Extent can be calculated by multiplying
        BlockSize by NumberOfBlocks. If the BlockSize is 1,
        this property is the total size of the Extent."
    ::= { msvmLogicalDiskEntry 32 }

msvmldOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmLogicalDiskEntry 33 }

msvmldOtherEnabledState OBJECT-TYPE
    SYNTAX     WtcsDisplayString
    MAX-ACCESS read-only
    STATUS     current
    DESCRIPTION
        "A string that describes the enabled or disabled
        state of the element when the EnabledState property
        is set to 1 ('Other'). This property must be set to
        null when EnabledState is any value other than 1."
    ::= { msvmLogicalDiskEntry 34 }

msvmldOtherIdentifyingInfo OBJECT-TYPE
    SYNTAX     WtcsDisplayString (SIZE (0..256))
    MAX-ACCESS read-only
    STATUS     current
    DESCRIPTION
        "OtherIdentifyingInfo captures data, in addition to
        DeviceID information, that could be used to
        identify a LogicalDevice. For example, you could
        use this property to hold the operating system's
        user-friendly name for the Device."
    ::= { msvmLogicalDiskEntry 35 }

msvmldOtherNameFormat OBJECT-TYPE
    SYNTAX     WtcsDisplayString
    MAX-ACCESS read-only
    STATUS     current
    DESCRIPTION
        "A string describing the format of the Name
        property when NameFormat includes the value 1,
        'Other'."
    ::= { msvmLogicalDiskEntry 36 }

msvmldOtherNameNamespace OBJECT-TYPE
    SYNTAX     WtcsDisplayString
    MAX-ACCESS read-only
    STATUS     current
    DESCRIPTION
        "A string describing the namespace of the Name
        property when NameNamespace includes the value 1,
        'Other'."
    ::= { msvmLogicalDiskEntry 37 }

msvmldPackageRedundancy OBJECT-TYPE
    SYNTAX     Integer32
    MAX-ACCESS read-only
    STATUS     current
    DESCRIPTION
        "How many physical packages can currently fail
        without data loss. For example, in the storage
        domain, this might be disk spindles."
    ::= { msvmLogicalDiskEntry 38 }

msvmldPowerManagementCapability OBJECT-TYPE
    SYNTAX     INTEGER {
        unknown(0),
        notSupported(1),
        disabled(2),
        enabled(3),
        powerSavingModesEnteredAutomatic(4),
        powerStateSettable(5),
        powerCyclingSupported(6),
        timedPowerOnSupported(7)
    }
    MAX-ACCESS read-only
    STATUS     current
    DESCRIPTION
        "Note: The use of this property has been
        deprecated. Instead, use the PowerCapabilites
        property in an associated
        PowerManagementCapabilities class. Deprecated
        description: An enumerated array describing the
        power management capabilities of the Device."
    ::= { msvmLogicalDiskEntry 39 }

msvmldPowerManagementSupported OBJECT-TYPE
    SYNTAX     TruthValue
    MAX-ACCESS read-only
    STATUS     current
    DESCRIPTION
        "Note: The use of this property has been
        deprecated. Instead, the existence of an associated
        PowerManagementCapabilities class (associated using
        the ElementCapabilities relationship) indicates
        that power management is supported. Deprecated
        description: Boolean that indicates that the Device
        can use power management."
    ::= { msvmLogicalDiskEntry 40 }

msvmldPowerOnHours OBJECT-TYPE
    SYNTAX     Gauge32
    UNITS "Hours"
    MAX-ACCESS read-only
    STATUS     current
    DESCRIPTION
        "Note: The use of this method is deprecated. 
        Deprecated description: The number of consecutive
        hours that this Device has been powered on since
        its last power cycle."
    ::= { msvmLogicalDiskEntry 41 }

msvmldPrimordial OBJECT-TYPE
    SYNTAX     TruthValue
    MAX-ACCESS read-only
    STATUS     current
    DESCRIPTION
        "If true, 'Primordial' indicates that the
        containing System does not have the ability to
        create or delete this operational element. This is
        important because StorageExtents are assembled into
        higher-level abstractions using the BasedOn
        association. Although the higher-level abstractions
        can be created and deleted, the most basic, (i.e.
        primordial), hardware-based storage entities
        cannot. They are physically realized as part of the
        System, or are actually managed by some other
        System and imported as if they were physically
        realized. In other words, a Primordial
        StorageExtent exists in, but is not created by its
        System and conversely a non-Primordial
        StorageExtent is created in the context of its
        System. For StorageVolumes, this property will
        generally be false. One use of this property is to
        enable algorithms that aggregate
        StorageExtent.ConsumableSpace across all,
        StorageExtents but that also want to distinquish
        the space that underlies Primordial StoragePools.
        Since implementations are not required to surface
        all Component StorageExtents of a StoragePool, this
        information is not accessible in any other way."
    ::= { msvmLogicalDiskEntry 42 }

msvmldPurpose OBJECT-TYPE
    SYNTAX     WtcsDisplayString
    MAX-ACCESS read-only
    STATUS     current
    DESCRIPTION
        "A free form string describing the media and/or its
        use."
    ::= { msvmLogicalDiskEntry 43 }

msvmldRequestedState OBJECT-TYPE
    SYNTAX     INTEGER {
        enabled(2),
        disabled(3),
        shutDown(4),
        noChange(5),
        offline(6),
        test(7),
        deferred(8),
        quiesce(9),
        reboot(10),
        reset(11),
        notApplicable(12)
    }
    MAX-ACCESS read-only
    STATUS     current
    DESCRIPTION
        "RequestedState is an integer enumeration that
        indicates the last requested or desired state for
        the element. The actual state of the element is
        represented by EnabledState. This property is
        provided to compare the last requested and current
        enabled or disabled states. Note that when
        EnabledState is set to 5 ('Not Applicable'), then
        this property has no meaning. By default, the
        RequestedState of the element is 5 ('No Change').
        Refer to the EnabledState property description for
        explanations of the values in the RequestedState
        enumeration. 
        
        It should be noted that there are two new values in
        RequestedState that build on the statuses of
        EnabledState. These are 'Reboot' (10) and 'Reset'
        (11). Reboot refers to doing a 'Shut Down' and then
        moving to an 'Enabled' state. Reset indicates that
        the element is first 'Disabled' and then 'Enabled'.
        The distinction between requesting 'Shut Down' and
        'Disabled' should also be noted. Shut Down requests
        an orderly transition to the Disabled state, and
        might involve removing power, to completely erase
        any existing state. The Disabled state requests an
        immediate disabling of the element, such that it
        will not execute or accept any commands or
        processing requests. 
        
        This property is set as the result of a method
        invocation (such as Start or StopService on
        CIM_Service), or can be overridden and defined as
        WRITEable in a subclass. The method approach is
        considered superior to a WRITEable property,
        because it allows an explicit invocation of the
        operation and the return of a result code. 
        
        A particular instance of EnabledLogicalElement
        might not support RequestedStateChange. If this
        occurs, the value 12 ('Not Applicable') is used."
    ::= { msvmLogicalDiskEntry 44 }

msvmldSequentialAccess OBJECT-TYPE
    SYNTAX     TruthValue
    MAX-ACCESS read-only
    STATUS     current
    DESCRIPTION
        "Boolean set to TRUE if the Storage is sequentially
        accessed by a MediaAccessDevice. A TapePartition is
        an example of a sequentially accessed
        StorageExtent. StorageVolumes, Disk Partitions and
        LogicalDisks represent randomly accessed Extents."
    ::= { msvmLogicalDiskEntry 45 }

msvmldStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmLogicalDiskEntry 46 }

msvmldStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmLogicalDiskEntry 47 }

msvmldStatusInfo OBJECT-TYPE
    SYNTAX     INTEGER {
        other(1),
        unknown(2),
        enabled(3),
        disabled(4),
        notApplicable(5)
    }
    MAX-ACCESS read-only
    STATUS     current
    DESCRIPTION
        "Note: The use of this method is deprecated in lieu
        of a more clearly named property (EnabledState)
        that is inherited from ManagedSystemElement and
        that has additional enumerated values. 
        Deprecated description: The StatusInfo property
        indicates whether the Logical Device is in an
        enabled state (value=3), disabled state (value=4),
        some other state (value=1), or an unknown state
        (value=2). If this property does not apply to the
        LogicalDevice, the value 5 ('Not Applicable')
        should be used. If a Device is
        ('Enabled')(value=3), it has been powered up and is
        configured and operational. The Device might or
        might not be functionally active, depending on
        whether its Availability (or
        AdditionalAvailability) indicates that it is
        ('Running/Full Power')(value=3) or ('Off line')
        (value=8). In an enabled but offline mode, a Device
        might be performing out-of-band requests, such as
        running Diagnostics. If StatusInfo is ('Disabled')
        (value=4), a Device can only be 'enabled' or
        powered off. In a personal computer environment,
        ('Disabled') means that the driver of the device is
        not available in the stack. In other environments,
        a Device can be disabled by removing its
        configuration file. A disabled device is physically
        present in a System and consuming resources, but it
        cannot be communicated with until a driver is
        loaded, a configuration file is loaded, or some
        other 'enabling' activity has occurred."
    ::= { msvmLogicalDiskEntry 48 }

msvmldSystemCreationClassName OBJECT-TYPE
    SYNTAX     WtcsDisplayString (SIZE (0..256))
    MAX-ACCESS read-only
    STATUS     current
    DESCRIPTION
        "The CreationClassName of the scoping system."
    ::= { msvmLogicalDiskEntry 49 }

msvmldSystemName OBJECT-TYPE
    SYNTAX     WtcsDisplayString (SIZE (0..256))
    MAX-ACCESS read-only
    STATUS     current
    DESCRIPTION
        "The System Name of the scoping system."
    ::= { msvmLogicalDiskEntry 50 }

msvmldTimeOfLastStateChange OBJECT-TYPE
    SYNTAX     DateAndTime
    MAX-ACCESS read-only
    STATUS     current
    DESCRIPTION
        "The date or time when the EnabledState of the
        element last changed. If the state of the element
        has not changed and this property is populated,
        then it must be set to a 0 interval value. If a
        state change was requested, but rejected or not yet
        processed, the property must not be updated."
    ::= { msvmLogicalDiskEntry 51 }

msvmldTotalPowerOnHours OBJECT-TYPE
    SYNTAX     Gauge32
    UNITS "Hours"
    MAX-ACCESS read-only
    STATUS     current
    DESCRIPTION
        "Note: The use of this method is deprecated. 
        Deprecated description: The total number of hours
        that this Device has been powered on."
    ::= { msvmLogicalDiskEntry 52 }

msvmMediaPresentTable OBJECT-TYPE
    SYNTAX     SEQUENCE OF MsvmMediaPresent
    MAX-ACCESS not-accessible
    STATUS     current
    DESCRIPTION
        "Associates a storage drive with the media inserted
        into the drive. This association is used for all
        storage drive objects."
    ::= { msvmStorage 9 }

msvmMediaPresentEntry OBJECT-TYPE
    SYNTAX     MsvmMediaPresent
    MAX-ACCESS not-accessible
    STATUS     current
    DESCRIPTION
        "None"
    INDEX      { msvmmpIndex }
    ::= { msvmMediaPresentTable 1 }

MsvmMediaPresent ::= SEQUENCE {
    msvmmpIndex Integer32,
    msvmmpAntecedent WtcsDisplayString,
    msvmmpDependent WtcsDisplayString,
    msvmmpFixedMedia TruthValue
}

msvmmpIndex OBJECT-TYPE
    SYNTAX     Integer32 (1..2147483647)
    MAX-ACCESS read-only
    STATUS     current
    DESCRIPTION
        "The value of this object uniquely identifies the
        instance entry for this class."
    ::= { msvmMediaPresentEntry 1 }

msvmmpAntecedent OBJECT-TYPE
    SYNTAX     WtcsDisplayString
    MAX-ACCESS read-only
    STATUS     current
    DESCRIPTION
        "Antecedent represents the independent object in
        this association."
    ::= { msvmMediaPresentEntry 2 }

msvmmpDependent OBJECT-TYPE
    SYNTAX     WtcsDisplayString
    MAX-ACCESS read-only
    STATUS     current
    DESCRIPTION
        "Dependent represents the object that is dependent
        on the Antecedent."
    ::= { msvmMediaPresentEntry 3 }

msvmmpFixedMedia OBJECT-TYPE
    SYNTAX     TruthValue
    MAX-ACCESS read-only
    STATUS     current
    DESCRIPTION
        "Boolean indicating that the accessed StorageExtent
        is fixed in the MediaAccessDevice and can not be
        ejected."
    ::= { msvmMediaPresentEntry 4 }

msvmProtocolControlForUnitTable OBJECT-TYPE
    SYNTAX     SEQUENCE OF MsvmProtocolControllerForUnit
    MAX-ACCESS not-accessible
    STATUS     current
    DESCRIPTION
        "This association indicates a subclass of
        LogicalDevice (for example a Storage Volume) is
        connected through a specific ProtocolController."
    ::= { msvmStorage 10 }

msvmProtocolControlForUnitEntry OBJECT-TYPE
    SYNTAX     MsvmProtocolControllerForUnit
    MAX-ACCESS not-accessible
    STATUS     current
    DESCRIPTION
        "None"
    INDEX      { msvmpcfuIndex }
    ::= { msvmProtocolControlForUnitTable 1 }

MsvmProtocolControllerForUnit ::= SEQUENCE {
    msvmpcfuIndex Integer32,
    msvmpcfuAccessPriority Integer32,
    msvmpcfuAccessState INTEGER,
    msvmpcfuAntecedent WtcsDisplayString,
    msvmpcfuDependent WtcsDisplayString,
    msvmpcfuDeviceNumber WtcsDisplayString
}

msvmpcfuIndex OBJECT-TYPE
    SYNTAX     Integer32 (1..2147483647)
    MAX-ACCESS read-only
    STATUS     current
    DESCRIPTION
        "The value of this object uniquely identifies the
        instance entry for this class."
    ::= { msvmProtocolControlForUnitEntry 1 }

msvmpcfuAccessPriority OBJECT-TYPE
    SYNTAX     Integer32
    MAX-ACCESS read-only
    STATUS     current
    DESCRIPTION
        "This property describes the priority given to
        accesses of the device through this Controller. The
        highest priority path will have the lowest value
        for this parameter."
    ::= { msvmProtocolControlForUnitEntry 2 }

msvmpcfuAccessState OBJECT-TYPE
    SYNTAX     INTEGER {
        unknown(0),
        active(2),
        inactive(3)
    }
    MAX-ACCESS read-only
    STATUS     current
    DESCRIPTION
        "The State property indicates whether the
        Controller is actively commanding or accessing the
        device (value=2) or not (value=3). Also, the value,
        'Unknown' (0), can be defined. This information is
        necessary when a LogicalDevice can be commanded by,
        or accessed through, multiple ProtocolControllers."
    ::= { msvmProtocolControlForUnitEntry 3 }

msvmpcfuAntecedent OBJECT-TYPE
    SYNTAX     WtcsDisplayString
    MAX-ACCESS read-only
    STATUS     current
    DESCRIPTION
        "Antecedent represents the independent object in
        this association."
    ::= { msvmProtocolControlForUnitEntry 4 }

msvmpcfuDependent OBJECT-TYPE
    SYNTAX     WtcsDisplayString
    MAX-ACCESS read-only
    STATUS     current
    DESCRIPTION
        "Dependent represents the object that is dependent
        on the Antecedent."
    ::= { msvmProtocolControlForUnitEntry 5 }

msvmpcfuDeviceNumber OBJECT-TYPE
    SYNTAX     WtcsDisplayString
    MAX-ACCESS read-only
    STATUS     current
    DESCRIPTION
        "Address of the associated Device in the context of
        the Antecedent Controller."
    ::= { msvmProtocolControlForUnitEntry 6 }

msvmSCSIProtocolControllerTable OBJECT-TYPE
    SYNTAX     SEQUENCE OF MsvmSCSIProtocolController
    MAX-ACCESS not-accessible
    STATUS     current
    DESCRIPTION
        "Represents a synthetic SCSI controller."
    ::= { msvmStorage 11 }

msvmSCSIProtocolControllerEntry OBJECT-TYPE
    SYNTAX     MsvmSCSIProtocolController
    MAX-ACCESS not-accessible
    STATUS     current
    DESCRIPTION
        "None"
    INDEX      { msvmspcIndex }
    ::= { msvmSCSIProtocolControllerTable 1 }

MsvmSCSIProtocolController ::= SEQUENCE {
    msvmspcIndex Integer32,
    msvmspcAdditionalAvailability INTEGER,
    msvmspcAvailability INTEGER,
    msvmspcCaption WtcsDisplayString,
    msvmspcCreationClassName WtcsDisplayString,
    msvmspcDescription WtcsDisplayString,
    msvmspcDeviceID WtcsDisplayString,
    msvmspcElementName WtcsDisplayString,
    msvmspcEnabledDefault INTEGER,
    msvmspcEnabledState INTEGER,
    msvmspcErrorCleared TruthValue,
    msvmspcErrorDescription WtcsDisplayString,
    msvmspcHealthState INTEGER,
    msvmspcIdentifyingDescriptions WtcsDisplayString,
    msvmspcInstallDate DateAndTime,
    msvmspcLastErrorCode Gauge32,
    msvmspcLocationIndicator INTEGER,
    msvmspcMaxQuiesceTime Gauge32,
    msvmspcMaxUnitsControlled Gauge32,
    msvmspcName WtcsDisplayString,
    msvmspcNameFormat INTEGER,
    msvmspcOperationalStatus INTEGER,
    msvmspcOtherEnabledState WtcsDisplayString,
    msvmspcOtherIdentifyingInfo WtcsDisplayString,
    msvmspcOtherNameFormat WtcsDisplayString,
    msvmspcPowerManagementCapability INTEGER,
    msvmspcPowerManagementSupported TruthValue,
    msvmspcPowerOnHours Gauge32,
    msvmspcRequestedState INTEGER,
    msvmspcStatus WtcsDisplayString,
    msvmspcStatusDescriptions WtcsDisplayString,
    msvmspcStatusInfo INTEGER,
    msvmspcSystemCreationClassName WtcsDisplayString,
    msvmspcSystemName WtcsDisplayString,
    msvmspcTimeOfLastStateChange DateAndTime,
    msvmspcTotalPowerOnHours Gauge32
}

msvmspcIndex OBJECT-TYPE
    SYNTAX     Integer32 (1..2147483647)
    MAX-ACCESS read-only
    STATUS     current
    DESCRIPTION
        "The value of this object uniquely identifies the
        instance entry for this class."
    ::= { msvmSCSIProtocolControllerEntry 1 }

msvmspcAdditionalAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Additional availability and status of the Device
        in addition to that specified in the Availability
        property. The Availability property denotes the
        primary status and availability of the Device. In
        some cases, this property will not be sufficient to
        denote the complete status of the Device. In those
        cases, the AdditionalAvailability property can be
        used to provide further information. For example,
        the primary Availability of a device might be 'Off
        line' (value=8) or in a low-power state
        (AdditionalAvailability value=14), or the Device
        could be running Diagnostics
        (AdditionalAvailability value=5, 'In Test')."
    ::= { msvmSCSIProtocolControllerEntry 2 }

msvmspcAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Note: The use of this property has been
        deprecated. 
        Deprecated description: The primary availability
        and status of the Device. (Additional status
        information can be specified using the Additional
        Availability array property.) For example, the
        Availability property indicates that the Device is
        running and has full power (value=3), or is in a
        warning (4), test (5), degraded (10) or power save
        state (values 13-15 and 17). The Power Save states
        are defined as follows: Value 13 ('Power Save -
        Unknown') indicates that the Device is known to be
        in a power save mode, but its exact status in this
        mode is unknown; value 14 ('Power Save - Low Power
        Mode') indicates that the Device is in a power save
        state but still functioning, and might exhibit
        degraded performance; value 15 ('Power Save -
        Standby') indicates that the Device is not
        functioning but could be brought to full power
        'quickly'; and value 17 ('Power Save - Warning')
        indicates that the Device is in a warning state,
        but is also in a power save mode."
    ::= { msvmSCSIProtocolControllerEntry 3 }

msvmspcCaption OBJECT-TYPE
    SYNTAX     WtcsDisplayString (SIZE (0..64))
    MAX-ACCESS read-only
    STATUS     current
    DESCRIPTION
        "The Caption property is a short textual
        description (one- line string) of the object."
    ::= { msvmSCSIProtocolControllerEntry 4 }

msvmspcCreationClassName OBJECT-TYPE
    SYNTAX     WtcsDisplayString (SIZE (0..256))
    MAX-ACCESS read-only
    STATUS     current
    DESCRIPTION
        "CreationClassName indicates the name of the class
        or the subclass used in the creation of an
        instance. When used with the other key properties
        of this class, this property allows all instances
        of this class and its subclasses to be uniquely
        identified."
    ::= { msvmSCSIProtocolControllerEntry 5 }

msvmspcDescription OBJECT-TYPE
    SYNTAX     WtcsDisplayString
    MAX-ACCESS read-only
    STATUS     current
    DESCRIPTION
        "The Description property provides a textual
        description of the object."
    ::= { msvmSCSIProtocolControllerEntry 6 }

msvmspcDeviceID OBJECT-TYPE
    SYNTAX     WtcsDisplayString (SIZE (0..64))
    MAX-ACCESS read-only
    STATUS     current
    DESCRIPTION
        "An address or other identifying information used
        to uniquely name the LogicalDevice."
    ::= { msvmSCSIProtocolControllerEntry 7 }

msvmspcElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmSCSIProtocolControllerEntry 8 }

msvmspcEnabledDefault OBJECT-TYPE
    SYNTAX     INTEGER {
        enabled(2),
        disabled(3),
        notApplicable(5),
        enabledbutOffline(6),
        noDefault(7)
    }
    MAX-ACCESS read-only
    STATUS     current
    DESCRIPTION
        "An enumerated value indicating an administrator's
        default or startup configuration for the Enabled
        State of an element. By default, the element is
        'Enabled' (value=2)."
    ::= { msvmSCSIProtocolControllerEntry 9 }

msvmspcEnabledState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "EnabledState is an integer enumeration that
        indicates the enabled and disabled states of an
        element. It can also indicate the transitions
        between these requested states. For example,
        shutting down (value=4) and starting (value=10) are
        transient states between enabled and disabled. The
        following text briefly summarizes the various
        enabled and disabled states: 
        Enabled (2) indicates that the element is or could
        be executing commands, will process any queued
        commands, and queues new requests. 
        Disabled (3) indicates that the element will not
        execute commands and will drop any new requests. 
        Shutting Down (4) indicates that the element is in
        the process of going to a Disabled state. 
        Not Applicable (5) indicates the element does not
        support being enabled or disabled. 
        Enabled but Offline (6) indicates that the element
        might be completing commands, and will drop any new
        requests. 
        Test (7) indicates that the element is in a test
        state. 
        Deferred (8) indicates that the element might be
        completing commands, but will queue any new
        requests. 
        Quiesce (9) indicates that the element is enabled
        but in a restricted mode. The behavior of the
        element is similar to the Enabled state, but it
        processes only a restricted set of commands. All
        other requests are queued. 
        Starting (10) indicates that the element is in the
        process of going to an Enabled state. New requests
        are queued."
    ::= { msvmSCSIProtocolControllerEntry 10 }

msvmspcErrorCleared OBJECT-TYPE
    SYNTAX     TruthValue
    MAX-ACCESS read-only
    STATUS     current
    DESCRIPTION
        "Note: The use of this method is deprecated. 
        Deprecated description: ErrorCleared is a Boolean
        property that indicates that the error reported in
        LastErrorCode is now cleared."
    ::= { msvmSCSIProtocolControllerEntry 11 }

msvmspcErrorDescription OBJECT-TYPE
    SYNTAX     WtcsDisplayString
    MAX-ACCESS read-only
    STATUS     current
    DESCRIPTION
        "Note: The use of this method is deprecated. 
        Deprecated description: ErrorDescription is a
        free-form string that supplies more information
        about the error recorded in LastErrorCode and
        information on any corrective actions that can be
        taken."
    ::= { msvmSCSIProtocolControllerEntry 12 }

msvmspcHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmSCSIProtocolControllerEntry 13 }

msvmspcIdentifyingDescriptions OBJECT-TYPE
    SYNTAX     WtcsDisplayString
    MAX-ACCESS read-only
    STATUS     current
    DESCRIPTION
        "An array of free-form strings providing
        explanations and details behind the entries in the
        OtherIdentifyingInfo array. Note that each entry of
        this array is related to the entry in
        OtherIdentifyingInfo that is located at the same
        index."
    ::= { msvmSCSIProtocolControllerEntry 14 }

msvmspcInstallDate OBJECT-TYPE
    SYNTAX     DateAndTime
    MAX-ACCESS read-only
    STATUS     current
    DESCRIPTION
        "A datetime value that indicates when the object
        was installed. Lack of a value does not indicate
        that the object is not installed."
    ::= { msvmSCSIProtocolControllerEntry 15 }

msvmspcLastErrorCode OBJECT-TYPE
    SYNTAX     Gauge32
    MAX-ACCESS read-only
    STATUS     current
    DESCRIPTION
        "Note: The use of this method is deprecated. 
        Deprecated description: LastErrorCode captures the
        last error code reported by the LogicalDevice."
    ::= { msvmSCSIProtocolControllerEntry 16 }

msvmspcLocationIndicator OBJECT-TYPE
    SYNTAX     INTEGER {
        unknown(0),
        on(2),
        off(3),
        notSupported(4)
    }
    MAX-ACCESS read-only
    STATUS     current
    DESCRIPTION
        "An integer that reflects the state of an indicator
        (e.g., LED) that is part of a device. Reading the
        value gives the current state. Writing the value
        with 'On'/'Off' turns the indicator on/off, other
        values may not be written."
    ::= { msvmSCSIProtocolControllerEntry 17 }

msvmspcMaxQuiesceTime OBJECT-TYPE
    SYNTAX     Gauge32
    UNITS "MilliSeconds"
    MAX-ACCESS read-only
    STATUS     current
    DESCRIPTION
        "Note: The use of this property has been
        deprecated. When evaluating the use of Quiesce, it
        was determined that this single property is not
        adequate for describing when a device will
        automatically exit a quiescent state. In fact, the
        most likely scenario for a device to exit a
        quiescent state was determined to be based on the
        number of outstanding requests queued rather than
        on a maximum time. This decision will be
        re-evaluated and repositioned later. 
        Deprecated description: Maximum time, in
        milliseconds, that a Device can run in a 'Quiesced'
        state. The state is defined in its Availability and
        AdditionalAvailability properties, where 'Quiesced'
        is conveyed by the value 21. What occurs at the end
        of the time limit is device-specific. The Device
        can unquiesce, can be offline, or can take other
        actions. A value of 0 indicates that a Device can
        remain quiesced indefinitely."
    ::= { msvmSCSIProtocolControllerEntry 18 }

msvmspcMaxUnitsControlled OBJECT-TYPE
    SYNTAX     Gauge32
    MAX-ACCESS read-only
    STATUS     current
    DESCRIPTION
        "Maximum number of Units that can be controlled by
        or accessed through this ProtocolController."
    ::= { msvmSCSIProtocolControllerEntry 19 }

msvmspcName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmSCSIProtocolControllerEntry 20 }

msvmspcNameFormat OBJECT-TYPE
    SYNTAX     INTEGER {
        unknown(0),
        other(1),
        fcPortWWN(2),
        iSCSIName(3)
    }
    MAX-ACCESS read-only
    STATUS     current
    DESCRIPTION
        "The NameFormat property identifies how the Name of
        the SCSIProtocolController is selected. 
        For Fibre Channel, the NameFormat is 'FC Port WWN'.
        
        For iSCSI, Name can use any of the 3 iSCSI formats
        (iqn, eui, naa) which include the iSCSI format as
        as a prefix in the name, so they are not
        ambiguous."
    ::= { msvmSCSIProtocolControllerEntry 21 }

msvmspcOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmSCSIProtocolControllerEntry 22 }

msvmspcOtherEnabledState OBJECT-TYPE
    SYNTAX     WtcsDisplayString
    MAX-ACCESS read-only
    STATUS     current
    DESCRIPTION
        "A string that describes the enabled or disabled
        state of the element when the EnabledState property
        is set to 1 ('Other'). This property must be set to
        null when EnabledState is any value other than 1."
    ::= { msvmSCSIProtocolControllerEntry 23 }

msvmspcOtherIdentifyingInfo OBJECT-TYPE
    SYNTAX     WtcsDisplayString (SIZE (0..256))
    MAX-ACCESS read-only
    STATUS     current
    DESCRIPTION
        "OtherIdentifyingInfo captures data, in addition to
        DeviceID information, that could be used to
        identify a LogicalDevice. For example, you could
        use this property to hold the operating system's
        user-friendly name for the Device."
    ::= { msvmSCSIProtocolControllerEntry 24 }

msvmspcOtherNameFormat OBJECT-TYPE
    SYNTAX     WtcsDisplayString
    MAX-ACCESS read-only
    STATUS     current
    DESCRIPTION
        "A string describing how the ProtocolController is
        identified when the NameFormat is 'Other'."
    ::= { msvmSCSIProtocolControllerEntry 25 }

msvmspcPowerManagementCapability OBJECT-TYPE
    SYNTAX     INTEGER {
        unknown(0),
        notSupported(1),
        disabled(2),
        enabled(3),
        powerSavingModesEnteredAutomatic(4),
        powerStateSettable(5),
        powerCyclingSupported(6),
        timedPowerOnSupported(7)
    }
    MAX-ACCESS read-only
    STATUS     current
    DESCRIPTION
        "Note: The use of this property has been
        deprecated. Instead, use the PowerCapabilites
        property in an associated
        PowerManagementCapabilities class. Deprecated
        description: An enumerated array describing the
        power management capabilities of the Device."
    ::= { msvmSCSIProtocolControllerEntry 26 }

msvmspcPowerManagementSupported OBJECT-TYPE
    SYNTAX     TruthValue
    MAX-ACCESS read-only
    STATUS     current
    DESCRIPTION
        "Note: The use of this property has been
        deprecated. Instead, the existence of an associated
        PowerManagementCapabilities class (associated using
        the ElementCapabilities relationship) indicates
        that power management is supported. Deprecated
        description: Boolean that indicates that the Device
        can use power management."
    ::= { msvmSCSIProtocolControllerEntry 27 }

msvmspcPowerOnHours OBJECT-TYPE
    SYNTAX     Gauge32
    UNITS "Hours"
    MAX-ACCESS read-only
    STATUS     current
    DESCRIPTION
        "Note: The use of this method is deprecated. 
        Deprecated description: The number of consecutive
        hours that this Device has been powered on since
        its last power cycle."
    ::= { msvmSCSIProtocolControllerEntry 28 }

msvmspcRequestedState OBJECT-TYPE
    SYNTAX     INTEGER {
        enabled(2),
        disabled(3),
        shutDown(4),
        noChange(5),
        offline(6),
        test(7),
        deferred(8),
        quiesce(9),
        reboot(10),
        reset(11),
        notApplicable(12)
    }
    MAX-ACCESS read-only
    STATUS     current
    DESCRIPTION
        "RequestedState is an integer enumeration that
        indicates the last requested or desired state for
        the element. The actual state of the element is
        represented by EnabledState. This property is
        provided to compare the last requested and current
        enabled or disabled states. Note that when
        EnabledState is set to 5 ('Not Applicable'), then
        this property has no meaning. By default, the
        RequestedState of the element is 5 ('No Change').
        Refer to the EnabledState property description for
        explanations of the values in the RequestedState
        enumeration. 
        
        It should be noted that there are two new values in
        RequestedState that build on the statuses of
        EnabledState. These are 'Reboot' (10) and 'Reset'
        (11). Reboot refers to doing a 'Shut Down' and then
        moving to an 'Enabled' state. Reset indicates that
        the element is first 'Disabled' and then 'Enabled'.
        The distinction between requesting 'Shut Down' and
        'Disabled' should also be noted. Shut Down requests
        an orderly transition to the Disabled state, and
        might involve removing power, to completely erase
        any existing state. The Disabled state requests an
        immediate disabling of the element, such that it
        will not execute or accept any commands or
        processing requests. 
        
        This property is set as the result of a method
        invocation (such as Start or StopService on
        CIM_Service), or can be overridden and defined as
        WRITEable in a subclass. The method approach is
        considered superior to a WRITEable property,
        because it allows an explicit invocation of the
        operation and the return of a result code. 
        
        A particular instance of EnabledLogicalElement
        might not support RequestedStateChange. If this
        occurs, the value 12 ('Not Applicable') is used."
    ::= { msvmSCSIProtocolControllerEntry 29 }

msvmspcStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmSCSIProtocolControllerEntry 30 }

msvmspcStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmSCSIProtocolControllerEntry 31 }

msvmspcStatusInfo OBJECT-TYPE
    SYNTAX     INTEGER {
        other(1),
        unknown(2),
        enabled(3),
        disabled(4),
        notApplicable(5)
    }
    MAX-ACCESS read-only
    STATUS     current
    DESCRIPTION
        "Note: The use of this method is deprecated in lieu
        of a more clearly named property (EnabledState)
        that is inherited from ManagedSystemElement and
        that has additional enumerated values. 
        Deprecated description: The StatusInfo property
        indicates whether the Logical Device is in an
        enabled state (value=3), disabled state (value=4),
        some other state (value=1), or an unknown state
        (value=2). If this property does not apply to the
        LogicalDevice, the value 5 ('Not Applicable')
        should be used. If a Device is
        ('Enabled')(value=3), it has been powered up and is
        configured and operational. The Device might or
        might not be functionally active, depending on
        whether its Availability (or
        AdditionalAvailability) indicates that it is
        ('Running/Full Power')(value=3) or ('Off line')
        (value=8). In an enabled but offline mode, a Device
        might be performing out-of-band requests, such as
        running Diagnostics. If StatusInfo is ('Disabled')
        (value=4), a Device can only be 'enabled' or
        powered off. In a personal computer environment,
        ('Disabled') means that the driver of the device is
        not available in the stack. In other environments,
        a Device can be disabled by removing its
        configuration file. A disabled device is physically
        present in a System and consuming resources, but it
        cannot be communicated with until a driver is
        loaded, a configuration file is loaded, or some
        other 'enabling' activity has occurred."
    ::= { msvmSCSIProtocolControllerEntry 32 }

msvmspcSystemCreationClassName OBJECT-TYPE
    SYNTAX     WtcsDisplayString (SIZE (0..256))
    MAX-ACCESS read-only
    STATUS     current
    DESCRIPTION
        "The CreationClassName of the scoping system."
    ::= { msvmSCSIProtocolControllerEntry 33 }

msvmspcSystemName OBJECT-TYPE
    SYNTAX     WtcsDisplayString (SIZE (0..256))
    MAX-ACCESS read-only
    STATUS     current
    DESCRIPTION
        "The System Name of the scoping system."
    ::= { msvmSCSIProtocolControllerEntry 34 }

msvmspcTimeOfLastStateChange OBJECT-TYPE
    SYNTAX     DateAndTime
    MAX-ACCESS read-only
    STATUS     current
    DESCRIPTION
        "The date or time when the EnabledState of the
        element last changed. If the state of the element
        has not changed and this property is populated,
        then it must be set to a 0 interval value. If a
        state change was requested, but rejected or not yet
        processed, the property must not be updated."
    ::= { msvmSCSIProtocolControllerEntry 35 }

msvmspcTotalPowerOnHours OBJECT-TYPE
    SYNTAX     Gauge32
    UNITS "Hours"
    MAX-ACCESS read-only
    STATUS     current
    DESCRIPTION
        "Note: The use of this method is deprecated. 
        Deprecated description: The total number of hours
        that this Device has been powered on."
    ::= { msvmSCSIProtocolControllerEntry 36 }

msvmStorageJobTable OBJECT-TYPE
    SYNTAX     SEQUENCE OF MsvmStorageJob
    MAX-ACCESS not-accessible
    STATUS     current
    DESCRIPTION
        "This class represents a image operation job
        created by the Microsoft Hyper-V Image Management
        Service."
    ::= { msvmStorage 12 }

msvmStorageJobEntry OBJECT-TYPE
    SYNTAX     MsvmStorageJob
    MAX-ACCESS not-accessible
    STATUS     current
    DESCRIPTION
        "None"
    INDEX      { msvmsjIndex }
    ::= { msvmStorageJobTable 1 }

MsvmStorageJob ::= SEQUENCE {
    msvmsjIndex Integer32,
    msvmsjCaption WtcsDisplayString,
    msvmsjChild WtcsDisplayString,
    msvmsjDeleteOnCompletion TruthValue,
    msvmsjDescription WtcsDisplayString,
    msvmsjElapsedTime DateAndTime,
    msvmsjElementName WtcsDisplayString,
    msvmsjErrorCode Integer32,
    msvmsjErrorDescription WtcsDisplayString,
    msvmsjErrorSummaryDescription WtcsDisplayString,
    msvmsjHealthState INTEGER,
    msvmsjInstallDate DateAndTime,
    msvmsjInstanceID WtcsDisplayString,
    msvmsjJobCompletionStatusCode Gauge32,
    msvmsjJobRunTimes Gauge32,
    msvmsjJobState INTEGER,
    msvmsjJobStatus WtcsDisplayString,
    msvmsjLocalOrUtcTime INTEGER,
    msvmsjLun Integer32,
    msvmsjName WtcsDisplayString,
    msvmsjNotify WtcsDisplayString,
    msvmsjOperationalStatus INTEGER,
    msvmsjOtherRecoveryAction WtcsDisplayString,
    msvmsjOwner WtcsDisplayString,
    msvmsjParent WtcsDisplayString,
    msvmsjPathId Integer32,
    msvmsjPercentComplete Integer32,
    msvmsjPortNumber Integer32,
    msvmsjPriority Gauge32,
    msvmsjRecoveryAction INTEGER,
    msvmsjRunDay Integer32,
    msvmsjRunDayOfWeek Integer32,
    msvmsjRunMonth INTEGER,
    msvmsjRunStartInterval DateAndTime,
    msvmsjScheduledStartTime DateAndTime,
    msvmsjStartTime DateAndTime,
    msvmsjStatus WtcsDisplayString,
    msvmsjStatusDescriptions WtcsDisplayString,
    msvmsjTargetId Integer32,
    msvmsjTimeBeforeRemoval DateAndTime,
    msvmsjTimeOfLastStateChange DateAndTime,
    msvmsjTimeSubmitted DateAndTime,
    msvmsjType INTEGER,
    msvmsjUntilTime DateAndTime
}

msvmsjIndex OBJECT-TYPE
    SYNTAX     Integer32 (1..2147483647)
    MAX-ACCESS read-only
    STATUS     current
    DESCRIPTION
        "The value of this object uniquely identifies the
        instance entry for this class."
    ::= { msvmStorageJobEntry 1 }

msvmsjCaption OBJECT-TYPE
    SYNTAX     WtcsDisplayString (SIZE (0..64))
    MAX-ACCESS read-only
    STATUS     current
    DESCRIPTION
        "The Caption property is a short textual
        description (one- line string) of the object."
    ::= { msvmStorageJobEntry 2 }

msvmsjChild OBJECT-TYPE
    SYNTAX     WtcsDisplayString
    MAX-ACCESS read-only
    STATUS     current
    DESCRIPTION
        "On failure of the asynchronous operation, this
        property contains the file path to the child of the
        virtual hard drive being affected by this
        operation. This property is inherited from
        CIM_ConcreteJob."
    ::= { msvmStorageJobEntry 3 }

msvmsjDeleteOnCompletion OBJECT-TYPE
    SYNTAX     TruthValue
    MAX-ACCESS read-only
    STATUS     current
    DESCRIPTION
        "Indicates whether or not the job should be
        automatically deleted upon completion. Note that
        the 'completion' of a recurring job is defined by
        its JobRunTimes or UntilTime properties, or when
        the Job is terminated by manual intervention. If
        this property is set to false and the job
        completes, then the extrinsic method DeleteInstance
        must be used to delete the job instead of updating
        this property."
    ::= { msvmStorageJobEntry 4 }

msvmsjDescription OBJECT-TYPE
    SYNTAX     WtcsDisplayString
    MAX-ACCESS read-only
    STATUS     current
    DESCRIPTION
        "The Description property provides a textual
        description of the object."
    ::= { msvmStorageJobEntry 5 }

msvmsjElapsedTime OBJECT-TYPE
    SYNTAX     DateAndTime
    MAX-ACCESS read-only
    STATUS     current
    DESCRIPTION
        "The time interval that the Job has been executing
        or the total execution time if the Job is complete.
        Note that this property is also present in the
        JobProcessingStatistics class. This class is
        necessary to capture the processing information for
        recurring Jobs, because only the 'last' run time
        can be stored in this single-valued property."
    ::= { msvmStorageJobEntry 6 }

msvmsjElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmStorageJobEntry 7 }

msvmsjErrorCode OBJECT-TYPE
    SYNTAX     Integer32
    MAX-ACCESS read-only
    STATUS     current
    DESCRIPTION
        "A vendor-specific error code. The value must be
        set to zero if the Job completed without error.
        Note that this property is also present in the
        JobProcessingStatistics class. This class is
        necessary to capture the processing information for
        recurring Jobs, because only the 'last' run error
        can be stored in this single-valued property."
    ::= { msvmStorageJobEntry 8 }

msvmsjErrorDescription OBJECT-TYPE
    SYNTAX     WtcsDisplayString
    MAX-ACCESS read-only
    STATUS     current
    DESCRIPTION
        "A free-form string that contains the vendor error
        description. Note that this property is also
        present in the JobProcessingStatistics class. This
        class is necessary to capture the processing
        information for recurring Jobs, because only the
        'last' run error can be stored in this
        single-valued property."
    ::= { msvmStorageJobEntry 9 }

msvmsjErrorSummaryDescription OBJECT-TYPE
    SYNTAX     WtcsDisplayString
    MAX-ACCESS read-only
    STATUS     current
    DESCRIPTION
        "A free-form string that contains the vendor
        summary error description. Note that this property
        is also present in the JobProcessingStatistics
        class. This class is necessary to capture the
        processing information for recurring Jobs, because
        only the 'last' run error can be stored in this
        single-valued property."
    ::= { msvmStorageJobEntry 10 }

msvmsjHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmStorageJobEntry 11 }

msvmsjInstallDate OBJECT-TYPE
    SYNTAX     DateAndTime
    MAX-ACCESS read-only
    STATUS     current
    DESCRIPTION
        "A datetime value that indicates when the object
        was installed. Lack of a value does not indicate
        that the object is not installed."
    ::= { msvmStorageJobEntry 12 }

msvmsjInstanceID OBJECT-TYPE
    SYNTAX     WtcsDisplayString
    MAX-ACCESS read-only
    STATUS     current
    DESCRIPTION
        "Within the scope of the instantiating Namespace,
        InstanceID opaquely and uniquely identifies an
        instance of this class. In order to ensure
        uniqueness within the NameSpace, the value of
        InstanceID SHOULD be constructed using the
        following 'preferred' algorithm: 
        <OrgID>:<LocalID> 
        Where <OrgID> and <LocalID> are separated by a
        colon ':', and where <OrgID> must include a
        copyrighted, trademarked or otherwise unique name
        that is owned by the business entity that is
        creating or defining the InstanceID, or that is a
        registered ID that is assigned to the business
        entity by a recognized global authority. (This
        requirement is similar to the <Schema Name>_<Class
        Name> structure of Schema class names.) In
        addition, to ensure uniqueness <OrgID> must not
        contain a colon (':'). When using this algorithm,
        the first colon to appear in InstanceID must appear
        between <OrgID> and <LocalID>. 
        <LocalID> is chosen by the business entity and
        should not be re-used to identify different
        underlying (real-world) elements. If the above
        'preferred' algorithm is not used, the defining
        entity must assure that the resulting InstanceID is
        not re-used across any InstanceIDs produced by this
        or other providers for the NameSpace of this
        instance. 
        For DMTF defined instances, the 'preferred'
        algorithm must be used with the <OrgID> set to
        'CIM'."
    ::= { msvmStorageJobEntry 13 }

msvmsjJobCompletionStatusCode OBJECT-TYPE
    SYNTAX     Gauge32
    MAX-ACCESS read-only
    STATUS     current
    DESCRIPTION
        "HRESULT for a completed job."
    ::= { msvmStorageJobEntry 14 }

msvmsjJobRunTimes OBJECT-TYPE
    SYNTAX     Gauge32
    MAX-ACCESS read-only
    STATUS     current
    DESCRIPTION
        "The number of times that the Job should be run. A
        value of 1 indicates that the Job is not recurring,
        while any non-zero value indicates a limit to the
        number of times that the Job will recur. Zero
        indicates that there is no limit to the number of
        times that the Job can be processed, but that it is
        terminated either after the UntilTime or by manual
        intervention. By default, a Job is processed once."
    ::= { msvmStorageJobEntry 15 }

msvmsjJobState OBJECT-TYPE
    SYNTAX     INTEGER {
        new(2),
        starting(3),
        running(4),
        suspended(5),
        shuttingDown(6),
        completed(7),
        terminated(8),
        killed(9),
        exception(10),
        service(11)
    }
    MAX-ACCESS read-only
    STATUS     current
    DESCRIPTION
        "JobState is an integer enumeration that indicates
        the operational state of a Job. It can also
        indicate transitions between these states, for
        example, 'Shutting Down' and 'Starting'. Following
        is a brief description of the states: 
        New (2) indicates that the job has never been
        started. 
        Starting (3) indicates that the job is moving from
        the 'New', 'Suspended', or 'Service' states into
        the 'Running' state. 
        Running (4) indicates that the Job is running. 
        Suspended (5) indicates that the Job is stopped,
        but can be restarted in a seamless manner. 
        Shutting Down (6) indicates that the job is moving
        to a 'Completed', 'Terminated', or 'Killed' state. 
        Completed (7) indicates that the job has completed
        normally. 
        Terminated (8) indicates that the job has been
        stopped by a 'Terminate' state change request. The
        job and all its underlying processes are ended and
        can be restarted (this is job-specific) only as a
        new job. 
        Killed (9) indicates that the job has been stopped
        by a 'Kill' state change request. Underlying
        processes might have been left running, and cleanup
        might be required to free up resources. 
        Exception (10) indicates that the Job is in an
        abnormal state that might be indicative of an error
        condition. Actual status might be displayed though
        job-specific objects. 
        Service (11) indicates that the Job is in a
        vendor-specific state that supports problem
        discovery, or resolution, or both."
    ::= { msvmStorageJobEntry 16 }

msvmsjJobStatus OBJECT-TYPE
    SYNTAX     WtcsDisplayString
    MAX-ACCESS read-only
    STATUS     current
    DESCRIPTION
        "A free-form string that represents the status of
        the job. The primary status is reflected in the
        inherited OperationalStatus property. JobStatus
        provides additional, implementation-specific
        details."
    ::= { msvmStorageJobEntry 17 }

msvmsjLocalOrUtcTime OBJECT-TYPE
    SYNTAX     INTEGER {
        localTime(1),
        utcTime(2)
    }
    MAX-ACCESS read-only
    STATUS     current
    DESCRIPTION
        "This property indicates whether the times
        represented in the RunStartInterval and UntilTime
        properties represent local times or UTC times. Time
        values are synchronized worldwide by using the
        enumeration value 2, 'UTC Time'."
    ::= { msvmStorageJobEntry 18 }

msvmsjLun OBJECT-TYPE
    SYNTAX     Integer32
    MAX-ACCESS read-only
    STATUS     current
    DESCRIPTION
        "SCSI address lun id."
    ::= { msvmStorageJobEntry 19 }

msvmsjName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmStorageJobEntry 20 }

msvmsjNotify OBJECT-TYPE
    SYNTAX     WtcsDisplayString
    MAX-ACCESS read-only
    STATUS     current
    DESCRIPTION
        "The User who is to be notified upon the Job
        completion or failure."
    ::= { msvmStorageJobEntry 21 }

msvmsjOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmStorageJobEntry 22 }

msvmsjOtherRecoveryAction OBJECT-TYPE
    SYNTAX     WtcsDisplayString
    MAX-ACCESS read-only
    STATUS     current
    DESCRIPTION
        "A string describing the recovery action when the
        RecoveryAction property of the instance is 1
        ('Other')."
    ::= { msvmStorageJobEntry 23 }

msvmsjOwner OBJECT-TYPE
    SYNTAX     WtcsDisplayString
    MAX-ACCESS read-only
    STATUS     current
    DESCRIPTION
        "The User that submitted the Job, or the Service or
        method name that caused the job to be created."
    ::= { msvmStorageJobEntry 24 }

msvmsjParent OBJECT-TYPE
    SYNTAX     WtcsDisplayString
    MAX-ACCESS read-only
    STATUS     current
    DESCRIPTION
        "On failure of the asynchronous operation, this
        property contains the file path to the parent of
        the virtual hard drive being affected by this
        operation. This property is inherited from
        CIM_ConcreteJob."
    ::= { msvmStorageJobEntry 25 }

msvmsjPathId OBJECT-TYPE
    SYNTAX     Integer32
    MAX-ACCESS read-only
    STATUS     current
    DESCRIPTION
        "SCSI address path id."
    ::= { msvmStorageJobEntry 26 }

msvmsjPercentComplete OBJECT-TYPE
    SYNTAX     Integer32
    UNITS "Percent"
    MAX-ACCESS read-only
    STATUS     current
    DESCRIPTION
        "The percentage of the job that has completed at
        the time that this value is requested. Note that
        this property is also present in the
        JobProcessingStatistics class. This class is
        necessary to capture the processing information for
        recurring Jobs, because only the 'last' run data
        can be stored in this single-valued property. 
        Note that the value 101 is undefined and will be
        not be allowed in the next major revision of the
        specification."
    ::= { msvmStorageJobEntry 27 }

msvmsjPortNumber OBJECT-TYPE
    SYNTAX     Integer32
    MAX-ACCESS read-only
    STATUS     current
    DESCRIPTION
        "SCSI address port number."
    ::= { msvmStorageJobEntry 28 }

msvmsjPriority OBJECT-TYPE
    SYNTAX     Gauge32
    MAX-ACCESS read-only
    STATUS     current
    DESCRIPTION
        "Indicates the urgency or importance of execution
        of the Job. The lower the number, the higher the
        priority. Note that this property is also present
        in the JobProcessingStatistics class. This class is
        necessary to capture the setting information that
        would influence the results of a job."
    ::= { msvmStorageJobEntry 29 }

msvmsjRecoveryAction OBJECT-TYPE
    SYNTAX     INTEGER {
        unknown(0),
        other(1),
        doNotContinue(2),
        continueWithNextJob(3),
        rerunJob(4),
        runRecoveryJob(5)
    }
    MAX-ACCESS read-only
    STATUS     current
    DESCRIPTION
        "Describes the recovery action to be taken for an
        unsuccessfully run Job. The possible values are: 
        0 = 'Unknown', meaning it is unknown as to what
        recovery action to take 
        1 = 'Other', indicating that the recovery action
        will be specified in the OtherRecoveryAction
        property 
        2 = 'Do Not Continue', meaning stop the execution
        of the job and appropriately update its status 
        3 = 'Continue With Next Job', meaning continue with
        the next job in the queue 
        4 = 'Re-run Job', indicating that the job should be
        re-run 
        5 = 'Run Recovery Job', meaning run the Job
        associated using the RecoveryJob relationship. Note
        that the recovery Job must already be in the queue
        from which it will run."
    ::= { msvmStorageJobEntry 30 }

msvmsjRunDay OBJECT-TYPE
    SYNTAX     Integer32
    MAX-ACCESS read-only
    STATUS     current
    DESCRIPTION
        "The day in the month on which the Job should be
        processed. There are two different interpretations
        for this property, depending on the value of
        DayOfWeek. In one case, RunDay defines the
        day-in-month on which the Job is processed. This
        interpretation is used when the DayOfWeek is 0. A
        positive or negative integer indicates whether the
        RunDay should be calculated from the beginning or
        end of the month. For example, 5 indicates the
        fifth day in the RunMonth and -1 indicates the last
        day in the RunMonth. 
        
        When RunDayOfWeek is not 0, RunDay is the
        day-in-month on which the Job is processed, defined
        in conjunction with RunDayOfWeek. For example, if
        RunDay is 15 and RunDayOfWeek is Saturday, then the
        Job is processed on the first Saturday on or after
        the 15th day in the RunMonth (for example, the
        third Saturday in the month). If RunDay is 20 and
        RunDayOfWeek is -Saturday, then this indicates the
        first Saturday on or before the 20th day in the
        RunMonth. If RunDay is -1 and RunDayOfWeek is
        -Sunday, then this indicates the last Sunday in the
        RunMonth."
    ::= { msvmStorageJobEntry 31 }

msvmsjRunDayOfWeek OBJECT-TYPE
    SYNTAX     Integer32
    MAX-ACCESS read-only
    STATUS     current
    DESCRIPTION
        "A positive or negative integer used in conjunction
        with RunDay to indicate the day of the week on
        which the Job is processed. RunDayOfWeek is set to
        0 to indicate an exact day of the month, such as
        March 1. A positive integer (representing Sunday,
        Monday, ..., Saturday) means that the day of week
        is found on or after the specified RunDay. A
        negative integer (representing -Sunday, -Monday,
        ..., -Saturday) means that the day of week is found
        on or BEFORE the RunDay."
    ::= { msvmStorageJobEntry 32 }

msvmsjRunMonth OBJECT-TYPE
    SYNTAX     INTEGER {
        january(0),
        february(1),
        march(2),
        april(3),
        may(4),
        june(5),
        july(6),
        august(7),
        september(8),
        october(9),
        november(10),
        december(11)
    }
    MAX-ACCESS read-only
    STATUS     current
    DESCRIPTION
        "The month during which the Job should be
        processed. Specify 0 for January, 1 for February,
        and so on."
    ::= { msvmStorageJobEntry 33 }

msvmsjRunStartInterval OBJECT-TYPE
    SYNTAX     DateAndTime
    MAX-ACCESS read-only
    STATUS     current
    DESCRIPTION
        "The time interval after midnight when the Job
        should be processed. For example, 
        00000000020000.000000:000 
        indicates that the Job should be run on or after
        two o'clock, local time or UTC time (distinguished
        using the LocalOrUtcTime property."
    ::= { msvmStorageJobEntry 34 }

msvmsjScheduledStartTime OBJECT-TYPE
    SYNTAX     DateAndTime
    MAX-ACCESS read-only
    STATUS     current
    DESCRIPTION
        "The time that the current Job is scheduled to
        start. This time can be represented by the actual
        date and time, or an interval relative to the time
        that this property is requested. A value of all
        zeroes indicates that the Job is already executing.
        The property is deprecated in lieu of the more
        expressive scheduling properties, RunMonth, RunDay,
        RunDayOfWeek, and RunStartInterval."
    ::= { msvmStorageJobEntry 35 }

msvmsjStartTime OBJECT-TYPE
    SYNTAX     DateAndTime
    MAX-ACCESS read-only
    STATUS     current
    DESCRIPTION
        "The time that the Job was actually started. This
        time can be represented by an actual date and time,
        or by an interval relative to the time that this
        property is requested. Note that this property is
        also present in the JobProcessingStatistics class.
        This class is necessary to capture the processing
        information for recurring Jobs, because only the
        'last' run time can be stored in this single-valued
        property."
    ::= { msvmStorageJobEntry 36 }

msvmsjStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmStorageJobEntry 37 }

msvmsjStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmStorageJobEntry 38 }

msvmsjTargetId OBJECT-TYPE
    SYNTAX     Integer32
    MAX-ACCESS read-only
    STATUS     current
    DESCRIPTION
        "SCSI address target id."
    ::= { msvmStorageJobEntry 39 }

msvmsjTimeBeforeRemoval OBJECT-TYPE
    SYNTAX     DateAndTime
    MAX-ACCESS read-only
    STATUS     current
    DESCRIPTION
        "The amount of time that the Job is retained after
        it has finished executing, either succeeding or
        failing in that execution. The job must remain in
        existence for some period of time regardless of the
        value of the DeleteOnCompletion property. 
        The default is five minutes."
    ::= { msvmStorageJobEntry 40 }

msvmsjTimeOfLastStateChange OBJECT-TYPE
    SYNTAX     DateAndTime
    MAX-ACCESS read-only
    STATUS     current
    DESCRIPTION
        "The date or time when the state of the Job last
        changed. If the state of the Job has not changed
        and this property is populated, then it must be set
        to a 0 interval value. If a state change was
        requested, but rejected or not yet processed, the
        property must not be updated."
    ::= { msvmStorageJobEntry 41 }

msvmsjTimeSubmitted OBJECT-TYPE
    SYNTAX     DateAndTime
    MAX-ACCESS read-only
    STATUS     current
    DESCRIPTION
        "The time that the Job was submitted to execute. A
        value of all zeroes indicates that the owning
        element is not capable of reporting a date and
        time. Therefore, the ScheduledStartTime and
        StartTime are reported as intervals relative to the
        time their values are requested."
    ::= { msvmStorageJobEntry 42 }

msvmsjType OBJECT-TYPE
    SYNTAX     INTEGER {
        diskJobTypeInvalid(0),
        diskJobTypeCreation(1),
        diskJobTypeFloppyCreation(2),
        diskJobTypeCompaction(3),
        diskJobTypeExpansion(4),
        diskJobTypeMerging(5),
        diskJobTypeForking(6),
        diskJobTypeConversion(7),
        diskJobTypeLoopbackMount(8)
    }
    MAX-ACCESS read-only
    STATUS     current
    DESCRIPTION
        "The type of job."
    ::= { msvmStorageJobEntry 43 }

msvmsjUntilTime OBJECT-TYPE
    SYNTAX     DateAndTime
    MAX-ACCESS read-only
    STATUS     current
    DESCRIPTION
        "The time after which the Job is invalid or should
        be stopped. This time can be represented by an
        actual date and time, or by an interval relative to
        the time that this property is requested. A value
        of all nines indicates that the Job can run
        indefinitely."
    ::= { msvmStorageJobEntry 44 }

msvmVirtualHardDiskInfoTable OBJECT-TYPE
    SYNTAX     SEQUENCE OF MsvmVirtualHardDiskInfo
    MAX-ACCESS not-accessible
    STATUS     current
    DESCRIPTION
        "Provides detailed information about an existing
        virtual hard disk image."
    ::= { msvmStorage 13 }

msvmVirtualHardDiskInfoEntry OBJECT-TYPE
    SYNTAX     MsvmVirtualHardDiskInfo
    MAX-ACCESS not-accessible
    STATUS     current
    DESCRIPTION
        "None"
    INDEX      { msvmvhdiIndex }
    ::= { msvmVirtualHardDiskInfoTable 1 }

MsvmVirtualHardDiskInfo ::= SEQUENCE {
    msvmvhdiIndex Integer32,
    msvmvhdiFileSize Gauge32,
    msvmvhdiInSavedState TruthValue,
    msvmvhdiInUse TruthValue,
    msvmvhdiMaxInternalSize Gauge32,
    msvmvhdiParentPath WtcsDisplayString,
    msvmvhdiType INTEGER
}

msvmvhdiIndex OBJECT-TYPE
    SYNTAX     Integer32 (1..2147483647)
    MAX-ACCESS read-only
    STATUS     current
    DESCRIPTION
        "The value of this object uniquely identifies the
        instance entry for this class."
    ::= { msvmVirtualHardDiskInfoEntry 1 }

msvmvhdiFileSize OBJECT-TYPE
    SYNTAX     Gauge32
    MAX-ACCESS read-only
    STATUS     current
    DESCRIPTION
        "The size of the virtual hard disk file on the host
        volume."
    ::= { msvmVirtualHardDiskInfoEntry 2 }

msvmvhdiInSavedState OBJECT-TYPE
    SYNTAX     TruthValue
    MAX-ACCESS read-only
    STATUS     current
    DESCRIPTION
        "Reflects whether this disk image is associated
        with a virtual machine in a saved state."
    ::= { msvmVirtualHardDiskInfoEntry 3 }

msvmvhdiInUse OBJECT-TYPE
    SYNTAX     TruthValue
    MAX-ACCESS read-only
    STATUS     current
    DESCRIPTION
        "Reflects whether this disk image is currently
        mounted and in use."
    ::= { msvmVirtualHardDiskInfoEntry 4 }

msvmvhdiMaxInternalSize OBJECT-TYPE
    SYNTAX     Gauge32
    MAX-ACCESS read-only
    STATUS     current
    DESCRIPTION
        "The maximum size of the virtual hard disk as
        viewable by the virtual machine."
    ::= { msvmVirtualHardDiskInfoEntry 5 }

msvmvhdiParentPath OBJECT-TYPE
    SYNTAX     WtcsDisplayString
    MAX-ACCESS read-only
    STATUS     current
    DESCRIPTION
        "The parent of the virtual hard disk. If the
        virtual hard disk does not have a parent, then this
        field is empty."
    ::= { msvmVirtualHardDiskInfoEntry 6 }

msvmvhdiType OBJECT-TYPE
    SYNTAX     INTEGER {
        fixed(2),
        dynamic(3),
        differencing(4)
    }
    MAX-ACCESS read-only
    STATUS     current
    DESCRIPTION
        "The type of virtual hard disk."
    ::= { msvmVirtualHardDiskInfoEntry 7 }

msvmVideo OBJECT-IDENTITY
    STATUS     current
    DESCRIPTION
        "All virtual machines reflect the prescence of an
        emulated S3 video controller and an accelerated,
        synthetic video controller.
        
        Each display controller has a video head object
        associated with it. Only one display controller can
        be active in a virtual machine at any time.
        
        A terminal connection is present for every active
        remote session connected to a virtual machine."
    ::= { informantHyperV 11 }

msvmS3DisplayControllerTable OBJECT-TYPE
    SYNTAX     SEQUENCE OF MsvmS3DisplayController
    MAX-ACCESS not-accessible
    STATUS     current
    DESCRIPTION
        "Represents the state of the emulated S3 controller
        that is present in each virtual machine
        configuration."
    ::= { msvmVideo 1 }

msvmS3DisplayControllerEntry OBJECT-TYPE
    SYNTAX     MsvmS3DisplayController
    MAX-ACCESS not-accessible
    STATUS     current
    DESCRIPTION
        "None"
    INDEX      { msvms3dcIndex }
    ::= { msvmS3DisplayControllerTable 1 }

MsvmS3DisplayController ::= SEQUENCE {
    msvms3dcIndex Integer32,
    msvms3dcAcceleratorCapabilities INTEGER,
    msvms3dcAdditionalAvailability INTEGER,
    msvms3dcAvailability INTEGER,
    msvms3dcCapabilityDescriptions WtcsDisplayString,
    msvms3dcCaption WtcsDisplayString,
    msvms3dcCreationClassName WtcsDisplayString,
    msvms3dcDescription WtcsDisplayString,
    msvms3dcDeviceID WtcsDisplayString,
    msvms3dcElementName WtcsDisplayString,
    msvms3dcEnabledDefault INTEGER,
    msvms3dcEnabledState INTEGER,
    msvms3dcErrorCleared TruthValue,
    msvms3dcErrorDescription WtcsDisplayString,
    msvms3dcHealthState INTEGER,
    msvms3dcIdentifyingDescriptions WtcsDisplayString,
    msvms3dcInstallDate DateAndTime,
    msvms3dcLastErrorCode Gauge32,
    msvms3dcLocationIndicator INTEGER,
    msvms3dcMaxMemorySupported Gauge32,
    msvms3dcMaxNumberControlled Gauge32,
    msvms3dcMaxQuiesceTime Gauge32,
    msvms3dcName WtcsDisplayString,
    msvms3dcNumberOfVideoPages Gauge32,
    msvms3dcOperationalStatus INTEGER,
    msvms3dcOtherEnabledState WtcsDisplayString,
    msvms3dcOtherIdentifyingInfo WtcsDisplayString,
    msvms3dcOtherVideoMemoryType WtcsDisplayString,
    msvms3dcPowerMgtCapability INTEGER,
    msvms3dcPowerManagementSupported TruthValue,
    msvms3dcPowerOnHours Gauge32,
    msvms3dcProtocolDescription WtcsDisplayString,
    msvms3dcProtocolSupported Integer32,
    msvms3dcRequestedState INTEGER,
    msvms3dcStatus WtcsDisplayString,
    msvms3dcStatusDescriptions WtcsDisplayString,
    msvms3dcStatusInfo INTEGER,
    msvms3dcSystemCreationClassName WtcsDisplayString,
    msvms3dcSystemName WtcsDisplayString,
    msvms3dcTimeOfLastReset DateAndTime,
    msvms3dcTimeOfLastStateChange DateAndTime,
    msvms3dcTotalPowerOnHours Gauge32,
    msvms3dcVideoMemoryType INTEGER,
    msvms3dcVideoProcessor WtcsDisplayString
}

msvms3dcIndex OBJECT-TYPE
    SYNTAX     Integer32 (1..2147483647)
    MAX-ACCESS read-only
    STATUS     current
    DESCRIPTION
        "The value of this object uniquely identifies the
        instance entry for this class."
    ::= { msvmS3DisplayControllerEntry 1 }

msvms3dcAcceleratorCapabilities OBJECT-TYPE
    SYNTAX     INTEGER {
        unknown(0),
        other(1),
        graphicsAccelerator(2),
        a3DAccelerator(3),
        pciFastWrite(4),
        multiMonitorSupport(5),
        pciMastering(6),
        secondMonochromeAdapterSupport(7),
        largeMemoryAddressSupport(8)
    }
    MAX-ACCESS read-only
    STATUS     current
    DESCRIPTION
        "An array of integers indicating the graphics and
        3D capabilities of the DisplayController."
    ::= { msvmS3DisplayControllerEntry 2 }

msvms3dcAdditionalAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Additional availability and status of the Device
        in addition to that specified in the Availability
        property. The Availability property denotes the
        primary status and availability of the Device. In
        some cases, this property will not be sufficient to
        denote the complete status of the Device. In those
        cases, the AdditionalAvailability property can be
        used to provide further information. For example,
        the primary Availability of a device might be 'Off
        line' (value=8) or in a low-power state
        (AdditionalAvailability value=14), or the Device
        could be running Diagnostics
        (AdditionalAvailability value=5, 'In Test')."
    ::= { msvmS3DisplayControllerEntry 3 }

msvms3dcAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Note: The use of this property has been
        deprecated. 
        Deprecated description: The primary availability
        and status of the Device. (Additional status
        information can be specified using the Additional
        Availability array property.) For example, the
        Availability property indicates that the Device is
        running and has full power (value=3), or is in a
        warning (4), test (5), degraded (10) or power save
        state (values 13-15 and 17). The Power Save states
        are defined as follows: Value 13 ('Power Save -
        Unknown') indicates that the Device is known to be
        in a power save mode, but its exact status in this
        mode is unknown; value 14 ('Power Save - Low Power
        Mode') indicates that the Device is in a power save
        state but still functioning, and might exhibit
        degraded performance; value 15 ('Power Save -
        Standby') indicates that the Device is not
        functioning but could be brought to full power
        'quickly'; and value 17 ('Power Save - Warning')
        indicates that the Device is in a warning state,
        but is also in a power save mode."
    ::= { msvmS3DisplayControllerEntry 4 }

msvms3dcCapabilityDescriptions OBJECT-TYPE
    SYNTAX     WtcsDisplayString
    MAX-ACCESS read-only
    STATUS     current
    DESCRIPTION
        "An array of free-form strings providing more
        detailed explanations for any of the video
        Accelerator features indicated in the Capabilities
        array. Note, each entry of this array is related to
        the entry in the Capabilities array that is located
        at the same index."
    ::= { msvmS3DisplayControllerEntry 5 }

msvms3dcCaption OBJECT-TYPE
    SYNTAX     WtcsDisplayString (SIZE (0..64))
    MAX-ACCESS read-only
    STATUS     current
    DESCRIPTION
        "The Caption property is a short textual
        description (one- line string) of the object."
    ::= { msvmS3DisplayControllerEntry 6 }

msvms3dcCreationClassName OBJECT-TYPE
    SYNTAX     WtcsDisplayString (SIZE (0..256))
    MAX-ACCESS read-only
    STATUS     current
    DESCRIPTION
        "CreationClassName indicates the name of the class
        or the subclass used in the creation of an
        instance. When used with the other key properties
        of this class, this property allows all instances
        of this class and its subclasses to be uniquely
        identified."
    ::= { msvmS3DisplayControllerEntry 7 }

msvms3dcDescription OBJECT-TYPE
    SYNTAX     WtcsDisplayString
    MAX-ACCESS read-only
    STATUS     current
    DESCRIPTION
        "The Description property provides a textual
        description of the object."
    ::= { msvmS3DisplayControllerEntry 8 }

msvms3dcDeviceID OBJECT-TYPE
    SYNTAX     WtcsDisplayString (SIZE (0..64))
    MAX-ACCESS read-only
    STATUS     current
    DESCRIPTION
        "An address or other identifying information used
        to uniquely name the LogicalDevice."
    ::= { msvmS3DisplayControllerEntry 9 }

msvms3dcElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmS3DisplayControllerEntry 10 }

msvms3dcEnabledDefault OBJECT-TYPE
    SYNTAX     INTEGER {
        enabled(2),
        disabled(3),
        notApplicable(5),
        enabledbutOffline(6),
        noDefault(7)
    }
    MAX-ACCESS read-only
    STATUS     current
    DESCRIPTION
        "An enumerated value indicating an administrator's
        default or startup configuration for the Enabled
        State of an element. By default, the element is
        'Enabled' (value=2)."
    ::= { msvmS3DisplayControllerEntry 11 }

msvms3dcEnabledState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "EnabledState is an integer enumeration that
        indicates the enabled and disabled states of an
        element. It can also indicate the transitions
        between these requested states. For example,
        shutting down (value=4) and starting (value=10) are
        transient states between enabled and disabled. The
        following text briefly summarizes the various
        enabled and disabled states: 
        Enabled (2) indicates that the element is or could
        be executing commands, will process any queued
        commands, and queues new requests. 
        Disabled (3) indicates that the element will not
        execute commands and will drop any new requests. 
        Shutting Down (4) indicates that the element is in
        the process of going to a Disabled state. 
        Not Applicable (5) indicates the element does not
        support being enabled or disabled. 
        Enabled but Offline (6) indicates that the element
        might be completing commands, and will drop any new
        requests. 
        Test (7) indicates that the element is in a test
        state. 
        Deferred (8) indicates that the element might be
        completing commands, but will queue any new
        requests. 
        Quiesce (9) indicates that the element is enabled
        but in a restricted mode. The behavior of the
        element is similar to the Enabled state, but it
        processes only a restricted set of commands. All
        other requests are queued. 
        Starting (10) indicates that the element is in the
        process of going to an Enabled state. New requests
        are queued."
    ::= { msvmS3DisplayControllerEntry 12 }

msvms3dcErrorCleared OBJECT-TYPE
    SYNTAX     TruthValue
    MAX-ACCESS read-only
    STATUS     current
    DESCRIPTION
        "Note: The use of this method is deprecated. 
        Deprecated description: ErrorCleared is a Boolean
        property that indicates that the error reported in
        LastErrorCode is now cleared."
    ::= { msvmS3DisplayControllerEntry 13 }

msvms3dcErrorDescription OBJECT-TYPE
    SYNTAX     WtcsDisplayString
    MAX-ACCESS read-only
    STATUS     current
    DESCRIPTION
        "Note: The use of this method is deprecated. 
        Deprecated description: ErrorDescription is a
        free-form string that supplies more information
        about the error recorded in LastErrorCode and
        information on any corrective actions that can be
        taken."
    ::= { msvmS3DisplayControllerEntry 14 }

msvms3dcHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmS3DisplayControllerEntry 15 }

msvms3dcIdentifyingDescriptions OBJECT-TYPE
    SYNTAX     WtcsDisplayString
    MAX-ACCESS read-only
    STATUS     current
    DESCRIPTION
        "An array of free-form strings providing
        explanations and details behind the entries in the
        OtherIdentifyingInfo array. Note that each entry of
        this array is related to the entry in
        OtherIdentifyingInfo that is located at the same
        index."
    ::= { msvmS3DisplayControllerEntry 16 }

msvms3dcInstallDate OBJECT-TYPE
    SYNTAX     DateAndTime
    MAX-ACCESS read-only
    STATUS     current
    DESCRIPTION
        "A datetime value that indicates when the object
        was installed. Lack of a value does not indicate
        that the object is not installed."
    ::= { msvmS3DisplayControllerEntry 17 }

msvms3dcLastErrorCode OBJECT-TYPE
    SYNTAX     Gauge32
    MAX-ACCESS read-only
    STATUS     current
    DESCRIPTION
        "Note: The use of this method is deprecated. 
        Deprecated description: LastErrorCode captures the
        last error code reported by the LogicalDevice."
    ::= { msvmS3DisplayControllerEntry 18 }

msvms3dcLocationIndicator OBJECT-TYPE
    SYNTAX     INTEGER {
        unknown(0),
        on(2),
        off(3),
        notSupported(4)
    }
    MAX-ACCESS read-only
    STATUS     current
    DESCRIPTION
        "An integer that reflects the state of an indicator
        (e.g., LED) that is part of a device. Reading the
        value gives the current state. Writing the value
        with 'On'/'Off' turns the indicator on/off, other
        values may not be written."
    ::= { msvmS3DisplayControllerEntry 19 }

msvms3dcMaxMemorySupported OBJECT-TYPE
    SYNTAX     Gauge32
    UNITS "Bytes"
    MAX-ACCESS read-only
    STATUS     current
    DESCRIPTION
        "Maximum amount of memory supported in bytes."
    ::= { msvmS3DisplayControllerEntry 20 }

msvms3dcMaxNumberControlled OBJECT-TYPE
    SYNTAX     Gauge32
    MAX-ACCESS read-only
    STATUS     current
    DESCRIPTION
        "Maximum number of directly addressable entities
        that are supported by this Controller. A value of 0
        should be used if the number is unknown or
        unlimited."
    ::= { msvmS3DisplayControllerEntry 21 }

msvms3dcMaxQuiesceTime OBJECT-TYPE
    SYNTAX     Gauge32
    UNITS "MilliSeconds"
    MAX-ACCESS read-only
    STATUS     current
    DESCRIPTION
        "Note: The use of this property has been
        deprecated. When evaluating the use of Quiesce, it
        was determined that this single property is not
        adequate for describing when a device will
        automatically exit a quiescent state. In fact, the
        most likely scenario for a device to exit a
        quiescent state was determined to be based on the
        number of outstanding requests queued rather than
        on a maximum time. This decision will be
        re-evaluated and repositioned later. 
        Deprecated description: Maximum time, in
        milliseconds, that a Device can run in a 'Quiesced'
        state. The state is defined in its Availability and
        AdditionalAvailability properties, where 'Quiesced'
        is conveyed by the value 21. What occurs at the end
        of the time limit is device-specific. The Device
        can unquiesce, can be offline, or can take other
        actions. A value of 0 indicates that a Device can
        remain quiesced indefinitely."
    ::= { msvmS3DisplayControllerEntry 22 }

msvms3dcName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmS3DisplayControllerEntry 23 }

msvms3dcNumberOfVideoPages OBJECT-TYPE
    SYNTAX     Gauge32
    MAX-ACCESS read-only
    STATUS     current
    DESCRIPTION
        "Number of video pages supported given the current
        resolutions and available memory."
    ::= { msvmS3DisplayControllerEntry 24 }

msvms3dcOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmS3DisplayControllerEntry 25 }

msvms3dcOtherEnabledState OBJECT-TYPE
    SYNTAX     WtcsDisplayString
    MAX-ACCESS read-only
    STATUS     current
    DESCRIPTION
        "A string that describes the enabled or disabled
        state of the element when the EnabledState property
        is set to 1 ('Other'). This property must be set to
        null when EnabledState is any value other than 1."
    ::= { msvmS3DisplayControllerEntry 26 }

msvms3dcOtherIdentifyingInfo OBJECT-TYPE
    SYNTAX     WtcsDisplayString (SIZE (0..256))
    MAX-ACCESS read-only
    STATUS     current
    DESCRIPTION
        "OtherIdentifyingInfo captures data, in addition to
        DeviceID information, that could be used to
        identify a LogicalDevice. For example, you could
        use this property to hold the operating system's
        user-friendly name for the Device."
    ::= { msvmS3DisplayControllerEntry 27 }

msvms3dcOtherVideoMemoryType OBJECT-TYPE
    SYNTAX     WtcsDisplayString
    MAX-ACCESS read-only
    STATUS     current
    DESCRIPTION
        "A string describing the video memory type when the
        instance's VideoMemoryType property is 1
        ('Other')."
    ::= { msvmS3DisplayControllerEntry 28 }

msvms3dcPowerMgtCapability OBJECT-TYPE
    SYNTAX     INTEGER {
        unknown(0),
        notSupported(1),
        disabled(2),
        enabled(3),
        powerSavingModesEnteredAutomatic(4),
        powerStateSettable(5),
        powerCyclingSupported(6),
        timedPowerOnSupported(7)
    }
    MAX-ACCESS read-only
    STATUS     current
    DESCRIPTION
        "Note: The use of this property has been
        deprecated. Instead, use the PowerCapabilites
        property in an associated
        PowerManagementCapabilities class. Deprecated
        description: An enumerated array describing the
        power management capabilities of the Device."
    ::= { msvmS3DisplayControllerEntry 29 }

msvms3dcPowerManagementSupported OBJECT-TYPE
    SYNTAX     TruthValue
    MAX-ACCESS read-only
    STATUS     current
    DESCRIPTION
        "Note: The use of this property has been
        deprecated. Instead, the existence of an associated
        PowerManagementCapabilities class (associated using
        the ElementCapabilities relationship) indicates
        that power management is supported. Deprecated
        description: Boolean that indicates that the Device
        can use power management."
    ::= { msvmS3DisplayControllerEntry 30 }

msvms3dcPowerOnHours OBJECT-TYPE
    SYNTAX     Gauge32
    UNITS "Hours"
    MAX-ACCESS read-only
    STATUS     current
    DESCRIPTION
        "Note: The use of this method is deprecated. 
        Deprecated description: The number of consecutive
        hours that this Device has been powered on since
        its last power cycle."
    ::= { msvmS3DisplayControllerEntry 31 }

msvms3dcProtocolDescription OBJECT-TYPE
    SYNTAX     WtcsDisplayString
    MAX-ACCESS read-only
    STATUS     current
    DESCRIPTION
        "A free-form string that provides more information
        that is related to the ProtocolSupported by the
        Controller."
    ::= { msvmS3DisplayControllerEntry 32 }

msvms3dcProtocolSupported OBJECT-TYPE
    SYNTAX     Integer32
    MAX-ACCESS read-only
    STATUS     current
    DESCRIPTION
        "The protocol used by the Controller to access
        controlled Devices."
    ::= { msvmS3DisplayControllerEntry 33 }

msvms3dcRequestedState OBJECT-TYPE
    SYNTAX     INTEGER {
        enabled(2),
        disabled(3),
        shutDown(4),
        noChange(5),
        offline(6),
        test(7),
        deferred(8),
        quiesce(9),
        reboot(10),
        reset(11),
        notApplicable(12)
    }
    MAX-ACCESS read-only
    STATUS     current
    DESCRIPTION
        "RequestedState is an integer enumeration that
        indicates the last requested or desired state for
        the element. The actual state of the element is
        represented by EnabledState. This property is
        provided to compare the last requested and current
        enabled or disabled states. Note that when
        EnabledState is set to 5 ('Not Applicable'), then
        this property has no meaning. By default, the
        RequestedState of the element is 5 ('No Change').
        Refer to the EnabledState property description for
        explanations of the values in the RequestedState
        enumeration. 
        
        It should be noted that there are two new values in
        RequestedState that build on the statuses of
        EnabledState. These are 'Reboot' (10) and 'Reset'
        (11). Reboot refers to doing a 'Shut Down' and then
        moving to an 'Enabled' state. Reset indicates that
        the element is first 'Disabled' and then 'Enabled'.
        The distinction between requesting 'Shut Down' and
        'Disabled' should also be noted. Shut Down requests
        an orderly transition to the Disabled state, and
        might involve removing power, to completely erase
        any existing state. The Disabled state requests an
        immediate disabling of the element, such that it
        will not execute or accept any commands or
        processing requests. 
        
        This property is set as the result of a method
        invocation (such as Start or StopService on
        CIM_Service), or can be overridden and defined as
        WRITEable in a subclass. The method approach is
        considered superior to a WRITEable property,
        because it allows an explicit invocation of the
        operation and the return of a result code. 
        
        A particular instance of EnabledLogicalElement
        might not support RequestedStateChange. If this
        occurs, the value 12 ('Not Applicable') is used."
    ::= { msvmS3DisplayControllerEntry 34 }

msvms3dcStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmS3DisplayControllerEntry 35 }

msvms3dcStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmS3DisplayControllerEntry 36 }

msvms3dcStatusInfo OBJECT-TYPE
    SYNTAX     INTEGER {
        other(1),
        unknown(2),
        enabled(3),
        disabled(4),
        notApplicable(5)
    }
    MAX-ACCESS read-only
    STATUS     current
    DESCRIPTION
        "Note: The use of this method is deprecated in lieu
        of a more clearly named property (EnabledState)
        that is inherited from ManagedSystemElement and
        that has additional enumerated values. 
        Deprecated description: The StatusInfo property
        indicates whether the Logical Device is in an
        enabled state (value=3), disabled state (value=4),
        some other state (value=1), or an unknown state
        (value=2). If this property does not apply to the
        LogicalDevice, the value 5 ('Not Applicable')
        should be used. If a Device is
        ('Enabled')(value=3), it has been powered up and is
        configured and operational. The Device might or
        might not be functionally active, depending on
        whether its Availability (or
        AdditionalAvailability) indicates that it is
        ('Running/Full Power')(value=3) or ('Off line')
        (value=8). In an enabled but offline mode, a Device
        might be performing out-of-band requests, such as
        running Diagnostics. If StatusInfo is ('Disabled')
        (value=4), a Device can only be 'enabled' or
        powered off. In a personal computer environment,
        ('Disabled') means that the driver of the device is
        not available in the stack. In other environments,
        a Device can be disabled by removing its
        configuration file. A disabled device is physically
        present in a System and consuming resources, but it
        cannot be communicated with until a driver is
        loaded, a configuration file is loaded, or some
        other 'enabling' activity has occurred."
    ::= { msvmS3DisplayControllerEntry 37 }

msvms3dcSystemCreationClassName OBJECT-TYPE
    SYNTAX     WtcsDisplayString (SIZE (0..256))
    MAX-ACCESS read-only
    STATUS     current
    DESCRIPTION
        "The CreationClassName of the scoping system."
    ::= { msvmS3DisplayControllerEntry 38 }

msvms3dcSystemName OBJECT-TYPE
    SYNTAX     WtcsDisplayString (SIZE (0..256))
    MAX-ACCESS read-only
    STATUS     current
    DESCRIPTION
        "The System Name of the scoping system."
    ::= { msvmS3DisplayControllerEntry 39 }

msvms3dcTimeOfLastReset OBJECT-TYPE
    SYNTAX     DateAndTime
    MAX-ACCESS read-only
    STATUS     current
    DESCRIPTION
        "Time of last reset of the Controller."
    ::= { msvmS3DisplayControllerEntry 40 }

msvms3dcTimeOfLastStateChange OBJECT-TYPE
    SYNTAX     DateAndTime
    MAX-ACCESS read-only
    STATUS     current
    DESCRIPTION
        "The date or time when the EnabledState of the
        element last changed. If the state of the element
        has not changed and this property is populated,
        then it must be set to a 0 interval value. If a
        state change was requested, but rejected or not yet
        processed, the property must not be updated."
    ::= { msvmS3DisplayControllerEntry 41 }

msvms3dcTotalPowerOnHours OBJECT-TYPE
    SYNTAX     Gauge32
    UNITS "Hours"
    MAX-ACCESS read-only
    STATUS     current
    DESCRIPTION
        "Note: The use of this method is deprecated. 
        Deprecated description: The total number of hours
        that this Device has been powered on."
    ::= { msvmS3DisplayControllerEntry 42 }

msvms3dcVideoMemoryType OBJECT-TYPE
    SYNTAX     INTEGER {
        unknown(0),
        other(1),
        vram(2),
        dram(3),
        sram(4),
        wram(5),
        edoRAM(6),
        burstSynchronousDRAM(7),
        pipelinedBurstSRAM(8),
        cdram(9),
        a3DRAM(10),
        sdram(11),
        sgram(12)
    }
    MAX-ACCESS read-only
    STATUS     current
    DESCRIPTION
        "An integer enumeration indicating the type of
        video memory."
    ::= { msvmS3DisplayControllerEntry 43 }

msvms3dcVideoProcessor OBJECT-TYPE
    SYNTAX     WtcsDisplayString
    MAX-ACCESS read-only
    STATUS     current
    DESCRIPTION
        "A free-form string describing the video
        processor/Controller."
    ::= { msvmS3DisplayControllerEntry 44 }

msvmSyntheticDisplayControlTable OBJECT-TYPE
    SYNTAX     SEQUENCE OF MsvmSyntheticDisplayController
    MAX-ACCESS not-accessible
    STATUS     current
    DESCRIPTION
        "Represents the state of the synthetic display
        controller that is present in each virtual machine
        configuration."
    ::= { msvmVideo 2 }

msvmSyntheticDisplayControlEntry OBJECT-TYPE
    SYNTAX     MsvmSyntheticDisplayController
    MAX-ACCESS not-accessible
    STATUS     current
    DESCRIPTION
        "None"
    INDEX      { msvmsydcIndex }
    ::= { msvmSyntheticDisplayControlTable 1 }

MsvmSyntheticDisplayController ::= SEQUENCE {
    msvmsydcIndex Integer32,
    msvmsydcAcceleratorCapabilities INTEGER,
    msvmsydcAdditionalAvailability INTEGER,
    msvmsydcAvailability INTEGER,
    msvmsydcCapabilityDescriptions WtcsDisplayString,
    msvmsydcCaption WtcsDisplayString,
    msvmsydcCreationClassName WtcsDisplayString,
    msvmsydcDescription WtcsDisplayString,
    msvmsydcDeviceID WtcsDisplayString,
    msvmsydcElementName WtcsDisplayString,
    msvmsydcEnabledDefault INTEGER,
    msvmsydcEnabledState INTEGER,
    msvmsydcErrorCleared TruthValue,
    msvmsydcErrorDescription WtcsDisplayString,
    msvmsydcHealthState INTEGER,
    msvmsydcIdentifyingDescriptions WtcsDisplayString,
    msvmsydcInstallDate DateAndTime,
    msvmsydcLastErrorCode Gauge32,
    msvmsydcLocationIndicator INTEGER,
    msvmsydcMaxMemorySupported Gauge32,
    msvmsydcMaxNumberControlled Gauge32,
    msvmsydcMaxQuiesceTime Gauge32,
    msvmsydcName WtcsDisplayString,
    msvmsydcNumberOfVideoPages Gauge32,
    msvmsydcOperationalStatus INTEGER,
    msvmsydcOtherEnabledState WtcsDisplayString,
    msvmsydcOtherIdentifyingInfo WtcsDisplayString,
    msvmsydcOtherVideoMemoryType WtcsDisplayString,
    msvmsydcPowerMgtCapability INTEGER,
    msvmsydcPowerManagementSupported TruthValue,
    msvmsydcPowerOnHours Gauge32,
    msvmsydcProtocolDescription WtcsDisplayString,
    msvmsydcProtocolSupported Integer32,
    msvmsydcRequestedState INTEGER,
    msvmsydcStatus WtcsDisplayString,
    msvmsydcStatusDescriptions WtcsDisplayString,
    msvmsydcStatusInfo INTEGER,
    msvmsydcSystemCreationClassName WtcsDisplayString,
    msvmsydcSystemName WtcsDisplayString,
    msvmsydcTimeOfLastReset DateAndTime,
    msvmsydcTimeOfLastStateChange DateAndTime,
    msvmsydcTotalPowerOnHours Gauge32,
    msvmsydcVideoMemoryType INTEGER,
    msvmsydcVideoProcessor WtcsDisplayString
}

msvmsydcIndex OBJECT-TYPE
    SYNTAX     Integer32 (1..2147483647)
    MAX-ACCESS read-only
    STATUS     current
    DESCRIPTION
        "The value of this object uniquely identifies the
        instance entry for this class."
    ::= { msvmSyntheticDisplayControlEntry 1 }

msvmsydcAcceleratorCapabilities OBJECT-TYPE
    SYNTAX     INTEGER {
        unknown(0),
        other(1),
        graphicsAccelerator(2),
        a3DAccelerator(3),
        pciFastWrite(4),
        multiMonitorSupport(5),
        pciMastering(6),
        secondMonochromeAdapterSupport(7),
        largeMemoryAddressSupport(8)
    }
    MAX-ACCESS read-only
    STATUS     current
    DESCRIPTION
        "An array of integers indicating the graphics and
        3D capabilities of the DisplayController."
    ::= { msvmSyntheticDisplayControlEntry 2 }

msvmsydcAdditionalAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Additional availability and status of the Device
        in addition to that specified in the Availability
        property. The Availability property denotes the
        primary status and availability of the Device. In
        some cases, this property will not be sufficient to
        denote the complete status of the Device. In those
        cases, the AdditionalAvailability property can be
        used to provide further information. For example,
        the primary Availability of a device might be 'Off
        line' (value=8) or in a low-power state
        (AdditionalAvailability value=14), or the Device
        could be running Diagnostics
        (AdditionalAvailability value=5, 'In Test')."
    ::= { msvmSyntheticDisplayControlEntry 3 }

msvmsydcAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Note: The use of this property has been
        deprecated. 
        Deprecated description: The primary availability
        and status of the Device. (Additional status
        information can be specified using the Additional
        Availability array property.) For example, the
        Availability property indicates that the Device is
        running and has full power (value=3), or is in a
        warning (4), test (5), degraded (10) or power save
        state (values 13-15 and 17). The Power Save states
        are defined as follows: Value 13 ('Power Save -
        Unknown') indicates that the Device is known to be
        in a power save mode, but its exact status in this
        mode is unknown; value 14 ('Power Save - Low Power
        Mode') indicates that the Device is in a power save
        state but still functioning, and might exhibit
        degraded performance; value 15 ('Power Save -
        Standby') indicates that the Device is not
        functioning but could be brought to full power
        'quickly'; and value 17 ('Power Save - Warning')
        indicates that the Device is in a warning state,
        but is also in a power save mode."
    ::= { msvmSyntheticDisplayControlEntry 4 }

msvmsydcCapabilityDescriptions OBJECT-TYPE
    SYNTAX     WtcsDisplayString
    MAX-ACCESS read-only
    STATUS     current
    DESCRIPTION
        "An array of free-form strings providing more
        detailed explanations for any of the video
        Accelerator features indicated in the Capabilities
        array. Note, each entry of this array is related to
        the entry in the Capabilities array that is located
        at the same index."
    ::= { msvmSyntheticDisplayControlEntry 5 }

msvmsydcCaption OBJECT-TYPE
    SYNTAX     WtcsDisplayString (SIZE (0..64))
    MAX-ACCESS read-only
    STATUS     current
    DESCRIPTION
        "The Caption property is a short textual
        description (one- line string) of the object."
    ::= { msvmSyntheticDisplayControlEntry 6 }

msvmsydcCreationClassName OBJECT-TYPE
    SYNTAX     WtcsDisplayString (SIZE (0..256))
    MAX-ACCESS read-only
    STATUS     current
    DESCRIPTION
        "CreationClassName indicates the name of the class
        or the subclass used in the creation of an
        instance. When used with the other key properties
        of this class, this property allows all instances
        of this class and its subclasses to be uniquely
        identified."
    ::= { msvmSyntheticDisplayControlEntry 7 }

msvmsydcDescription OBJECT-TYPE
    SYNTAX     WtcsDisplayString
    MAX-ACCESS read-only
    STATUS     current
    DESCRIPTION
        "The Description property provides a textual
        description of the object."
    ::= { msvmSyntheticDisplayControlEntry 8 }

msvmsydcDeviceID OBJECT-TYPE
    SYNTAX     WtcsDisplayString (SIZE (0..64))
    MAX-ACCESS read-only
    STATUS     current
    DESCRIPTION
        "An address or other identifying information used
        to uniquely name the LogicalDevice."
    ::= { msvmSyntheticDisplayControlEntry 9 }

msvmsydcElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmSyntheticDisplayControlEntry 10 }

msvmsydcEnabledDefault OBJECT-TYPE
    SYNTAX     INTEGER {
        enabled(2),
        disabled(3),
        notApplicable(5),
        enabledbutOffline(6),
        noDefault(7)
    }
    MAX-ACCESS read-only
    STATUS     current
    DESCRIPTION
        "An enumerated value indicating an administrator's
        default or startup configuration for the Enabled
        State of an element. By default, the element is
        'Enabled' (value=2)."
    ::= { msvmSyntheticDisplayControlEntry 11 }

msvmsydcEnabledState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "EnabledState is an integer enumeration that
        indicates the enabled and disabled states of an
        element. It can also indicate the transitions
        between these requested states. For example,
        shutting down (value=4) and starting (value=10) are
        transient states between enabled and disabled. The
        following text briefly summarizes the various
        enabled and disabled states: 
        Enabled (2) indicates that the element is or could
        be executing commands, will process any queued
        commands, and queues new requests. 
        Disabled (3) indicates that the element will not
        execute commands and will drop any new requests. 
        Shutting Down (4) indicates that the element is in
        the process of going to a Disabled state. 
        Not Applicable (5) indicates the element does not
        support being enabled or disabled. 
        Enabled but Offline (6) indicates that the element
        might be completing commands, and will drop any new
        requests. 
        Test (7) indicates that the element is in a test
        state. 
        Deferred (8) indicates that the element might be
        completing commands, but will queue any new
        requests. 
        Quiesce (9) indicates that the element is enabled
        but in a restricted mode. The behavior of the
        element is similar to the Enabled state, but it
        processes only a restricted set of commands. All
        other requests are queued. 
        Starting (10) indicates that the element is in the
        process of going to an Enabled state. New requests
        are queued."
    ::= { msvmSyntheticDisplayControlEntry 12 }

msvmsydcErrorCleared OBJECT-TYPE
    SYNTAX     TruthValue
    MAX-ACCESS read-only
    STATUS     current
    DESCRIPTION
        "Note: The use of this method is deprecated. 
        Deprecated description: ErrorCleared is a Boolean
        property that indicates that the error reported in
        LastErrorCode is now cleared."
    ::= { msvmSyntheticDisplayControlEntry 13 }

msvmsydcErrorDescription OBJECT-TYPE
    SYNTAX     WtcsDisplayString
    MAX-ACCESS read-only
    STATUS     current
    DESCRIPTION
        "Note: The use of this method is deprecated. 
        Deprecated description: ErrorDescription is a
        free-form string that supplies more information
        about the error recorded in LastErrorCode and
        information on any corrective actions that can be
        taken."
    ::= { msvmSyntheticDisplayControlEntry 14 }

msvmsydcHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmSyntheticDisplayControlEntry 15 }

msvmsydcIdentifyingDescriptions OBJECT-TYPE
    SYNTAX     WtcsDisplayString
    MAX-ACCESS read-only
    STATUS     current
    DESCRIPTION
        "An array of free-form strings providing
        explanations and details behind the entries in the
        OtherIdentifyingInfo array. Note that each entry of
        this array is related to the entry in
        OtherIdentifyingInfo that is located at the same
        index."
    ::= { msvmSyntheticDisplayControlEntry 16 }

msvmsydcInstallDate OBJECT-TYPE
    SYNTAX     DateAndTime
    MAX-ACCESS read-only
    STATUS     current
    DESCRIPTION
        "A datetime value that indicates when the object
        was installed. Lack of a value does not indicate
        that the object is not installed."
    ::= { msvmSyntheticDisplayControlEntry 17 }

msvmsydcLastErrorCode OBJECT-TYPE
    SYNTAX     Gauge32
    MAX-ACCESS read-only
    STATUS     current
    DESCRIPTION
        "Note: The use of this method is deprecated. 
        Deprecated description: LastErrorCode captures the
        last error code reported by the LogicalDevice."
    ::= { msvmSyntheticDisplayControlEntry 18 }

msvmsydcLocationIndicator OBJECT-TYPE
    SYNTAX     INTEGER {
        unknown(0),
        on(2),
        off(3),
        notSupported(4)
    }
    MAX-ACCESS read-only
    STATUS     current
    DESCRIPTION
        "An integer that reflects the state of an indicator
        (e.g., LED) that is part of a device. Reading the
        value gives the current state. Writing the value
        with 'On'/'Off' turns the indicator on/off, other
        values may not be written."
    ::= { msvmSyntheticDisplayControlEntry 19 }

msvmsydcMaxMemorySupported OBJECT-TYPE
    SYNTAX     Gauge32
    UNITS "Bytes"
    MAX-ACCESS read-only
    STATUS     current
    DESCRIPTION
        "Maximum amount of memory supported in bytes."
    ::= { msvmSyntheticDisplayControlEntry 20 }

msvmsydcMaxNumberControlled OBJECT-TYPE
    SYNTAX     Gauge32
    MAX-ACCESS read-only
    STATUS     current
    DESCRIPTION
        "Maximum number of directly addressable entities
        that are supported by this Controller. A value of 0
        should be used if the number is unknown or
        unlimited."
    ::= { msvmSyntheticDisplayControlEntry 21 }

msvmsydcMaxQuiesceTime OBJECT-TYPE
    SYNTAX     Gauge32
    UNITS "MilliSeconds"
    MAX-ACCESS read-only
    STATUS     current
    DESCRIPTION
        "Note: The use of this property has been
        deprecated. When evaluating the use of Quiesce, it
        was determined that this single property is not
        adequate for describing when a device will
        automatically exit a quiescent state. In fact, the
        most likely scenario for a device to exit a
        quiescent state was determined to be based on the
        number of outstanding requests queued rather than
        on a maximum time. This decision will be
        re-evaluated and repositioned later. 
        Deprecated description: Maximum time, in
        milliseconds, that a Device can run in a 'Quiesced'
        state. The state is defined in its Availability and
        AdditionalAvailability properties, where 'Quiesced'
        is conveyed by the value 21. What occurs at the end
        of the time limit is device-specific. The Device
        can unquiesce, can be offline, or can take other
        actions. A value of 0 indicates that a Device can
        remain quiesced indefinitely."
    ::= { msvmSyntheticDisplayControlEntry 22 }

msvmsydcName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmSyntheticDisplayControlEntry 23 }

msvmsydcNumberOfVideoPages OBJECT-TYPE
    SYNTAX     Gauge32
    MAX-ACCESS read-only
    STATUS     current
    DESCRIPTION
        "Number of video pages supported given the current
        resolutions and available memory."
    ::= { msvmSyntheticDisplayControlEntry 24 }

msvmsydcOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmSyntheticDisplayControlEntry 25 }

msvmsydcOtherEnabledState OBJECT-TYPE
    SYNTAX     WtcsDisplayString
    MAX-ACCESS read-only
    STATUS     current
    DESCRIPTION
        "A string that describes the enabled or disabled
        state of the element when the EnabledState property
        is set to 1 ('Other'). This property must be set to
        null when EnabledState is any value other than 1."
    ::= { msvmSyntheticDisplayControlEntry 26 }

msvmsydcOtherIdentifyingInfo OBJECT-TYPE
    SYNTAX     WtcsDisplayString (SIZE (0..256))
    MAX-ACCESS read-only
    STATUS     current
    DESCRIPTION
        "OtherIdentifyingInfo captures data, in addition to
        DeviceID information, that could be used to
        identify a LogicalDevice. For example, you could
        use this property to hold the operating system's
        user-friendly name for the Device."
    ::= { msvmSyntheticDisplayControlEntry 27 }

msvmsydcOtherVideoMemoryType OBJECT-TYPE
    SYNTAX     WtcsDisplayString
    MAX-ACCESS read-only
    STATUS     current
    DESCRIPTION
        "A string describing the video memory type when the
        instance's VideoMemoryType property is 1
        ('Other')."
    ::= { msvmSyntheticDisplayControlEntry 28 }

msvmsydcPowerMgtCapability OBJECT-TYPE
    SYNTAX     INTEGER {
        unknown(0),
        notSupported(1),
        disabled(2),
        enabled(3),
        powerSavingModesEnteredAutomatic(4),
        powerStateSettable(5),
        powerCyclingSupported(6),
        timedPowerOnSupported(7)
    }
    MAX-ACCESS read-only
    STATUS     current
    DESCRIPTION
        "Note: The use of this property has been
        deprecated. Instead, use the PowerCapabilites
        property in an associated
        PowerManagementCapabilities class. Deprecated
        description: An enumerated array describing the
        power management capabilities of the Device."
    ::= { msvmSyntheticDisplayControlEntry 29 }

msvmsydcPowerManagementSupported OBJECT-TYPE
    SYNTAX     TruthValue
    MAX-ACCESS read-only
    STATUS     current
    DESCRIPTION
        "Note: The use of this property has been
        deprecated. Instead, the existence of an associated
        PowerManagementCapabilities class (associated using
        the ElementCapabilities relationship) indicates
        that power management is supported. Deprecated
        description: Boolean that indicates that the Device
        can use power management."
    ::= { msvmSyntheticDisplayControlEntry 30 }

msvmsydcPowerOnHours OBJECT-TYPE
    SYNTAX     Gauge32
    UNITS "Hours"
    MAX-ACCESS read-only
    STATUS     current
    DESCRIPTION
        "Note: The use of this method is deprecated. 
        Deprecated description: The number of consecutive
        hours that this Device has been powered on since
        its last power cycle."
    ::= { msvmSyntheticDisplayControlEntry 31 }

msvmsydcProtocolDescription OBJECT-TYPE
    SYNTAX     WtcsDisplayString
    MAX-ACCESS read-only
    STATUS     current
    DESCRIPTION
        "A free-form string that provides more information
        that is related to the ProtocolSupported by the
        Controller."
    ::= { msvmSyntheticDisplayControlEntry 32 }

msvmsydcProtocolSupported OBJECT-TYPE
    SYNTAX     Integer32
    MAX-ACCESS read-only
    STATUS     current
    DESCRIPTION
        "The protocol used by the Controller to access
        controlled Devices."
    ::= { msvmSyntheticDisplayControlEntry 33 }

msvmsydcRequestedState OBJECT-TYPE
    SYNTAX     INTEGER {
        enabled(2),
        disabled(3),
        shutDown(4),
        noChange(5),
        offline(6),
        test(7),
        deferred(8),
        quiesce(9),
        reboot(10),
        reset(11),
        notApplicable(12)
    }
    MAX-ACCESS read-only
    STATUS     current
    DESCRIPTION
        "RequestedState is an integer enumeration that
        indicates the last requested or desired state for
        the element. The actual state of the element is
        represented by EnabledState. This property is
        provided to compare the last requested and current
        enabled or disabled states. Note that when
        EnabledState is set to 5 ('Not Applicable'), then
        this property has no meaning. By default, the
        RequestedState of the element is 5 ('No Change').
        Refer to the EnabledState property description for
        explanations of the values in the RequestedState
        enumeration. 
        
        It should be noted that there are two new values in
        RequestedState that build on the statuses of
        EnabledState. These are 'Reboot' (10) and 'Reset'
        (11). Reboot refers to doing a 'Shut Down' and then
        moving to an 'Enabled' state. Reset indicates that
        the element is first 'Disabled' and then 'Enabled'.
        The distinction between requesting 'Shut Down' and
        'Disabled' should also be noted. Shut Down requests
        an orderly transition to the Disabled state, and
        might involve removing power, to completely erase
        any existing state. The Disabled state requests an
        immediate disabling of the element, such that it
        will not execute or accept any commands or
        processing requests. 
        
        This property is set as the result of a method
        invocation (such as Start or StopService on
        CIM_Service), or can be overridden and defined as
        WRITEable in a subclass. The method approach is
        considered superior to a WRITEable property,
        because it allows an explicit invocation of the
        operation and the return of a result code. 
        
        A particular instance of EnabledLogicalElement
        might not support RequestedStateChange. If this
        occurs, the value 12 ('Not Applicable') is used."
    ::= { msvmSyntheticDisplayControlEntry 34 }

msvmsydcStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmSyntheticDisplayControlEntry 35 }

msvmsydcStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmSyntheticDisplayControlEntry 36 }

msvmsydcStatusInfo OBJECT-TYPE
    SYNTAX     INTEGER {
        other(1),
        unknown(2),
        enabled(3),
        disabled(4),
        notApplicable(5)
    }
    MAX-ACCESS read-only
    STATUS     current
    DESCRIPTION
        "Note: The use of this method is deprecated in lieu
        of a more clearly named property (EnabledState)
        that is inherited from ManagedSystemElement and
        that has additional enumerated values. 
        Deprecated description: The StatusInfo property
        indicates whether the Logical Device is in an
        enabled state (value=3), disabled state (value=4),
        some other state (value=1), or an unknown state
        (value=2). If this property does not apply to the
        LogicalDevice, the value 5 ('Not Applicable')
        should be used. If a Device is
        ('Enabled')(value=3), it has been powered up and is
        configured and operational. The Device might or
        might not be functionally active, depending on
        whether its Availability (or
        AdditionalAvailability) indicates that it is
        ('Running/Full Power')(value=3) or ('Off line')
        (value=8). In an enabled but offline mode, a Device
        might be performing out-of-band requests, such as
        running Diagnostics. If StatusInfo is ('Disabled')
        (value=4), a Device can only be 'enabled' or
        powered off. In a personal computer environment,
        ('Disabled') means that the driver of the device is
        not available in the stack. In other environments,
        a Device can be disabled by removing its
        configuration file. A disabled device is physically
        present in a System and consuming resources, but it
        cannot be communicated with until a driver is
        loaded, a configuration file is loaded, or some
        other 'enabling' activity has occurred."
    ::= { msvmSyntheticDisplayControlEntry 37 }

msvmsydcSystemCreationClassName OBJECT-TYPE
    SYNTAX     WtcsDisplayString (SIZE (0..256))
    MAX-ACCESS read-only
    STATUS     current
    DESCRIPTION
        "The CreationClassName of the scoping system."
    ::= { msvmSyntheticDisplayControlEntry 38 }

msvmsydcSystemName OBJECT-TYPE
    SYNTAX     WtcsDisplayString (SIZE (0..256))
    MAX-ACCESS read-only
    STATUS     current
    DESCRIPTION
        "The System Name of the scoping system."
    ::= { msvmSyntheticDisplayControlEntry 39 }

msvmsydcTimeOfLastReset OBJECT-TYPE
    SYNTAX     DateAndTime
    MAX-ACCESS read-only
    STATUS     current
    DESCRIPTION
        "Time of last reset of the Controller."
    ::= { msvmSyntheticDisplayControlEntry 40 }

msvmsydcTimeOfLastStateChange OBJECT-TYPE
    SYNTAX     DateAndTime
    MAX-ACCESS read-only
    STATUS     current
    DESCRIPTION
        "The date or time when the EnabledState of the
        element last changed. If the state of the element
        has not changed and this property is populated,
        then it must be set to a 0 interval value. If a
        state change was requested, but rejected or not yet
        processed, the property must not be updated."
    ::= { msvmSyntheticDisplayControlEntry 41 }

msvmsydcTotalPowerOnHours OBJECT-TYPE
    SYNTAX     Gauge32
    UNITS "Hours"
    MAX-ACCESS read-only
    STATUS     current
    DESCRIPTION
        "Note: The use of this method is deprecated. 
        Deprecated description: The total number of hours
        that this Device has been powered on."
    ::= { msvmSyntheticDisplayControlEntry 42 }

msvmsydcVideoMemoryType OBJECT-TYPE
    SYNTAX     INTEGER {
        unknown(0),
        other(1),
        vram(2),
        dram(3),
        sram(4),
        wram(5),
        edoRAM(6),
        burstSynchronousDRAM(7),
        pipelinedBurstSRAM(8),
        cdram(9),
        a3DRAM(10),
        sdram(11),
        sgram(12)
    }
    MAX-ACCESS read-only
    STATUS     current
    DESCRIPTION
        "An integer enumeration indicating the type of
        video memory."
    ::= { msvmSyntheticDisplayControlEntry 43 }

msvmsydcVideoProcessor OBJECT-TYPE
    SYNTAX     WtcsDisplayString
    MAX-ACCESS read-only
    STATUS     current
    DESCRIPTION
        "A free-form string describing the video
        processor/Controller."
    ::= { msvmSyntheticDisplayControlEntry 44 }

msvmSystemTerminalConnTable OBJECT-TYPE
    SYNTAX     SEQUENCE OF MsvmSystemTerminalConnection
    MAX-ACCESS not-accessible
    STATUS     current
    DESCRIPTION
        "Associates a virtual computer system with a
        terminal connection."
    ::= { msvmVideo 3 }

msvmSystemTerminalConnEntry OBJECT-TYPE
    SYNTAX     MsvmSystemTerminalConnection
    MAX-ACCESS not-accessible
    STATUS     current
    DESCRIPTION
        "None"
    INDEX      { msvmstcIndex }
    ::= { msvmSystemTerminalConnTable 1 }

MsvmSystemTerminalConnection ::= SEQUENCE {
    msvmstcIndex Integer32,
    msvmstcAntecedent WtcsDisplayString,
    msvmstcDependent WtcsDisplayString
}

msvmstcIndex OBJECT-TYPE
    SYNTAX     Integer32 (1..2147483647)
    MAX-ACCESS read-only
    STATUS     current
    DESCRIPTION
        "The value of this object uniquely identifies the
        instance entry for this class."
    ::= { msvmSystemTerminalConnEntry 1 }

msvmstcAntecedent OBJECT-TYPE
    SYNTAX     WtcsDisplayString
    MAX-ACCESS read-only
    STATUS     current
    DESCRIPTION
        "The scoping Virtual ComputerSystem."
    ::= { msvmSystemTerminalConnEntry 2 }

msvmstcDependent OBJECT-TYPE
    SYNTAX     WtcsDisplayString
    MAX-ACCESS read-only
    STATUS     current
    DESCRIPTION
        "The hosted TerminalConnection."
    ::= { msvmSystemTerminalConnEntry 3 }

msvmTerminalConnectionTable OBJECT-TYPE
    SYNTAX     SEQUENCE OF MsvmTerminalConnection
    MAX-ACCESS not-accessible
    STATUS     current
    DESCRIPTION
        "Indicates the state of an active remote session
        interacting with a virtual computer system."
    ::= { msvmVideo 4 }

msvmTerminalConnectionEntry OBJECT-TYPE
    SYNTAX     MsvmTerminalConnection
    MAX-ACCESS not-accessible
    STATUS     current
    DESCRIPTION
        "None"
    INDEX      { msvmtcIndex }
    ::= { msvmTerminalConnectionTable 1 }

MsvmTerminalConnection ::= SEQUENCE {
    msvmtcIndex Integer32,
    msvmtcCaption WtcsDisplayString,
    msvmtcConnectionID WtcsDisplayString,
    msvmtcDescription WtcsDisplayString,
    msvmtcElementName WtcsDisplayString,
    msvmtcEnabledDefault INTEGER,
    msvmtcEnabledState INTEGER,
    msvmtcHealthState INTEGER,
    msvmtcInstallDate DateAndTime,
    msvmtcName WtcsDisplayString,
    msvmtcOperationalStatus INTEGER,
    msvmtcOtherEnabledState WtcsDisplayString,
    msvmtcRequestedState INTEGER,
    msvmtcStatus WtcsDisplayString,
    msvmtcStatusDescriptions WtcsDisplayString,
    msvmtcTimeOfLastStateChange DateAndTime
}

msvmtcIndex OBJECT-TYPE
    SYNTAX     Integer32 (1..2147483647)
    MAX-ACCESS read-only
    STATUS     current
    DESCRIPTION
        "The value of this object uniquely identifies the
        instance entry for this class."
    ::= { msvmTerminalConnectionEntry 1 }

msvmtcCaption OBJECT-TYPE
    SYNTAX     WtcsDisplayString (SIZE (0..64))
    MAX-ACCESS read-only
    STATUS     current
    DESCRIPTION
        "The Caption property is a short textual
        description (one- line string) of the object."
    ::= { msvmTerminalConnectionEntry 2 }

msvmtcConnectionID OBJECT-TYPE
    SYNTAX     WtcsDisplayString
    MAX-ACCESS read-only
    STATUS     current
    DESCRIPTION
        "Unique identifier for an instance of the terminal
        connection object. The identifier is of the form
        'Microsoft:<VMID>\<Index>'. For example,
        'Microsoft:67A5D397-A02D-11DB-AC13-001676AA34F0\0'.
        "
    ::= { msvmTerminalConnectionEntry 3 }

msvmtcDescription OBJECT-TYPE
    SYNTAX     WtcsDisplayString
    MAX-ACCESS read-only
    STATUS     current
    DESCRIPTION
        "The Description property provides a textual
        description of the object."
    ::= { msvmTerminalConnectionEntry 4 }

msvmtcElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmTerminalConnectionEntry 5 }

msvmtcEnabledDefault OBJECT-TYPE
    SYNTAX     INTEGER {
        enabled(2),
        disabled(3),
        notApplicable(5),
        enabledbutOffline(6),
        noDefault(7)
    }
    MAX-ACCESS read-only
    STATUS     current
    DESCRIPTION
        "An enumerated value indicating an administrator's
        default or startup configuration for the Enabled
        State of an element. By default, the element is
        'Enabled' (value=2)."
    ::= { msvmTerminalConnectionEntry 6 }

msvmtcEnabledState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "EnabledState is an integer enumeration that
        indicates the enabled and disabled states of an
        element. It can also indicate the transitions
        between these requested states. For example,
        shutting down (value=4) and starting (value=10) are
        transient states between enabled and disabled. The
        following text briefly summarizes the various
        enabled and disabled states: 
        Enabled (2) indicates that the element is or could
        be executing commands, will process any queued
        commands, and queues new requests. 
        Disabled (3) indicates that the element will not
        execute commands and will drop any new requests. 
        Shutting Down (4) indicates that the element is in
        the process of going to a Disabled state. 
        Not Applicable (5) indicates the element does not
        support being enabled or disabled. 
        Enabled but Offline (6) indicates that the element
        might be completing commands, and will drop any new
        requests. 
        Test (7) indicates that the element is in a test
        state. 
        Deferred (8) indicates that the element might be
        completing commands, but will queue any new
        requests. 
        Quiesce (9) indicates that the element is enabled
        but in a restricted mode. The behavior of the
        element is similar to the Enabled state, but it
        processes only a restricted set of commands. All
        other requests are queued. 
        Starting (10) indicates that the element is in the
        process of going to an Enabled state. New requests
        are queued."
    ::= { msvmTerminalConnectionEntry 7 }

msvmtcHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmTerminalConnectionEntry 8 }

msvmtcInstallDate OBJECT-TYPE
    SYNTAX     DateAndTime
    MAX-ACCESS read-only
    STATUS     current
    DESCRIPTION
        "A datetime value that indicates when the object
        was installed. Lack of a value does not indicate
        that the object is not installed."
    ::= { msvmTerminalConnectionEntry 9 }

msvmtcName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmTerminalConnectionEntry 10 }

msvmtcOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmTerminalConnectionEntry 11 }

msvmtcOtherEnabledState OBJECT-TYPE
    SYNTAX     WtcsDisplayString
    MAX-ACCESS read-only
    STATUS     current
    DESCRIPTION
        "A string that describes the enabled or disabled
        state of the element when the EnabledState property
        is set to 1 ('Other'). This property must be set to
        null when EnabledState is any value other than 1."
    ::= { msvmTerminalConnectionEntry 12 }

msvmtcRequestedState OBJECT-TYPE
    SYNTAX     INTEGER {
        enabled(2),
        disabled(3),
        shutDown(4),
        noChange(5),
        offline(6),
        test(7),
        deferred(8),
        quiesce(9),
        reboot(10),
        reset(11),
        notApplicable(12)
    }
    MAX-ACCESS read-only
    STATUS     current
    DESCRIPTION
        "RequestedState is an integer enumeration that
        indicates the last requested or desired state for
        the element. The actual state of the element is
        represented by EnabledState. This property is
        provided to compare the last requested and current
        enabled or disabled states. Note that when
        EnabledState is set to 5 ('Not Applicable'), then
        this property has no meaning. By default, the
        RequestedState of the element is 5 ('No Change').
        Refer to the EnabledState property description for
        explanations of the values in the RequestedState
        enumeration. 
        
        It should be noted that there are two new values in
        RequestedState that build on the statuses of
        EnabledState. These are 'Reboot' (10) and 'Reset'
        (11). Reboot refers to doing a 'Shut Down' and then
        moving to an 'Enabled' state. Reset indicates that
        the element is first 'Disabled' and then 'Enabled'.
        The distinction between requesting 'Shut Down' and
        'Disabled' should also be noted. Shut Down requests
        an orderly transition to the Disabled state, and
        might involve removing power, to completely erase
        any existing state. The Disabled state requests an
        immediate disabling of the element, such that it
        will not execute or accept any commands or
        processing requests. 
        
        This property is set as the result of a method
        invocation (such as Start or StopService on
        CIM_Service), or can be overridden and defined as
        WRITEable in a subclass. The method approach is
        considered superior to a WRITEable property,
        because it allows an explicit invocation of the
        operation and the return of a result code. 
        
        A particular instance of EnabledLogicalElement
        might not support RequestedStateChange. If this
        occurs, the value 12 ('Not Applicable') is used."
    ::= { msvmTerminalConnectionEntry 13 }

msvmtcStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmTerminalConnectionEntry 14 }

msvmtcStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmTerminalConnectionEntry 15 }

msvmtcTimeOfLastStateChange OBJECT-TYPE
    SYNTAX     DateAndTime
    MAX-ACCESS read-only
    STATUS     current
    DESCRIPTION
        "The date or time when the EnabledState of the
        element last changed. If the state of the element
        has not changed and this property is populated,
        then it must be set to a 0 interval value. If a
        state change was requested, but rejected or not yet
        processed, the property must not be updated."
    ::= { msvmTerminalConnectionEntry 16 }

msvmTerminalServiceTable OBJECT-TYPE
    SYNTAX     SEQUENCE OF MsvmTerminalService
    MAX-ACCESS not-accessible
    STATUS     current
    DESCRIPTION
        "Manages all remote terminal connections to a
        particular host. The service uses a configurable
        port to initiate all terminal connections."
    ::= { msvmVideo 5 }

msvmTerminalServiceEntry OBJECT-TYPE
    SYNTAX     MsvmTerminalService
    MAX-ACCESS not-accessible
    STATUS     current
    DESCRIPTION
        "None"
    INDEX      { msvmtsIndex }
    ::= { msvmTerminalServiceTable 1 }

MsvmTerminalService ::= SEQUENCE {
    msvmtsIndex Integer32,
    msvmtsCaption WtcsDisplayString,
    msvmtsCreationClassName WtcsDisplayString,
    msvmtsDescription WtcsDisplayString,
    msvmtsElementName WtcsDisplayString,
    msvmtsEnabledDefault INTEGER,
    msvmtsEnabledState INTEGER,
    msvmtsHealthState INTEGER,
    msvmtsInstallDate DateAndTime,
    msvmtsListenerPort Gauge32,
    msvmtsName WtcsDisplayString,
    msvmtsOperationalStatus INTEGER,
    msvmtsOtherEnabledState WtcsDisplayString,
    msvmtsPrimaryOwnerContact WtcsDisplayString,
    msvmtsPrimaryOwnerName WtcsDisplayString,
    msvmtsRequestedState INTEGER,
    msvmtsStartMode WtcsDisplayString,
    msvmtsStarted TruthValue,
    msvmtsStatus WtcsDisplayString,
    msvmtsStatusDescriptions WtcsDisplayString,
    msvmtsSystemCreationClassName WtcsDisplayString,
    msvmtsSystemName WtcsDisplayString,
    msvmtsTimeOfLastStateChange DateAndTime
}

msvmtsIndex OBJECT-TYPE
    SYNTAX     Integer32 (1..2147483647)
    MAX-ACCESS read-only
    STATUS     current
    DESCRIPTION
        "The value of this object uniquely identifies the
        instance entry for this class."
    ::= { msvmTerminalServiceEntry 1 }

msvmtsCaption OBJECT-TYPE
    SYNTAX     WtcsDisplayString (SIZE (0..64))
    MAX-ACCESS read-only
    STATUS     current
    DESCRIPTION
        "The Caption property is a short textual
        description (one- line string) of the object."
    ::= { msvmTerminalServiceEntry 2 }

msvmtsCreationClassName OBJECT-TYPE
    SYNTAX     WtcsDisplayString (SIZE (0..256))
    MAX-ACCESS read-only
    STATUS     current
    DESCRIPTION
        "CreationClassName indicates the name of the class
        or the subclass that is used in the creation of an
        instance. When used with the other key properties
        of this class, this property allows all instances
        of this class and its subclasses to be uniquely
        identified."
    ::= { msvmTerminalServiceEntry 3 }

msvmtsDescription OBJECT-TYPE
    SYNTAX     WtcsDisplayString
    MAX-ACCESS read-only
    STATUS     current
    DESCRIPTION
        "The Description property provides a textual
        description of the object."
    ::= { msvmTerminalServiceEntry 4 }

msvmtsElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmTerminalServiceEntry 5 }

msvmtsEnabledDefault OBJECT-TYPE
    SYNTAX     INTEGER {
        enabled(2),
        disabled(3),
        notApplicable(5),
        enabledbutOffline(6),
        noDefault(7)
    }
    MAX-ACCESS read-only
    STATUS     current
    DESCRIPTION
        "An enumerated value indicating an administrator's
        default or startup configuration for the Enabled
        State of an element. By default, the element is
        'Enabled' (value=2)."
    ::= { msvmTerminalServiceEntry 6 }

msvmtsEnabledState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "EnabledState is an integer enumeration that
        indicates the enabled and disabled states of an
        element. It can also indicate the transitions
        between these requested states. For example,
        shutting down (value=4) and starting (value=10) are
        transient states between enabled and disabled. The
        following text briefly summarizes the various
        enabled and disabled states: 
        Enabled (2) indicates that the element is or could
        be executing commands, will process any queued
        commands, and queues new requests. 
        Disabled (3) indicates that the element will not
        execute commands and will drop any new requests. 
        Shutting Down (4) indicates that the element is in
        the process of going to a Disabled state. 
        Not Applicable (5) indicates the element does not
        support being enabled or disabled. 
        Enabled but Offline (6) indicates that the element
        might be completing commands, and will drop any new
        requests. 
        Test (7) indicates that the element is in a test
        state. 
        Deferred (8) indicates that the element might be
        completing commands, but will queue any new
        requests. 
        Quiesce (9) indicates that the element is enabled
        but in a restricted mode. The behavior of the
        element is similar to the Enabled state, but it
        processes only a restricted set of commands. All
        other requests are queued. 
        Starting (10) indicates that the element is in the
        process of going to an Enabled state. New requests
        are queued."
    ::= { msvmTerminalServiceEntry 7 }

msvmtsHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmTerminalServiceEntry 8 }

msvmtsInstallDate OBJECT-TYPE
    SYNTAX     DateAndTime
    MAX-ACCESS read-only
    STATUS     current
    DESCRIPTION
        "A datetime value that indicates when the object
        was installed. Lack of a value does not indicate
        that the object is not installed."
    ::= { msvmTerminalServiceEntry 9 }

msvmtsListenerPort OBJECT-TYPE
    SYNTAX     Gauge32
    MAX-ACCESS read-only
    STATUS     current
    DESCRIPTION
        "The network port on which the initial remote
        session connection will be made."
    ::= { msvmTerminalServiceEntry 10 }

msvmtsName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmTerminalServiceEntry 11 }

msvmtsOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmTerminalServiceEntry 12 }

msvmtsOtherEnabledState OBJECT-TYPE
    SYNTAX     WtcsDisplayString
    MAX-ACCESS read-only
    STATUS     current
    DESCRIPTION
        "A string that describes the enabled or disabled
        state of the element when the EnabledState property
        is set to 1 ('Other'). This property must be set to
        null when EnabledState is any value other than 1."
    ::= { msvmTerminalServiceEntry 13 }

msvmtsPrimaryOwnerContact OBJECT-TYPE
    SYNTAX     WtcsDisplayString (SIZE (0..256))
    MAX-ACCESS read-only
    STATUS     current
    DESCRIPTION
        "A string that provides information on how the
        primary owner of the Service can be reached (for
        example, phone number, e-mail address, and so on)."
    ::= { msvmTerminalServiceEntry 14 }

msvmtsPrimaryOwnerName OBJECT-TYPE
    SYNTAX     WtcsDisplayString (SIZE (0..64))
    MAX-ACCESS read-only
    STATUS     current
    DESCRIPTION
        "The name of the primary owner for the service, if
        one is defined. The primary owner is the initial
        support contact for the Service."
    ::= { msvmTerminalServiceEntry 15 }

msvmtsRequestedState OBJECT-TYPE
    SYNTAX     INTEGER {
        enabled(2),
        disabled(3),
        shutDown(4),
        noChange(5),
        offline(6),
        test(7),
        deferred(8),
        quiesce(9),
        reboot(10),
        reset(11),
        notApplicable(12)
    }
    MAX-ACCESS read-only
    STATUS     current
    DESCRIPTION
        "RequestedState is an integer enumeration that
        indicates the last requested or desired state for
        the element. The actual state of the element is
        represented by EnabledState. This property is
        provided to compare the last requested and current
        enabled or disabled states. Note that when
        EnabledState is set to 5 ('Not Applicable'), then
        this property has no meaning. By default, the
        RequestedState of the element is 5 ('No Change').
        Refer to the EnabledState property description for
        explanations of the values in the RequestedState
        enumeration. 
        
        It should be noted that there are two new values in
        RequestedState that build on the statuses of
        EnabledState. These are 'Reboot' (10) and 'Reset'
        (11). Reboot refers to doing a 'Shut Down' and then
        moving to an 'Enabled' state. Reset indicates that
        the element is first 'Disabled' and then 'Enabled'.
        The distinction between requesting 'Shut Down' and
        'Disabled' should also be noted. Shut Down requests
        an orderly transition to the Disabled state, and
        might involve removing power, to completely erase
        any existing state. The Disabled state requests an
        immediate disabling of the element, such that it
        will not execute or accept any commands or
        processing requests. 
        
        This property is set as the result of a method
        invocation (such as Start or StopService on
        CIM_Service), or can be overridden and defined as
        WRITEable in a subclass. The method approach is
        considered superior to a WRITEable property,
        because it allows an explicit invocation of the
        operation and the return of a result code. 
        
        A particular instance of EnabledLogicalElement
        might not support RequestedStateChange. If this
        occurs, the value 12 ('Not Applicable') is used."
    ::= { msvmTerminalServiceEntry 16 }

msvmtsStartMode OBJECT-TYPE
    SYNTAX     WtcsDisplayString (SIZE (0..10))
    MAX-ACCESS read-only
    STATUS     current
    DESCRIPTION
        "Note: The use of this element is deprecated in
        lieu of the EnabledDefault property that is
        inherited from EnabledLogicalElement. The
        EnabledLogicalElement addresses the same semantics.
        The change to a uint16 data type was discussed when
        CIM V2.0 was defined. However, existing V1.0
        implementations used the string property. To remain
        compatible with those implementations, StartMode
        was grandfathered into the schema. Use of the
        deprecated qualifier allows the maintenance of the
        existing property but also permits an improved,
        clarified definition using EnabledDefault. 
        Deprecated description: StartMode is a string value
        that indicates whether the Service is automatically
        started by a System, an Operating System, and so
        on, or is started only upon request."
    ::= { msvmTerminalServiceEntry 17 }

msvmtsStarted OBJECT-TYPE
    SYNTAX     TruthValue
    MAX-ACCESS read-only
    STATUS     current
    DESCRIPTION
        "Started is a Boolean that indicates whether the
        Service has been started (TRUE), or stopped
        (FALSE)."
    ::= { msvmTerminalServiceEntry 18 }

msvmtsStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmTerminalServiceEntry 19 }

msvmtsStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmTerminalServiceEntry 20 }

msvmtsSystemCreationClassName OBJECT-TYPE
    SYNTAX     WtcsDisplayString (SIZE (0..256))
    MAX-ACCESS read-only
    STATUS     current
    DESCRIPTION
        "The CreationClassName of the scoping System."
    ::= { msvmTerminalServiceEntry 21 }

msvmtsSystemName OBJECT-TYPE
    SYNTAX     WtcsDisplayString (SIZE (0..256))
    MAX-ACCESS read-only
    STATUS     current
    DESCRIPTION
        "The Name of the scoping System."
    ::= { msvmTerminalServiceEntry 22 }

msvmtsTimeOfLastStateChange OBJECT-TYPE
    SYNTAX     DateAndTime
    MAX-ACCESS read-only
    STATUS     current
    DESCRIPTION
        "The date or time when the EnabledState of the
        element last changed. If the state of the element
        has not changed and this property is populated,
        then it must be set to a 0 interval value. If a
        state change was requested, but rejected or not yet
        processed, the property must not be updated."
    ::= { msvmTerminalServiceEntry 23 }

msvmVideoHeadTable OBJECT-TYPE
    SYNTAX     SEQUENCE OF MsvmVideoHead
    MAX-ACCESS not-accessible
    STATUS     current
    DESCRIPTION
        "Describes the primary drawing surface on a display
        controller."
    ::= { msvmVideo 6 }

msvmVideoHeadEntry OBJECT-TYPE
    SYNTAX     MsvmVideoHead
    MAX-ACCESS not-accessible
    STATUS     current
    DESCRIPTION
        "None"
    INDEX      { msvmvhIndex }
    ::= { msvmVideoHeadTable 1 }

MsvmVideoHead ::= SEQUENCE {
    msvmvhIndex Integer32,
    msvmvhAdditionalAvailability INTEGER,
    msvmvhAvailability INTEGER,
    msvmvhCaption WtcsDisplayString,
    msvmvhCreationClassName WtcsDisplayString,
    msvmvhCurrentBitsPerPixel Gauge32,
    msvmvhCurHorizontalResolution Gauge32,
    msvmvhCurrentNumberOfColors Gauge32,
    msvmvhCurrentNumberOfColumns Gauge32,
    msvmvhCurrentNumberOfRows Gauge32,
    msvmvhCurrentRefreshRate Gauge32,
    msvmvhCurrentScanMode INTEGER,
    msvmvhCurrentVerticalResolution Gauge32,
    msvmvhDescription WtcsDisplayString,
    msvmvhDeviceID WtcsDisplayString,
    msvmvhElementName WtcsDisplayString,
    msvmvhEnabledDefault INTEGER,
    msvmvhEnabledState INTEGER,
    msvmvhErrorCleared TruthValue,
    msvmvhErrorDescription WtcsDisplayString,
    msvmvhHealthState INTEGER,
    msvmvhIdentifyingDescriptions WtcsDisplayString,
    msvmvhInstallDate DateAndTime,
    msvmvhLastErrorCode Gauge32,
    msvmvhLocationIndicator INTEGER,
    msvmvhMaxQuiesceTime Gauge32,
    msvmvhMaxRefreshRate Gauge32,
    msvmvhMinRefreshRate Gauge32,
    msvmvhName WtcsDisplayString,
    msvmvhOperationalStatus INTEGER,
    msvmvhOtherCurrentScanMode WtcsDisplayString,
    msvmvhOtherEnabledState WtcsDisplayString,
    msvmvhOtherIdentifyingInfo WtcsDisplayString,
    msvmvhPowerManagementCapability INTEGER,
    msvmvhPowerManagementSupported TruthValue,
    msvmvhPowerOnHours Gauge32,
    msvmvhRequestedState INTEGER,
    msvmvhStatus WtcsDisplayString,
    msvmvhStatusDescriptions WtcsDisplayString,
    msvmvhStatusInfo INTEGER,
    msvmvhSystemCreationClassName WtcsDisplayString,
    msvmvhSystemName WtcsDisplayString,
    msvmvhTimeOfLastStateChange DateAndTime,
    msvmvhTotalPowerOnHours Gauge32
}

msvmvhIndex OBJECT-TYPE
    SYNTAX     Integer32 (1..2147483647)
    MAX-ACCESS read-only
    STATUS     current
    DESCRIPTION
        "The value of this object uniquely identifies the
        instance entry for this class."
    ::= { msvmVideoHeadEntry 1 }

msvmvhAdditionalAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Additional availability and status of the Device
        in addition to that specified in the Availability
        property. The Availability property denotes the
        primary status and availability of the Device. In
        some cases, this property will not be sufficient to
        denote the complete status of the Device. In those
        cases, the AdditionalAvailability property can be
        used to provide further information. For example,
        the primary Availability of a device might be 'Off
        line' (value=8) or in a low-power state
        (AdditionalAvailability value=14), or the Device
        could be running Diagnostics
        (AdditionalAvailability value=5, 'In Test')."
    ::= { msvmVideoHeadEntry 2 }

msvmvhAvailability OBJECT-TYPE
    SYNTAX     INTEGER {
        other(1),
        unknown(2),
        runningFullPower(3),
        warning(4),
        inTest(5),
        notApplicable(6),
        powerOff(7),
        offLine(8),
        offDuty(9),
        degraded(10),
        notInstalled(11),
        installError(12),
        powerSaveUnknown(13),
        powerSaveLowPowerMode(14),
        powerSaveStandby(15),
        powerCycle(16),
        powerSaveWarning(17),
        paused(18),
        notReady(19),
        notConfigured(20),
        quiesced(21)
    }
    MAX-ACCESS read-only
    STATUS     current
    DESCRIPTION
        "Note: The use of this property has been
        deprecated. 
        Deprecated description: The primary availability
        and status of the Device. (Additional status
        information can be specified using the Additional
        Availability array property.) For example, the
        Availability property indicates that the Device is
        running and has full power (value=3), or is in a
        warning (4), test (5), degraded (10) or power save
        state (values 13-15 and 17). The Power Save states
        are defined as follows: Value 13 ('Power Save -
        Unknown') indicates that the Device is known to be
        in a power save mode, but its exact status in this
        mode is unknown; value 14 ('Power Save - Low Power
        Mode') indicates that the Device is in a power save
        state but still functioning, and might exhibit
        degraded performance; value 15 ('Power Save -
        Standby') indicates that the Device is not
        functioning but could be brought to full power
        'quickly'; and value 17 ('Power Save - Warning')
        indicates that the Device is in a warning state,
        but is also in a power save mode."
    ::= { msvmVideoHeadEntry 3 }

msvmvhCaption OBJECT-TYPE
    SYNTAX     WtcsDisplayString (SIZE (0..64))
    MAX-ACCESS read-only
    STATUS     current
    DESCRIPTION
        "The Caption property is a short textual
        description (one- line string) of the object."
    ::= { msvmVideoHeadEntry 4 }

msvmvhCreationClassName OBJECT-TYPE
    SYNTAX     WtcsDisplayString (SIZE (0..256))
    MAX-ACCESS read-only
    STATUS     current
    DESCRIPTION
        "CreationClassName indicates the name of the class
        or the subclass used in the creation of an
        instance. When used with the other key properties
        of this class, this property allows all instances
        of this class and its subclasses to be uniquely
        identified."
    ::= { msvmVideoHeadEntry 5 }

msvmvhCurrentBitsPerPixel OBJECT-TYPE
    SYNTAX     Gauge32
    UNITS "Bits"
    MAX-ACCESS read-only
    STATUS     current
    DESCRIPTION
        "The number of bits used to display each pixel."
    ::= { msvmVideoHeadEntry 6 }

msvmvhCurHorizontalResolution OBJECT-TYPE
    SYNTAX     Gauge32
    UNITS "Pixels"
    MAX-ACCESS read-only
    STATUS     current
    DESCRIPTION
        "Current number of horizontal pixels."
    ::= { msvmVideoHeadEntry 7 }

msvmvhCurrentNumberOfColors OBJECT-TYPE
    SYNTAX     Gauge32
    MAX-ACCESS read-only
    STATUS     current
    DESCRIPTION
        "Number of colors supported at the current
        resolutions."
    ::= { msvmVideoHeadEntry 8 }

msvmvhCurrentNumberOfColumns OBJECT-TYPE
    SYNTAX     Gauge32
    MAX-ACCESS read-only
    STATUS     current
    DESCRIPTION
        "If in character mode, number of columns for this
        DisplayController. Otherwise, enter 0."
    ::= { msvmVideoHeadEntry 9 }

msvmvhCurrentNumberOfRows OBJECT-TYPE
    SYNTAX     Gauge32
    MAX-ACCESS read-only
    STATUS     current
    DESCRIPTION
        "If in character mode, number of rows for this
        Video Controller. Otherwise, enter 0."
    ::= { msvmVideoHeadEntry 10 }

msvmvhCurrentRefreshRate OBJECT-TYPE
    SYNTAX     Gauge32
    UNITS "Hertz"
    MAX-ACCESS read-only
    STATUS     current
    DESCRIPTION
        "Current refresh rate in Hertz."
    ::= { msvmVideoHeadEntry 11 }

msvmvhCurrentScanMode OBJECT-TYPE
    SYNTAX     INTEGER {
        unknown(0),
        other(1),
        notSupported(2),
        nonInterlacedOperation(3),
        interlacedOperation(4)
    }
    MAX-ACCESS read-only
    STATUS     current
    DESCRIPTION
        "Current scan mode."
    ::= { msvmVideoHeadEntry 12 }

msvmvhCurrentVerticalResolution OBJECT-TYPE
    SYNTAX     Gauge32
    UNITS "Pixels"
    MAX-ACCESS read-only
    STATUS     current
    DESCRIPTION
        "Current number of vertical pixels."
    ::= { msvmVideoHeadEntry 13 }

msvmvhDescription OBJECT-TYPE
    SYNTAX     WtcsDisplayString
    MAX-ACCESS read-only
    STATUS     current
    DESCRIPTION
        "The Description property provides a textual
        description of the object."
    ::= { msvmVideoHeadEntry 14 }

msvmvhDeviceID OBJECT-TYPE
    SYNTAX     WtcsDisplayString (SIZE (0..64))
    MAX-ACCESS read-only
    STATUS     current
    DESCRIPTION
        "An address or other identifying information used
        to uniquely name the LogicalDevice."
    ::= { msvmVideoHeadEntry 15 }

msvmvhElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmVideoHeadEntry 16 }

msvmvhEnabledDefault OBJECT-TYPE
    SYNTAX     INTEGER {
        enabled(2),
        disabled(3),
        notApplicable(5),
        enabledbutOffline(6),
        noDefault(7)
    }
    MAX-ACCESS read-only
    STATUS     current
    DESCRIPTION
        "An enumerated value indicating an administrator's
        default or startup configuration for the Enabled
        State of an element. By default, the element is
        'Enabled' (value=2)."
    ::= { msvmVideoHeadEntry 17 }

msvmvhEnabledState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "EnabledState is an integer enumeration that
        indicates the enabled and disabled states of an
        element. It can also indicate the transitions
        between these requested states. For example,
        shutting down (value=4) and starting (value=10) are
        transient states between enabled and disabled. The
        following text briefly summarizes the various
        enabled and disabled states: 
        Enabled (2) indicates that the element is or could
        be executing commands, will process any queued
        commands, and queues new requests. 
        Disabled (3) indicates that the element will not
        execute commands and will drop any new requests. 
        Shutting Down (4) indicates that the element is in
        the process of going to a Disabled state. 
        Not Applicable (5) indicates the element does not
        support being enabled or disabled. 
        Enabled but Offline (6) indicates that the element
        might be completing commands, and will drop any new
        requests. 
        Test (7) indicates that the element is in a test
        state. 
        Deferred (8) indicates that the element might be
        completing commands, but will queue any new
        requests. 
        Quiesce (9) indicates that the element is enabled
        but in a restricted mode. The behavior of the
        element is similar to the Enabled state, but it
        processes only a restricted set of commands. All
        other requests are queued. 
        Starting (10) indicates that the element is in the
        process of going to an Enabled state. New requests
        are queued."
    ::= { msvmVideoHeadEntry 18 }

msvmvhErrorCleared OBJECT-TYPE
    SYNTAX     TruthValue
    MAX-ACCESS read-only
    STATUS     current
    DESCRIPTION
        "Note: The use of this method is deprecated. 
        Deprecated description: ErrorCleared is a Boolean
        property that indicates that the error reported in
        LastErrorCode is now cleared."
    ::= { msvmVideoHeadEntry 19 }

msvmvhErrorDescription OBJECT-TYPE
    SYNTAX     WtcsDisplayString
    MAX-ACCESS read-only
    STATUS     current
    DESCRIPTION
        "Note: The use of this method is deprecated. 
        Deprecated description: ErrorDescription is a
        free-form string that supplies more information
        about the error recorded in LastErrorCode and
        information on any corrective actions that can be
        taken."
    ::= { msvmVideoHeadEntry 20 }

msvmvhHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmVideoHeadEntry 21 }

msvmvhIdentifyingDescriptions OBJECT-TYPE
    SYNTAX     WtcsDisplayString
    MAX-ACCESS read-only
    STATUS     current
    DESCRIPTION
        "An array of free-form strings providing
        explanations and details behind the entries in the
        OtherIdentifyingInfo array. Note that each entry of
        this array is related to the entry in
        OtherIdentifyingInfo that is located at the same
        index."
    ::= { msvmVideoHeadEntry 22 }

msvmvhInstallDate OBJECT-TYPE
    SYNTAX     DateAndTime
    MAX-ACCESS read-only
    STATUS     current
    DESCRIPTION
        "A datetime value that indicates when the object
        was installed. Lack of a value does not indicate
        that the object is not installed."
    ::= { msvmVideoHeadEntry 23 }

msvmvhLastErrorCode OBJECT-TYPE
    SYNTAX     Gauge32
    MAX-ACCESS read-only
    STATUS     current
    DESCRIPTION
        "Note: The use of this method is deprecated. 
        Deprecated description: LastErrorCode captures the
        last error code reported by the LogicalDevice."
    ::= { msvmVideoHeadEntry 24 }

msvmvhLocationIndicator OBJECT-TYPE
    SYNTAX     INTEGER {
        unknown(0),
        on(2),
        off(3),
        notSupported(4)
    }
    MAX-ACCESS read-only
    STATUS     current
    DESCRIPTION
        "An integer that reflects the state of an indicator
        (e.g., LED) that is part of a device. Reading the
        value gives the current state. Writing the value
        with 'On'/'Off' turns the indicator on/off, other
        values may not be written."
    ::= { msvmVideoHeadEntry 25 }

msvmvhMaxQuiesceTime OBJECT-TYPE
    SYNTAX     Gauge32
    UNITS "MilliSeconds"
    MAX-ACCESS read-only
    STATUS     current
    DESCRIPTION
        "Note: The use of this property has been
        deprecated. When evaluating the use of Quiesce, it
        was determined that this single property is not
        adequate for describing when a device will
        automatically exit a quiescent state. In fact, the
        most likely scenario for a device to exit a
        quiescent state was determined to be based on the
        number of outstanding requests queued rather than
        on a maximum time. This decision will be
        re-evaluated and repositioned later. 
        Deprecated description: Maximum time, in
        milliseconds, that a Device can run in a 'Quiesced'
        state. The state is defined in its Availability and
        AdditionalAvailability properties, where 'Quiesced'
        is conveyed by the value 21. What occurs at the end
        of the time limit is device-specific. The Device
        can unquiesce, can be offline, or can take other
        actions. A value of 0 indicates that a Device can
        remain quiesced indefinitely."
    ::= { msvmVideoHeadEntry 26 }

msvmvhMaxRefreshRate OBJECT-TYPE
    SYNTAX     Gauge32
    UNITS "Hertz"
    MAX-ACCESS read-only
    STATUS     current
    DESCRIPTION
        "Maximum refresh rate of the DisplayController in
        Hertz."
    ::= { msvmVideoHeadEntry 27 }

msvmvhMinRefreshRate OBJECT-TYPE
    SYNTAX     Gauge32
    UNITS "Hertz"
    MAX-ACCESS read-only
    STATUS     current
    DESCRIPTION
        "Minimum refresh rate of the Video Controller in
        Hertz."
    ::= { msvmVideoHeadEntry 28 }

msvmvhName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmVideoHeadEntry 29 }

msvmvhOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmVideoHeadEntry 30 }

msvmvhOtherCurrentScanMode OBJECT-TYPE
    SYNTAX     WtcsDisplayString
    MAX-ACCESS read-only
    STATUS     current
    DESCRIPTION
        "A string describing the current scan mode when the
        instance's CurrentScanMode property is 1
        ('Other')."
    ::= { msvmVideoHeadEntry 31 }

msvmvhOtherEnabledState OBJECT-TYPE
    SYNTAX     WtcsDisplayString
    MAX-ACCESS read-only
    STATUS     current
    DESCRIPTION
        "A string that describes the enabled or disabled
        state of the element when the EnabledState property
        is set to 1 ('Other'). This property must be set to
        null when EnabledState is any value other than 1."
    ::= { msvmVideoHeadEntry 32 }

msvmvhOtherIdentifyingInfo OBJECT-TYPE
    SYNTAX     WtcsDisplayString (SIZE (0..256))
    MAX-ACCESS read-only
    STATUS     current
    DESCRIPTION
        "OtherIdentifyingInfo captures data, in addition to
        DeviceID information, that could be used to
        identify a LogicalDevice. For example, you could
        use this property to hold the operating system's
        user-friendly name for the Device."
    ::= { msvmVideoHeadEntry 33 }

msvmvhPowerManagementCapability OBJECT-TYPE
    SYNTAX     INTEGER {
        unknown(0),
        notSupported(1),
        disabled(2),
        enabled(3),
        powerSavingModesEnteredAutomatic(4),
        powerStateSettable(5),
        powerCyclingSupported(6),
        timedPowerOnSupported(7)
    }
    MAX-ACCESS read-only
    STATUS     current
    DESCRIPTION
        "Note: The use of this property has been
        deprecated. Instead, use the PowerCapabilites
        property in an associated
        PowerManagementCapabilities class. Deprecated
        description: An enumerated array describing the
        power management capabilities of the Device."
    ::= { msvmVideoHeadEntry 34 }

msvmvhPowerManagementSupported OBJECT-TYPE
    SYNTAX     TruthValue
    MAX-ACCESS read-only
    STATUS     current
    DESCRIPTION
        "Note: The use of this property has been
        deprecated. Instead, the existence of an associated
        PowerManagementCapabilities class (associated using
        the ElementCapabilities relationship) indicates
        that power management is supported. Deprecated
        description: Boolean that indicates that the Device
        can use power management."
    ::= { msvmVideoHeadEntry 35 }

msvmvhPowerOnHours OBJECT-TYPE
    SYNTAX     Gauge32
    UNITS "Hours"
    MAX-ACCESS read-only
    STATUS     current
    DESCRIPTION
        "Note: The use of this method is deprecated. 
        Deprecated description: The number of consecutive
        hours that this Device has been powered on since
        its last power cycle."
    ::= { msvmVideoHeadEntry 36 }

msvmvhRequestedState OBJECT-TYPE
    SYNTAX     INTEGER {
        enabled(2),
        disabled(3),
        shutDown(4),
        noChange(5),
        offline(6),
        test(7),
        deferred(8),
        quiesce(9),
        reboot(10),
        reset(11),
        notApplicable(12)
    }
    MAX-ACCESS read-only
    STATUS     current
    DESCRIPTION
        "RequestedState is an integer enumeration that
        indicates the last requested or desired state for
        the element. The actual state of the element is
        represented by EnabledState. This property is
        provided to compare the last requested and current
        enabled or disabled states. Note that when
        EnabledState is set to 5 ('Not Applicable'), then
        this property has no meaning. By default, the
        RequestedState of the element is 5 ('No Change').
        Refer to the EnabledState property description for
        explanations of the values in the RequestedState
        enumeration. 
        
        It should be noted that there are two new values in
        RequestedState that build on the statuses of
        EnabledState. These are 'Reboot' (10) and 'Reset'
        (11). Reboot refers to doing a 'Shut Down' and then
        moving to an 'Enabled' state. Reset indicates that
        the element is first 'Disabled' and then 'Enabled'.
        The distinction between requesting 'Shut Down' and
        'Disabled' should also be noted. Shut Down requests
        an orderly transition to the Disabled state, and
        might involve removing power, to completely erase
        any existing state. The Disabled state requests an
        immediate disabling of the element, such that it
        will not execute or accept any commands or
        processing requests. 
        
        This property is set as the result of a method
        invocation (such as Start or StopService on
        CIM_Service), or can be overridden and defined as
        WRITEable in a subclass. The method approach is
        considered superior to a WRITEable property,
        because it allows an explicit invocation of the
        operation and the return of a result code. 
        
        A particular instance of EnabledLogicalElement
        might not support RequestedStateChange. If this
        occurs, the value 12 ('Not Applicable') is used."
    ::= { msvmVideoHeadEntry 37 }

msvmvhStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmVideoHeadEntry 38 }

msvmvhStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmVideoHeadEntry 39 }

msvmvhStatusInfo OBJECT-TYPE
    SYNTAX     INTEGER {
        other(1),
        unknown(2),
        enabled(3),
        disabled(4),
        notApplicable(5)
    }
    MAX-ACCESS read-only
    STATUS     current
    DESCRIPTION
        "Note: The use of this method is deprecated in lieu
        of a more clearly named property (EnabledState)
        that is inherited from ManagedSystemElement and
        that has additional enumerated values. 
        Deprecated description: The StatusInfo property
        indicates whether the Logical Device is in an
        enabled state (value=3), disabled state (value=4),
        some other state (value=1), or an unknown state
        (value=2). If this property does not apply to the
        LogicalDevice, the value 5 ('Not Applicable')
        should be used. If a Device is
        ('Enabled')(value=3), it has been powered up and is
        configured and operational. The Device might or
        might not be functionally active, depending on
        whether its Availability (or
        AdditionalAvailability) indicates that it is
        ('Running/Full Power')(value=3) or ('Off line')
        (value=8). In an enabled but offline mode, a Device
        might be performing out-of-band requests, such as
        running Diagnostics. If StatusInfo is ('Disabled')
        (value=4), a Device can only be 'enabled' or
        powered off. In a personal computer environment,
        ('Disabled') means that the driver of the device is
        not available in the stack. In other environments,
        a Device can be disabled by removing its
        configuration file. A disabled device is physically
        present in a System and consuming resources, but it
        cannot be communicated with until a driver is
        loaded, a configuration file is loaded, or some
        other 'enabling' activity has occurred."
    ::= { msvmVideoHeadEntry 40 }

msvmvhSystemCreationClassName OBJECT-TYPE
    SYNTAX     WtcsDisplayString (SIZE (0..256))
    MAX-ACCESS read-only
    STATUS     current
    DESCRIPTION
        "The CreationClassName of the scoping system."
    ::= { msvmVideoHeadEntry 41 }

msvmvhSystemName OBJECT-TYPE
    SYNTAX     WtcsDisplayString (SIZE (0..256))
    MAX-ACCESS read-only
    STATUS     current
    DESCRIPTION
        "The System Name of the scoping system."
    ::= { msvmVideoHeadEntry 42 }

msvmvhTimeOfLastStateChange OBJECT-TYPE
    SYNTAX     DateAndTime
    MAX-ACCESS read-only
    STATUS     current
    DESCRIPTION
        "The date or time when the EnabledState of the
        element last changed. If the state of the element
        has not changed and this property is populated,
        then it must be set to a 0 interval value. If a
        state change was requested, but rejected or not yet
        processed, the property must not be updated."
    ::= { msvmVideoHeadEntry 43 }

msvmvhTotalPowerOnHours OBJECT-TYPE
    SYNTAX     Gauge32
    UNITS "Hours"
    MAX-ACCESS read-only
    STATUS     current
    DESCRIPTION
        "Note: The use of this method is deprecated. 
        Deprecated description: The total number of hours
        that this Device has been powered on."
    ::= { msvmVideoHeadEntry 44 }

msvmVideoHeadOnControllerTable OBJECT-TYPE
    SYNTAX     SEQUENCE OF MsvmVideoHeadOnController
    MAX-ACCESS not-accessible
    STATUS     current
    DESCRIPTION
        "Associates a video head with the video controller
        that includes it."
    ::= { msvmVideo 7 }

msvmVideoHeadOnControllerEntry OBJECT-TYPE
    SYNTAX     MsvmVideoHeadOnController
    MAX-ACCESS not-accessible
    STATUS     current
    DESCRIPTION
        "None"
    INDEX      { msvmvhocIndex }
    ::= { msvmVideoHeadOnControllerTable 1 }

MsvmVideoHeadOnController ::= SEQUENCE {
    msvmvhocIndex Integer32,
    msvmvhocAntecedent WtcsDisplayString,
    msvmvhocDependent WtcsDisplayString
}

msvmvhocIndex OBJECT-TYPE
    SYNTAX     Integer32 (1..2147483647)
    MAX-ACCESS read-only
    STATUS     current
    DESCRIPTION
        "The value of this object uniquely identifies the
        instance entry for this class."
    ::= { msvmVideoHeadOnControllerEntry 1 }

msvmvhocAntecedent OBJECT-TYPE
    SYNTAX     WtcsDisplayString
    MAX-ACCESS read-only
    STATUS     current
    DESCRIPTION
        "The video controller that includes the head."
    ::= { msvmVideoHeadOnControllerEntry 2 }

msvmvhocDependent OBJECT-TYPE
    SYNTAX     WtcsDisplayString
    MAX-ACCESS read-only
    STATUS     current
    DESCRIPTION
        "The head on the video device."
    ::= { msvmVideoHeadOnControllerEntry 3 }

msvmVirtualSystem OBJECT-IDENTITY
    STATUS     current
    DESCRIPTION
        "The following are virtualization WMI classes
        related to the virtual system."
    ::= { informantHyperV 12 }

msvmComputerSystemTable OBJECT-TYPE
    SYNTAX     SEQUENCE OF MsvmComputerSystem
    MAX-ACCESS not-accessible
    STATUS     current
    DESCRIPTION
        "Represents a hosting computer system or virtual
        computer system."
    ::= { msvmVirtualSystem 1 }

msvmComputerSystemEntry OBJECT-TYPE
    SYNTAX     MsvmComputerSystem
    MAX-ACCESS not-accessible
    STATUS     current
    DESCRIPTION
        "None"
    INDEX      { msvmcsIndex }
    ::= { msvmComputerSystemTable 1 }

MsvmComputerSystem ::= SEQUENCE {
    msvmcsIndex Integer32,
    msvmcsAssignedNumaNodeList Integer32,
    msvmcsCaption WtcsDisplayString,
    msvmcsCreationClassName WtcsDisplayString,
    msvmcsDedicated INTEGER,
    msvmcsDescription WtcsDisplayString,
    msvmcsElementName WtcsDisplayString,
    msvmcsEnabledDefault INTEGER,
    msvmcsEnabledState INTEGER,
    msvmcsHealthState INTEGER,
    msvmcsIdentifyingDescriptions WtcsDisplayString,
    msvmcsInstallDate DateAndTime,
    msvmcsName WtcsDisplayString,
    msvmcsNameFormat WtcsDisplayString,
    msvmcsOnTimeInMilliseconds Gauge32,
    msvmcsOperationalStatus INTEGER,
    msvmcsOtherDedicatedDescriptions INTEGER,
    msvmcsOtherEnabledState INTEGER,
    msvmcsOtherIdentifyingInfo WtcsDisplayString,
    msvmcsPowerManagementCapability INTEGER,
    msvmcsPrimaryOwnerContact WtcsDisplayString,
    msvmcsPrimaryOwnerName WtcsDisplayString,
    msvmcsProcessID Gauge32,
    msvmcsRequestedState INTEGER,
    msvmcsResetCapability INTEGER,
    msvmcsRoles WtcsDisplayString,
    msvmcsStatus WtcsDisplayString,
    msvmcsStatusDescriptions WtcsDisplayString,
    msvmcsTimeOfLastConfigChange DateAndTime,
    msvmcsTimeOfLastStateChange DateAndTime
}

msvmcsIndex OBJECT-TYPE
    SYNTAX     Integer32 (1..2147483647)
    MAX-ACCESS read-only
    STATUS     current
    DESCRIPTION
        "The value of this object uniquely identifies the
        instance entry for this class."
    ::= { msvmComputerSystemEntry 1 }

msvmcsAssignedNumaNodeList OBJECT-TYPE
    SYNTAX     Integer32
    MAX-ACCESS read-only
    STATUS     current
    DESCRIPTION
        "None"
    ::= { msvmComputerSystemEntry 2 }

msvmcsCaption OBJECT-TYPE
    SYNTAX     WtcsDisplayString (SIZE (0..64))
    MAX-ACCESS read-only
    STATUS     current
    DESCRIPTION
        "The Caption property is a short textual
        description (one- line string) of the object."
    ::= { msvmComputerSystemEntry 3 }

msvmcsCreationClassName OBJECT-TYPE
    SYNTAX     WtcsDisplayString (SIZE (0..256))
    MAX-ACCESS read-only
    STATUS     current
    DESCRIPTION
        "CreationClassName indicates the name of the class
        or the subclass used in the creation of an
        instance. When used with the other key properties
        of this class, this property allows all instances
        of this class and its subclasses to be uniquely
        identified."
    ::= { msvmComputerSystemEntry 4 }

msvmcsDedicated OBJECT-TYPE
    SYNTAX     INTEGER {
        notDedicated(0),
        unknown(1),
        other(2),
        storage(3),
        router(4),
        switch(5),
        layer3Switch(6),
        centralOfficeSwitch(7),
        hub(8),
        accessServer(9),
        firewall(10),
        print(11),
        iO(12),
        webCaching(13),
        management(14),
        blockServer(15),
        fileServer(16),
        mobileUserDevice(17),
        repeater(18),
        bridgeExtender(19),
        gateway(20),
        storageVirtualizer(21),
        mediaLibrary(22),
        extenderNode(23),
        nasHead(24),
        selfcontainedNAS(25),
        ups(26),
        ipPhone(27),
        managementController(28),
        chassisManager(29)
    }
    MAX-ACCESS read-only
    STATUS     current
    DESCRIPTION
        "A string describing how or why the system is
        dedicated when the Dedicated array includes the
        value 2, 'Other'."
    ::= { msvmComputerSystemEntry 5 }

msvmcsDescription OBJECT-TYPE
    SYNTAX     WtcsDisplayString
    MAX-ACCESS read-only
    STATUS     current
    DESCRIPTION
        "The Description property provides a textual
        description of the object."
    ::= { msvmComputerSystemEntry 6 }

msvmcsElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmComputerSystemEntry 7 }

msvmcsEnabledDefault OBJECT-TYPE
    SYNTAX     INTEGER {
        enabled(2),
        disabled(3),
        notApplicable(5),
        enabledbutOffline(6),
        noDefault(7)
    }
    MAX-ACCESS read-only
    STATUS     current
    DESCRIPTION
        "An enumerated value indicating an administrator's
        default or startup configuration for the Enabled
        State of an element. By default, the element is
        'Enabled' (value=2)."
    ::= { msvmComputerSystemEntry 8 }

msvmcsEnabledState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "A string that describes the enabled or disabled
        state of the element when the EnabledState property
        is set to 1 ('Other'). This property must be set to
        null when EnabledState is any value other than 1."
    ::= { msvmComputerSystemEntry 9 }

msvmcsHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmComputerSystemEntry 10 }

msvmcsIdentifyingDescriptions OBJECT-TYPE
    SYNTAX     WtcsDisplayString
    MAX-ACCESS read-only
    STATUS     current
    DESCRIPTION
        "OtherIdentifyingInfo captures additional data,
        beyond System Name information, that could be used
        to identify a ComputerSystem. One example would be
        to hold the Fibre Channel World-Wide Name (WWN) of
        a node. Note that if only the Fibre Channel name is
        available and is unique (able to be used as the
        System key), then this property would be NULL and
        the WWN would become the System key, its data
        placed in the Name property."
    ::= { msvmComputerSystemEntry 11 }

msvmcsInstallDate OBJECT-TYPE
    SYNTAX     DateAndTime
    MAX-ACCESS read-only
    STATUS     current
    DESCRIPTION
        "A datetime value that indicates when the object
        was installed. Lack of a value does not indicate
        that the object is not installed."
    ::= { msvmComputerSystemEntry 12 }

msvmcsName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmComputerSystemEntry 13 }

msvmcsNameFormat OBJECT-TYPE
    SYNTAX     WtcsDisplayString (SIZE (0..64))
    MAX-ACCESS read-only
    STATUS     current
    DESCRIPTION
        "The System object and its derivatives are
        top-level objects of CIM. They provide the scope
        for numerous components. Having unique System keys
        is required. A heuristic can be defined in
        individual System subclasses to attempt to always
        generate the same System Name Key. The NameFormat
        property identifies how the System name was
        generated, using the heuristic of the subclass."
    ::= { msvmComputerSystemEntry 14 }

msvmcsOnTimeInMilliseconds OBJECT-TYPE
    SYNTAX     Gauge32
    MAX-ACCESS read-only
    STATUS     current
    DESCRIPTION
        "For the virtual system, this property describes
        the total up time, in milliseconds, since the
        machine was last turned on, reset, or restored.
        This time excludes the time the virtual system was
        in the paused state. For the host system, this
        property is set to NULL."
    ::= { msvmComputerSystemEntry 15 }

msvmcsOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmComputerSystemEntry 16 }

msvmcsOtherDedicatedDescriptions OBJECT-TYPE
    SYNTAX     INTEGER {
        notDedicated(0),
        unknown(1),
        other(2),
        storage(3),
        router(4),
        switch(5),
        layer3Switch(6),
        centralOfficeSwitch(7),
        hub(8),
        accessServer(9),
        firewall(10),
        print(11),
        iO(12),
        webCaching(13),
        management(14),
        blockServer(15),
        fileServer(16),
        mobileUserDevice(17),
        repeater(18),
        bridgeExtender(19),
        gateway(20),
        storageVirtualizer(21),
        mediaLibrary(22),
        extenderNode(23),
        nasHead(24),
        selfcontainedNAS(25),
        ups(26),
        ipPhone(27),
        managementController(28),
        chassisManager(29)
    }
    MAX-ACCESS read-only
    STATUS     current
    DESCRIPTION
        "Enumeration indicating whether the ComputerSystem
        is a special-purpose System (ie, dedicated to a
        particular use), versus being 'general purpose'.
        For example, one could specify that the System is
        dedicated to 'Print' (value=11) or acts as a 'Hub'
        (value=8). 
        A clarification is needed with respect to the value
        17 ('Mobile User Device'). An example of a
        dedicated user device is a mobile phone or a
        barcode scanner in a store that communicates via
        radio frequency. These systems are quite limited in
        functionality and programmability, and are not
        considered 'general purpose' computing platforms.
        Alternately, an example of a mobile system that is
        'general purpose' (i.e., is NOT dedicated) is a
        hand-held computer. Although limited in its
        programmability, new software can be downloaded and
        its functionality expanded by the user. 
        A value of 'Management' indicates this instance is
        dedicated to hosting system management software. 
        A value of 'Management Controller' indicates this
        instance represents specialized hardware dedicated
        to systems management (i.e., a Baseboard Management
        Controller (BMC) or service processor). 
        The management scope of a 'Management Controller'
        is typically a single managed system in which it is
        contained. 
        A value of 'Chassis Manager' indicates this
        instance represents a system dedicated to
        management of a blade chassis and its contained
        devices. This value would be used to represent a
        Shelf Controller. A 'Chassis Manager' is an
        aggregation point for management and may rely on
        subordinate management controllers for the
        management of constituent parts."
    ::= { msvmComputerSystemEntry 17 }

msvmcsOtherEnabledState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "EnabledState is an integer enumeration that
        indicates the enabled and disabled states of an
        element. It can also indicate the transitions
        between these requested states. For example,
        shutting down (value=4) and starting (value=10) are
        transient states between enabled and disabled. The
        following text briefly summarizes the various
        enabled and disabled states: 
        Enabled (2) indicates that the element is or could
        be executing commands, will process any queued
        commands, and queues new requests. 
        Disabled (3) indicates that the element will not
        execute commands and will drop any new requests. 
        Shutting Down (4) indicates that the element is in
        the process of going to a Disabled state. 
        Not Applicable (5) indicates the element does not
        support being enabled or disabled. 
        Enabled but Offline (6) indicates that the element
        might be completing commands, and will drop any new
        requests. 
        Test (7) indicates that the element is in a test
        state. 
        Deferred (8) indicates that the element might be
        completing commands, but will queue any new
        requests. 
        Quiesce (9) indicates that the element is enabled
        but in a restricted mode. The behavior of the
        element is similar to the Enabled state, but it
        processes only a restricted set of commands. All
        other requests are queued. 
        Starting (10) indicates that the element is in the
        process of going to an Enabled state. New requests
        are queued."
    ::= { msvmComputerSystemEntry 18 }

msvmcsOtherIdentifyingInfo OBJECT-TYPE
    SYNTAX     WtcsDisplayString (SIZE (0..256))
    MAX-ACCESS read-only
    STATUS     current
    DESCRIPTION
        "An array of free-form strings providing
        explanations and details behind the entries in the
        OtherIdentifying Info array. Note, each entry of
        this array is related to the entry in
        OtherIdentifyingInfo that is located at the same
        index."
    ::= { msvmComputerSystemEntry 19 }

msvmcsPowerManagementCapability OBJECT-TYPE
    SYNTAX     INTEGER {
        unknown(0),
        notSupported(1),
        disabled(2),
        enabled(3),
        powerSavingModesEnteredAutomatic(4),
        powerStateSettable(5),
        powerCyclingSupported(6),
        timedPowerOnSupported(7)
    }
    MAX-ACCESS read-only
    STATUS     current
    DESCRIPTION
        "An enumerated array describing the power
        management capabilities of the ComputerSystem. The
        use of this property has been deprecated. Instead,
        the Power Capabilites property in an associated
        PowerManagement Capabilities class should be used."
    ::= { msvmComputerSystemEntry 20 }

msvmcsPrimaryOwnerContact OBJECT-TYPE
    SYNTAX     WtcsDisplayString (SIZE (0..256))
    MAX-ACCESS read-only
    STATUS     current
    DESCRIPTION
        "A string that provides information on how the
        primary system owner can be reached (for example,
        phone number, e-mail address, and so on)."
    ::= { msvmComputerSystemEntry 21 }

msvmcsPrimaryOwnerName OBJECT-TYPE
    SYNTAX     WtcsDisplayString (SIZE (0..64))
    MAX-ACCESS read-only
    STATUS     current
    DESCRIPTION
        "The name of the primary system owner. The system
        owner is the primary user of the system."
    ::= { msvmComputerSystemEntry 22 }

msvmcsProcessID OBJECT-TYPE
    SYNTAX     Gauge32
    MAX-ACCESS read-only
    STATUS     current
    DESCRIPTION
        "None"
    ::= { msvmComputerSystemEntry 23 }

msvmcsRequestedState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "EnabledState is an integer enumeration that
        indicates the enabled and disabled states of an
        element. It can also indicate the transitions
        between these requested states. For example,
        shutting down (value=4) and starting (value=10) are
        transient states between enabled and disabled. The
        following text briefly summarizes the various
        enabled and disabled states: 
        Enabled (2) indicates that the element is or could
        be executing commands, will process any queued
        commands, and queues new requests. 
        Disabled (3) indicates that the element will not
        execute commands and will drop any new requests. 
        Shutting Down (4) indicates that the element is in
        the process of going to a Disabled state. 
        Not Applicable (5) indicates the element does not
        support being enabled or disabled. 
        Enabled but Offline (6) indicates that the element
        might be completing commands, and will drop any new
        requests. 
        Test (7) indicates that the element is in a test
        state. 
        Deferred (8) indicates that the element might be
        completing commands, but will queue any new
        requests. 
        Quiesce (9) indicates that the element is enabled
        but in a restricted mode. The behavior of the
        element is similar to the Enabled state, but it
        processes only a restricted set of commands. All
        other requests are queued. 
        Starting (10) indicates that the element is in the
        process of going to an Enabled state. New requests
        are queued."
    ::= { msvmComputerSystemEntry 24 }

msvmcsResetCapability OBJECT-TYPE
    SYNTAX     INTEGER {
        other(1),
        unknown(2),
        disabled(3),
        enabled(4),
        notImplemented(5)
    }
    MAX-ACCESS read-only
    STATUS     current
    DESCRIPTION
        "If enabled (value = 4), the ComputerSystem can be
        reset via hardware (e.g. the power and reset
        buttons). If disabled (value = 3), hardware reset
        is not allowed. In addition to Enabled and
        Disabled, other Values for the property are also
        defined - 'Not Implemented' (5), 'Other' (1) and
        'Unknown' (2)."
    ::= { msvmComputerSystemEntry 25 }

msvmcsRoles OBJECT-TYPE
    SYNTAX     WtcsDisplayString
    MAX-ACCESS read-only
    STATUS     current
    DESCRIPTION
        "An array (bag) of strings that specifies the
        administrator -defined roles this System plays in
        the managed environment. Examples might be
        'Building 8 print server' or 'Boise user
        directories'. A single system may perform multiple
        roles. 
        Note that the instrumentation view of the 'roles'
        of a System is defined by instantiating a specific
        subclass of System, or by properties in a subclass,
        or both. For example, the purpose of a
        ComputerSystem is defined using the Dedicated and
        OtherDedicatedDescription properties."
    ::= { msvmComputerSystemEntry 26 }

msvmcsStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmComputerSystemEntry 27 }

msvmcsStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmComputerSystemEntry 28 }

msvmcsTimeOfLastConfigChange OBJECT-TYPE
    SYNTAX     DateAndTime
    MAX-ACCESS read-only
    STATUS     current
    DESCRIPTION
        "The date or time when the enabled state of the
        element last changed. This property is inherited
        from CIM_EnabledLogicalElement."
    ::= { msvmComputerSystemEntry 29 }

msvmcsTimeOfLastStateChange OBJECT-TYPE
    SYNTAX     DateAndTime
    MAX-ACCESS read-only
    STATUS     current
    DESCRIPTION
        "The date or time when the EnabledState of the
        element last changed. If the state of the element
        has not changed and this property is populated,
        then it must be set to a 0 interval value. If a
        state change was requested, but rejected or not yet
        processed, the property must not be updated."
    ::= { msvmComputerSystemEntry 30 }

msvmConcreteComponentTable OBJECT-TYPE
    SYNTAX     SEQUENCE OF MsvmConcreteComponent
    MAX-ACCESS not-accessible
    STATUS     current
    DESCRIPTION
        "A generic association used to establish 'part of'
        relationships between ManagedElements."
    ::= { msvmVirtualSystem 2 }

msvmConcreteComponentEntry OBJECT-TYPE
    SYNTAX     MsvmConcreteComponent
    MAX-ACCESS not-accessible
    STATUS     current
    DESCRIPTION
        "None"
    INDEX      { msvmccIndex }
    ::= { msvmConcreteComponentTable 1 }

MsvmConcreteComponent ::= SEQUENCE {
    msvmccIndex Integer32,
    msvmccGroupComponent WtcsDisplayString,
    msvmccPartComponent WtcsDisplayString
}

msvmccIndex OBJECT-TYPE
    SYNTAX     Integer32 (1..2147483647)
    MAX-ACCESS read-only
    STATUS     current
    DESCRIPTION
        "The value of this object uniquely identifies the
        instance entry for this class."
    ::= { msvmConcreteComponentEntry 1 }

msvmccGroupComponent OBJECT-TYPE
    SYNTAX     WtcsDisplayString
    MAX-ACCESS read-only
    STATUS     current
    DESCRIPTION
        "The parent element in the association."
    ::= { msvmConcreteComponentEntry 2 }

msvmccPartComponent OBJECT-TYPE
    SYNTAX     WtcsDisplayString
    MAX-ACCESS read-only
    STATUS     current
    DESCRIPTION
        "The child element in the association."
    ::= { msvmConcreteComponentEntry 3 }

msvmLastAppliedSettingDataTable OBJECT-TYPE
    SYNTAX     SEQUENCE OF MsvmLastAppliedSettingData
    MAX-ACCESS not-accessible
    STATUS     current
    DESCRIPTION
        "An association between a virtual system and the
        setting data of the snapshot which was most
        recently applied to the virtual system."
    ::= { msvmVirtualSystem 3 }

msvmLastAppliedSettingDataEntry OBJECT-TYPE
    SYNTAX     MsvmLastAppliedSettingData
    MAX-ACCESS not-accessible
    STATUS     current
    DESCRIPTION
        "None"
    INDEX      { msvmlasdIndex }
    ::= { msvmLastAppliedSettingDataTable 1 }

MsvmLastAppliedSettingData ::= SEQUENCE {
    msvmlasdIndex Integer32,
    msvmlasdAppliedObject WtcsDisplayString,
    msvmlasdTarget WtcsDisplayString
}

msvmlasdIndex OBJECT-TYPE
    SYNTAX     Integer32 (1..2147483647)
    MAX-ACCESS read-only
    STATUS     current
    DESCRIPTION
        "The value of this object uniquely identifies the
        instance entry for this class."
    ::= { msvmLastAppliedSettingDataEntry 1 }

msvmlasdAppliedObject OBJECT-TYPE
    SYNTAX     WtcsDisplayString
    MAX-ACCESS read-only
    STATUS     current
    DESCRIPTION
        "The snapshot setting data which was most recently
        applied to the computer system."
    ::= { msvmLastAppliedSettingDataEntry 2 }

msvmlasdTarget OBJECT-TYPE
    SYNTAX     WtcsDisplayString
    MAX-ACCESS read-only
    STATUS     current
    DESCRIPTION
        "The computer system which was the target of the
        application."
    ::= { msvmLastAppliedSettingDataEntry 3 }

msvmParentChildSettingDataTable OBJECT-TYPE
    SYNTAX     SEQUENCE OF MsvmParentChildSettingData
    MAX-ACCESS not-accessible
    STATUS     current
    DESCRIPTION
        "An association between an instance of
        CIM_VirtualSystemSettingData and the
        CIM_VirtualSystemSettingData instance which
        represents the most recent snapshot upon which this
        object is based."
    ::= { msvmVirtualSystem 4 }

msvmParentChildSettingDataEntry OBJECT-TYPE
    SYNTAX     MsvmParentChildSettingData
    MAX-ACCESS not-accessible
    STATUS     current
    DESCRIPTION
        "None"
    INDEX      { msvmpcsdIndex }
    ::= { msvmParentChildSettingDataTable 1 }

MsvmParentChildSettingData ::= SEQUENCE {
    msvmpcsdIndex Integer32,
    msvmpcsdAntecedent WtcsDisplayString,
    msvmpcsdChild WtcsDisplayString,
    msvmpcsdDependent WtcsDisplayString,
    msvmpcsdParent WtcsDisplayString
}

msvmpcsdIndex OBJECT-TYPE
    SYNTAX     Integer32 (1..2147483647)
    MAX-ACCESS read-only
    STATUS     current
    DESCRIPTION
        "The value of this object uniquely identifies the
        instance entry for this class."
    ::= { msvmParentChildSettingDataEntry 1 }

msvmpcsdAntecedent OBJECT-TYPE
    SYNTAX     WtcsDisplayString
    MAX-ACCESS read-only
    STATUS     current
    DESCRIPTION
        "Antecedent represents the independent object in
        this association."
    ::= { msvmParentChildSettingDataEntry 2 }

msvmpcsdChild OBJECT-TYPE
    SYNTAX     WtcsDisplayString
    MAX-ACCESS read-only
    STATUS     current
    DESCRIPTION
        "The setting data for the virtual system which
        represents the child of the Parent."
    ::= { msvmParentChildSettingDataEntry 3 }

msvmpcsdDependent OBJECT-TYPE
    SYNTAX     WtcsDisplayString
    MAX-ACCESS read-only
    STATUS     current
    DESCRIPTION
        "Dependent represents the object that is dependent
        on the Antecedent."
    ::= { msvmParentChildSettingDataEntry 4 }

msvmpcsdParent OBJECT-TYPE
    SYNTAX     WtcsDisplayString
    MAX-ACCESS read-only
    STATUS     current
    DESCRIPTION
        "The snapshot setting data upon which the Child
        setting data is based."
    ::= { msvmParentChildSettingDataEntry 5 }

msvmPreviousSettingDataTable OBJECT-TYPE
    SYNTAX     SEQUENCE OF MsvmPreviousSettingData
    MAX-ACCESS not-accessible
    STATUS     current
    DESCRIPTION
        "An association between a virtual system and the
        setting data of the snapshot which is the parent to
        the virtual system."
    ::= { msvmVirtualSystem 5 }

msvmPreviousSettingDataEntry OBJECT-TYPE
    SYNTAX     MsvmPreviousSettingData
    MAX-ACCESS not-accessible
    STATUS     current
    DESCRIPTION
        "None"
    INDEX      { msvmpvsdIndex }
    ::= { msvmPreviousSettingDataTable 1 }

MsvmPreviousSettingData ::= SEQUENCE {
    msvmpvsdIndex Integer32,
    msvmpvsdPreviousObject WtcsDisplayString,
    msvmpvsdTarget WtcsDisplayString
}

msvmpvsdIndex OBJECT-TYPE
    SYNTAX     Integer32 (1..2147483647)
    MAX-ACCESS read-only
    STATUS     current
    DESCRIPTION
        "The value of this object uniquely identifies the
        instance entry for this class."
    ::= { msvmPreviousSettingDataEntry 1 }

msvmpvsdPreviousObject OBJECT-TYPE
    SYNTAX     WtcsDisplayString
    MAX-ACCESS read-only
    STATUS     current
    DESCRIPTION
        "The snapshot setting data which is the parent of
        this computer system."
    ::= { msvmPreviousSettingDataEntry 2 }

msvmpvsdTarget OBJECT-TYPE
    SYNTAX     WtcsDisplayString
    MAX-ACCESS read-only
    STATUS     current
    DESCRIPTION
        "The computer system which was the target of the
        application."
    ::= { msvmPreviousSettingDataEntry 3 }

msvmSummaryInformationTable OBJECT-TYPE
    SYNTAX     SEQUENCE OF MsvmSummaryInformation
    MAX-ACCESS not-accessible
    STATUS     current
    DESCRIPTION
        "Used in the GetSummaryInformation method in the
        Msvm_VirtualSystemManagementService class to
        quickly retrieve common information related to a
        virtual system or snapshot."
    ::= { msvmVirtualSystem 6 }

msvmSummaryInformationEntry OBJECT-TYPE
    SYNTAX     MsvmSummaryInformation
    MAX-ACCESS not-accessible
    STATUS     current
    DESCRIPTION
        "None"
    INDEX      { msvmsiIndex }
    ::= { msvmSummaryInformationTable 1 }

MsvmSummaryInformation ::= SEQUENCE {
    msvmsiIndex Integer32,
    msvmsiCreationTime DateAndTime,
    msvmsiElementName WtcsDisplayString,
    msvmsiEnabledState Integer32,
    msvmsiGuestOperatingSystem WtcsDisplayString,
    msvmsiHealthState Integer32,
    msvmsiHeartbeat Integer32,
    msvmsiMemoryUsage Gauge32,
    msvmsiName WtcsDisplayString,
    msvmsiNotes WtcsDisplayString,
    msvmsiNumberOfProcessors Integer32,
    msvmsiProcessorLoad Integer32,
    msvmsiProcessorLoadHistory Integer32,
    msvmsiThumbnailImage Integer32,
    msvmsiUpTime Gauge32
}

msvmsiIndex OBJECT-TYPE
    SYNTAX     Integer32 (1..2147483647)
    MAX-ACCESS read-only
    STATUS     current
    DESCRIPTION
        "The value of this object uniquely identifies the
        instance entry for this class."
    ::= { msvmSummaryInformationEntry 1 }

msvmsiCreationTime OBJECT-TYPE
    SYNTAX     DateAndTime
    MAX-ACCESS read-only
    STATUS     current
    DESCRIPTION
        "The time at which the virtual system or snapshot
        was created."
    ::= { msvmSummaryInformationEntry 3 }

msvmsiElementName OBJECT-TYPE
    SYNTAX     WtcsDisplayString
    MAX-ACCESS read-only
    STATUS     current
    DESCRIPTION
        "The friendly name for the virtual system or
        snapshot."
    ::= { msvmSummaryInformationEntry 4 }

msvmsiEnabledState OBJECT-TYPE
    SYNTAX     Integer32
    MAX-ACCESS read-only
    STATUS     current
    DESCRIPTION
        "The current state of the virtual system or
        snapshot."
    ::= { msvmSummaryInformationEntry 5 }

msvmsiGuestOperatingSystem OBJECT-TYPE
    SYNTAX     WtcsDisplayString
    MAX-ACCESS read-only
    STATUS     current
    DESCRIPTION
        "The name of the guest operating system, if
        available. If this information is not available,
        the value of this property is NULL. This property
        is not valid for instances of
        Msvm_SummaryInformation representing a virtual
        system snapshot."
    ::= { msvmSummaryInformationEntry 6 }

msvmsiHealthState OBJECT-TYPE
    SYNTAX     Integer32
    MAX-ACCESS read-only
    STATUS     current
    DESCRIPTION
        "Describes the current health state for the virtual
        system. This property is not valid for instances of
        Msvm_SummaryInformation representing a virtual
        system snapshot."
    ::= { msvmSummaryInformationEntry 7 }

msvmsiHeartbeat OBJECT-TYPE
    SYNTAX     Integer32
    MAX-ACCESS read-only
    STATUS     current
    DESCRIPTION
        "The current heartbeat status for the virtual
        system. This property may be one of the following
        values: 'OK'; 'Error'; 'No Contact'; or 'Lost
        Communication'. See the documentation for the
        StatusDescriptions property of the
        Msvm_HeartbeatComponent class for more information.
        This property is not valid for instances of
        Msvm_SummaryInformation representing a virtual
        system snapshot."
    ::= { msvmSummaryInformationEntry 8 }

msvmsiMemoryUsage OBJECT-TYPE
    SYNTAX     Gauge32
    MAX-ACCESS read-only
    STATUS     current
    DESCRIPTION
        "The current memory usage of the virtual system.
        This property is not valid for instances of
        Msvm_SummaryInformation representing a virtual
        system snapshot."
    ::= { msvmSummaryInformationEntry 9 }

msvmsiName OBJECT-TYPE
    SYNTAX     WtcsDisplayString
    MAX-ACCESS read-only
    STATUS     current
    DESCRIPTION
        "The unique name for the virtual system or
        snapshot."
    ::= { msvmSummaryInformationEntry 10 }

msvmsiNotes OBJECT-TYPE
    SYNTAX     WtcsDisplayString
    MAX-ACCESS read-only
    STATUS     current
    DESCRIPTION
        "The notes associated with the virtual system or
        snapshot."
    ::= { msvmSummaryInformationEntry 11 }

msvmsiNumberOfProcessors OBJECT-TYPE
    SYNTAX     Integer32
    MAX-ACCESS read-only
    STATUS     current
    DESCRIPTION
        "The total number of virtual processors allocated
        to the virtual system or snapshot."
    ::= { msvmSummaryInformationEntry 12 }

msvmsiProcessorLoad OBJECT-TYPE
    SYNTAX     Integer32
    MAX-ACCESS read-only
    STATUS     current
    DESCRIPTION
        "The current processor usage of the virtual system.
        This property is not valid for instances of
        Msvm_SummaryInformation representing a virtual
        system snapshot."
    ::= { msvmSummaryInformationEntry 13 }

msvmsiProcessorLoadHistory OBJECT-TYPE
    SYNTAX     Integer32
    MAX-ACCESS read-only
    STATUS     current
    DESCRIPTION
        "An array of the previous 100 samples of the
        processor usage for the virtual system. This
        property is not valid for instances of
        Msvm_SummaryInformation representing a virtual
        system snapshot."
    ::= { msvmSummaryInformationEntry 14 }

msvmsiThumbnailImage OBJECT-TYPE
    SYNTAX     Integer32
    MAX-ACCESS read-only
    STATUS     current
    DESCRIPTION
        "An array containing a small, thumbnail-sized image
        of the desktop for the virtual system or snapshot
        in RGB565 format."
    ::= { msvmSummaryInformationEntry 16 }

msvmsiUpTime OBJECT-TYPE
    SYNTAX     Gauge32
    MAX-ACCESS read-only
    STATUS     current
    DESCRIPTION
        "The amount of time since the virtual system was
        last booted. This property is not valid for
        instances of Msvm_SummaryInformation representing a
        virtual system snapshot."
    ::= { msvmSummaryInformationEntry 17 }

msvmSystemDeviceTable OBJECT-TYPE
    SYNTAX     SEQUENCE OF MsvmSystemDevice
    MAX-ACCESS not-accessible
    STATUS     current
    DESCRIPTION
        "LogicalDevices can be aggregated by a System. This
        relationship is made explicit by the SystemDevice
        association."
    ::= { msvmVirtualSystem 7 }

msvmSystemDeviceEntry OBJECT-TYPE
    SYNTAX     MsvmSystemDevice
    MAX-ACCESS not-accessible
    STATUS     current
    DESCRIPTION
        "None"
    INDEX      { msvmsdIndex }
    ::= { msvmSystemDeviceTable 1 }

MsvmSystemDevice ::= SEQUENCE {
    msvmsdvIndex Integer32,
    msvmsdvGroupComponent WtcsDisplayString,
    msvmsdvPartComponent WtcsDisplayString
}

msvmsdvIndex OBJECT-TYPE
    SYNTAX     Integer32 (1..2147483647)
    MAX-ACCESS read-only
    STATUS     current
    DESCRIPTION
        "The value of this object uniquely identifies the
        instance entry for this class."
    ::= { msvmSystemDeviceEntry 1 }

msvmsdvGroupComponent OBJECT-TYPE
    SYNTAX     WtcsDisplayString
    MAX-ACCESS read-only
    STATUS     current
    DESCRIPTION
        "The parent element in the association."
    ::= { msvmSystemDeviceEntry 2 }

msvmsdvPartComponent OBJECT-TYPE
    SYNTAX     WtcsDisplayString
    MAX-ACCESS read-only
    STATUS     current
    DESCRIPTION
        "The child element in the association."
    ::= { msvmSystemDeviceEntry 3 }

msvmVirtualSystemGlobalDataTable OBJECT-TYPE
    SYNTAX     SEQUENCE OF MsvmVirtualSysGlobalSettingData
    MAX-ACCESS not-accessible
    STATUS     current
    DESCRIPTION
        "Represents the global settings for a virtual
        system. These settings do not change if a new
        snapshot is applied to the virtual system."
    ::= { msvmVirtualSystem 8 }

msvmVirtualSystemGlobalDataEntry OBJECT-TYPE
    SYNTAX     MsvmVirtualSysGlobalSettingData
    MAX-ACCESS not-accessible
    STATUS     current
    DESCRIPTION
        "None"
    INDEX      { msvmvsgsdIndex }
    ::= { msvmVirtualSystemGlobalDataTable 1 }

MsvmVirtualSysGlobalSettingData ::= SEQUENCE {
    msvmvsgsdIndex Integer32,
    msvmvsgsdAdditionalRecoveryInfo WtcsDisplayString,
    msvmvsgsdAutomaticRecoveryAction INTEGER,
    msvmvsgsdAutomaticShutdownAction INTEGER,
    msvmvsgsdAutomaticStartupAction INTEGER,
    msvmvsgsdAutoStartupActionDelay DateAndTime,
    msvmvsgsdCaption WtcsDisplayString,
    msvmvsgsdDebugChannelId Gauge32,
    msvmvsgsdDescription WtcsDisplayString,
    msvmvsgsdElementName WtcsDisplayString,
    msvmvsgsdExternalDataRoot WtcsDisplayString,
    msvmvsgsdInstanceID WtcsDisplayString,
    msvmvsgsdScopeOfResidence WtcsDisplayString,
    msvmvsgsdSnapshotDataRoot WtcsDisplayString
}

msvmvsgsdIndex OBJECT-TYPE
    SYNTAX     Integer32 (1..2147483647)
    MAX-ACCESS read-only
    STATUS     current
    DESCRIPTION
        "The value of this object uniquely identifies the
        instance entry for this class."
    ::= { msvmVirtualSystemGlobalDataEntry 1 }

msvmvsgsdAdditionalRecoveryInfo OBJECT-TYPE
    SYNTAX     WtcsDisplayString
    MAX-ACCESS read-only
    STATUS     current
    DESCRIPTION
        "Additional information supplied to the recovery
        action. The meaning of this property is defined by
        the action in AutomaticRecoveryAction. If
        AutomaticRecoveryAction is 0 ('None') or 1
        ('Restart'), this value is NULL. If
        AutomaticRecoveryAction is 2 ('Revert to
        Snapshot'), this is the object path to a snapshot
        that should be applied on failure of the virtual
        machine worker process."
    ::= { msvmVirtualSystemGlobalDataEntry 2 }

msvmvsgsdAutomaticRecoveryAction OBJECT-TYPE
    SYNTAX     INTEGER {
        none(0),
        restart(1),
        reverttoSnapshot(2)
    }
    MAX-ACCESS read-only
    STATUS     current
    DESCRIPTION
        "Determines the action to take if the virtual
        machine worker process terminates abnormally. The
        default action is 1 ('Restart')."
    ::= { msvmVirtualSystemGlobalDataEntry 3 }

msvmvsgsdAutomaticShutdownAction OBJECT-TYPE
    SYNTAX     INTEGER {
        turnOff(0),
        saveState(1),
        shutDown(2)
    }
    MAX-ACCESS read-only
    STATUS     current
    DESCRIPTION
        "Determines the action to take when the host is
        shut down. The default action is 1 ('Save State')."
    ::= { msvmVirtualSystemGlobalDataEntry 4 }

msvmvsgsdAutomaticStartupAction OBJECT-TYPE
    SYNTAX     INTEGER {
        none(0),
        restartifPreviouslyRunning(1),
        alwaysStartup(2)
    }
    MAX-ACCESS read-only
    STATUS     current
    DESCRIPTION
        "Determines the action to take when the host is
        started. The default action is 1 ('Restart if
        Previously Running')."
    ::= { msvmVirtualSystemGlobalDataEntry 5 }

msvmvsgsdAutoStartupActionDelay OBJECT-TYPE
    SYNTAX     DateAndTime
    MAX-ACCESS read-only
    STATUS     current
    DESCRIPTION
        "The time interval to wait before performing the
        startup action. By default, there is no delay."
    ::= { msvmVirtualSystemGlobalDataEntry 6 }

msvmvsgsdCaption OBJECT-TYPE
    SYNTAX     WtcsDisplayString (SIZE (0..64))
    MAX-ACCESS read-only
    STATUS     current
    DESCRIPTION
        "The Caption property is a short textual
        description (one- line string) of the object."
    ::= { msvmVirtualSystemGlobalDataEntry 7 }

msvmvsgsdDebugChannelId OBJECT-TYPE
    SYNTAX     Gauge32
    MAX-ACCESS read-only
    STATUS     current
    DESCRIPTION
        "The channel identifier used to debug the virtual
        system using the VUD unified debugger."
    ::= { msvmVirtualSystemGlobalDataEntry 8 }

msvmvsgsdDescription OBJECT-TYPE
    SYNTAX     WtcsDisplayString
    MAX-ACCESS read-only
    STATUS     current
    DESCRIPTION
        "The Description property provides a textual
        description of the object."
    ::= { msvmVirtualSystemGlobalDataEntry 9 }

msvmvsgsdElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmVirtualSystemGlobalDataEntry 10 }

msvmvsgsdExternalDataRoot OBJECT-TYPE
    SYNTAX     WtcsDisplayString
    MAX-ACCESS read-only
    STATUS     current
    DESCRIPTION
        "The fully-qualified path to the root directory of
        an external data store. This store is managed by
        the virtual system management service and may
        contain private data from multiple virtual systems.
        This property may be specified only at the time the
        virtual machine is defined. If NULL, the virtual
        system management service uses its own internally
        managed store."
    ::= { msvmVirtualSystemGlobalDataEntry 11 }

msvmvsgsdInstanceID OBJECT-TYPE
    SYNTAX     WtcsDisplayString
    MAX-ACCESS read-only
    STATUS     current
    DESCRIPTION
        "Within the scope of the instantiating Namespace,
        InstanceID opaquely and uniquely identifies an
        instance of this class. To ensure uniqueness within
        the NameSpace, the value of InstanceID should be
        constructed using the following 'preferred'
        algorithm: 
        <OrgID>:<LocalID> 
        Where <OrgID> and <LocalID> are separated by a
        colon (:), and where <OrgID> must include a
        copyrighted, trademarked, or otherwise unique name
        that is owned by the business entity that is
        creating or defining the InstanceID or that is a
        registered ID assigned to the business entity by a
        recognized global authority. (This requirement is
        similar to the <Schema Name>_<Class Name> structure
        of Schema class names.) In addition, to ensure
        uniqueness, <OrgID> must not contain a colon (:).
        When using this algorithm, the first colon to
        appear in InstanceID must appear between <OrgID>
        and <LocalID>. 
        <LocalID> is chosen by the business entity and
        should not be reused to identify different
        underlying (real-world) elements. If the above
        'preferred' algorithm is not used, the defining
        entity must assure that the resulting InstanceID is
        not reused across any InstanceIDs produced by this
        or other providers for the NameSpace of this
        instance. 
        For DMTF-defined instances, the 'preferred'
        algorithm must be used with the <OrgID> set to
        CIM."
    ::= { msvmVirtualSystemGlobalDataEntry 12 }

msvmvsgsdScopeOfResidence OBJECT-TYPE
    SYNTAX     WtcsDisplayString
    MAX-ACCESS read-only
    STATUS     current
    DESCRIPTION
        "The authorization scope to use in determining the
        access control policy for this virtual system."
    ::= { msvmVirtualSystemGlobalDataEntry 13 }

msvmvsgsdSnapshotDataRoot OBJECT-TYPE
    SYNTAX     WtcsDisplayString
    MAX-ACCESS read-only
    STATUS     current
    DESCRIPTION
        "The fully-qualified path to the root directory of
        the external data store used to store snapshots for
        this virtual system. This store is managed by the
        virtual system management service and may contain
        private data from multiple virtual systems. Changes
        made to this property affect only snapshots taken
        subsequent to the change. If NULL, snapshots are
        stored in the location determined by the
        Msvm_VirtualSystemGlobalSettingData.ExternalDataRoo
        t property."
    ::= { msvmVirtualSystemGlobalDataEntry 14 }

msvmVirtualSystemSetDataTable OBJECT-TYPE
    SYNTAX     SEQUENCE OF MsvmVirtualSystemSettingData
    MAX-ACCESS not-accessible
    STATUS     current
    DESCRIPTION
        "Represents the virtualization-specific settings
        for a virtual system."
    ::= { msvmVirtualSystem 9 }

msvmVirtualSystemSetDataEntry OBJECT-TYPE
    SYNTAX     MsvmVirtualSystemSettingData
    MAX-ACCESS not-accessible
    STATUS     current
    DESCRIPTION
        "None"
    INDEX      { msvmvssdIndex }
    ::= { msvmVirtualSystemSetDataTable 1 }

MsvmVirtualSystemSettingData ::= SEQUENCE {
    msvmvssdIndex Integer32,
    msvmvssdAutoActivate TruthValue,
    msvmvssdBIOSGUID WtcsDisplayString,
    msvmvssdBIOSNumLock TruthValue,
    msvmvssdBIOSSerialNumber WtcsDisplayString,
    msvmvssdBaseBoardSerialNumber WtcsDisplayString,
    msvmvssdBootOrder Integer32,
    msvmvssdCaption WtcsDisplayString,
    msvmvssdChassisAssetTag WtcsDisplayString,
    msvmvssdChassisSerialNumber WtcsDisplayString,
    msvmvssdCreationTime DateAndTime,
    msvmvssdDescription WtcsDisplayString,
    msvmvssdElementName WtcsDisplayString,
    msvmvssdInstanceID WtcsDisplayString,
    msvmvssdNotes WtcsDisplayString,
    msvmvssdNumaNodeList Integer32,
    msvmvssdNumaNodesAreRequired TruthValue,
    msvmvssdOtherVirtualSystemType WtcsDisplayString,
    msvmvssdParent WtcsDisplayString,
    msvmvssdSettingType INTEGER,
    msvmvssdSystemName WtcsDisplayString,
    msvmvssdVirtualSystemType INTEGER
}

msvmvssdIndex OBJECT-TYPE
    SYNTAX     Integer32 (1..2147483647)
    MAX-ACCESS read-only
    STATUS     current
    DESCRIPTION
        "The value of this object uniquely identifies the
        instance entry for this class."
    ::= { msvmVirtualSystemSetDataEntry 1 }

msvmvssdAutoActivate OBJECT-TYPE
    SYNTAX     TruthValue
    MAX-ACCESS read-only
    STATUS     current
    DESCRIPTION
        "Flag indicating whether the virtual system is
        automatically started when the virtualization
        platform is started."
    ::= { msvmVirtualSystemSetDataEntry 2 }

msvmvssdBIOSGUID OBJECT-TYPE
    SYNTAX     WtcsDisplayString
    MAX-ACCESS read-only
    STATUS     current
    DESCRIPTION
        "The globally-unique identifier for the BIOS of the
        virtual computer system."
    ::= { msvmVirtualSystemSetDataEntry 3 }

msvmvssdBIOSNumLock OBJECT-TYPE
    SYNTAX     TruthValue
    MAX-ACCESS read-only
    STATUS     current
    DESCRIPTION
        "Set to TRUE if the num lock key is set to on by
        the BIOS, FALSE if the num lock key is set to off
        by the BIOS."
    ::= { msvmVirtualSystemSetDataEntry 4 }

msvmvssdBIOSSerialNumber OBJECT-TYPE
    SYNTAX     WtcsDisplayString
    MAX-ACCESS read-only
    STATUS     current
    DESCRIPTION
        "The serial number of the BIOS for the virtual
        computer system."
    ::= { msvmVirtualSystemSetDataEntry 5 }

msvmvssdBaseBoardSerialNumber OBJECT-TYPE
    SYNTAX     WtcsDisplayString
    MAX-ACCESS read-only
    STATUS     current
    DESCRIPTION
        "The serial number of the base board for the
        virtual computer system."
    ::= { msvmVirtualSystemSetDataEntry 6 }

msvmvssdBootOrder OBJECT-TYPE
    SYNTAX     Integer32
    MAX-ACCESS read-only
    STATUS     current
    DESCRIPTION
        "The boot order set within the BIOS of the virtual
        computer system. This property is an array of
        values where each value indicates a device to boot
        from. The virtual computer system will first
        attempt to boot from the device indicated by the
        first value within the array. If that device does
        not contain a boot sector, the virtual computer
        system will attempt to boot from the next device
        specified by the BootOrder property and so on. If
        no device specified within the BootOrder contains a
        boot sector the virtual computer system will fail
        to boot. The default value for a virtual computer
        system is [0, 1, 2, 3, 4]."
    ::= { msvmVirtualSystemSetDataEntry 7 }

msvmvssdCaption OBJECT-TYPE
    SYNTAX     WtcsDisplayString (SIZE (0..64))
    MAX-ACCESS read-only
    STATUS     current
    DESCRIPTION
        "The Caption property is a short textual
        description (one- line string) of the object."
    ::= { msvmVirtualSystemSetDataEntry 8 }

msvmvssdChassisAssetTag OBJECT-TYPE
    SYNTAX     WtcsDisplayString
    MAX-ACCESS read-only
    STATUS     current
    DESCRIPTION
        "The asset tag value of the chassis for the virtual
        computer system."
    ::= { msvmVirtualSystemSetDataEntry 9 }

msvmvssdChassisSerialNumber OBJECT-TYPE
    SYNTAX     WtcsDisplayString
    MAX-ACCESS read-only
    STATUS     current
    DESCRIPTION
        "The serial number of the chassis for the virtual
        computer system."
    ::= { msvmVirtualSystemSetDataEntry 10 }

msvmvssdCreationTime OBJECT-TYPE
    SYNTAX     DateAndTime
    MAX-ACCESS read-only
    STATUS     current
    DESCRIPTION
        "The date or time when the virtual system setting
        data was created.For snapshots, this value
        corresponds to the time at which the snapshot was
        taken. For non-snapshots, this value corresponds to
        the time at which the virtual system was created."
    ::= { msvmVirtualSystemSetDataEntry 11 }

msvmvssdDescription OBJECT-TYPE
    SYNTAX     WtcsDisplayString
    MAX-ACCESS read-only
    STATUS     current
    DESCRIPTION
        "The Description property provides a textual
        description of the object."
    ::= { msvmVirtualSystemSetDataEntry 12 }

msvmvssdElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmVirtualSystemSetDataEntry 13 }

msvmvssdInstanceID OBJECT-TYPE
    SYNTAX     WtcsDisplayString
    MAX-ACCESS read-only
    STATUS     current
    DESCRIPTION
        "Within the scope of the instantiating Namespace,
        InstanceID opaquely and uniquely identifies an
        instance of this class. To ensure uniqueness within
        the NameSpace, the value of InstanceID should be
        constructed using the following 'preferred'
        algorithm: 
        <OrgID>:<LocalID> 
        Where <OrgID> and <LocalID> are separated by a
        colon (:), and where <OrgID> must include a
        copyrighted, trademarked, or otherwise unique name
        that is owned by the business entity that is
        creating or defining the InstanceID or that is a
        registered ID assigned to the business entity by a
        recognized global authority. (This requirement is
        similar to the <Schema Name>_<Class Name> structure
        of Schema class names.) In addition, to ensure
        uniqueness, <OrgID> must not contain a colon (:).
        When using this algorithm, the first colon to
        appear in InstanceID must appear between <OrgID>
        and <LocalID>. 
        <LocalID> is chosen by the business entity and
        should not be reused to identify different
        underlying (real-world) elements. If the above
        'preferred' algorithm is not used, the defining
        entity must assure that the resulting InstanceID is
        not reused across any InstanceIDs produced by this
        or other providers for the NameSpace of this
        instance. 
        For DMTF-defined instances, the 'preferred'
        algorithm must be used with the <OrgID> set to
        CIM."
    ::= { msvmVirtualSystemSetDataEntry 14 }

msvmvssdNotes OBJECT-TYPE
    SYNTAX     WtcsDisplayString
    MAX-ACCESS read-only
    STATUS     current
    DESCRIPTION
        "A free-form string containing notes for the
        system."
    ::= { msvmVirtualSystemSetDataEntry 15 }

msvmvssdNumaNodeList OBJECT-TYPE
    SYNTAX     Integer32
    MAX-ACCESS read-only
    STATUS     current
    DESCRIPTION
        "For NUMA-capable systems, this is the list of NUMA
        nodes on which the virtual machine is to be run."
    ::= { msvmVirtualSystemSetDataEntry 16 }

msvmvssdNumaNodesAreRequired OBJECT-TYPE
    SYNTAX     TruthValue
    MAX-ACCESS read-only
    STATUS     current
    DESCRIPTION
        "For NUMA-capable systems, this value indicates
        whether the nodes specified in NumaNodeList are
        required or preferred. If this value is TRUE (the
        nodes are required), the virtual machine will fail
        to start if there are not enough resources
        available on the specified NUMA nodes."
    ::= { msvmVirtualSystemSetDataEntry 17 }

msvmvssdOtherVirtualSystemType OBJECT-TYPE
    SYNTAX     WtcsDisplayString
    MAX-ACCESS read-only
    STATUS     current
    DESCRIPTION
        "OtherVirtualSystemType designates the type of the
        virtual system if VirtualSystemType is set to 1 -
        Other."
    ::= { msvmVirtualSystemSetDataEntry 18 }

msvmvssdParent OBJECT-TYPE
    SYNTAX     WtcsDisplayString
    MAX-ACCESS read-only
    STATUS     current
    DESCRIPTION
        "If this instance does not represent a snapshot of
        the virtual system, this property is NULL.
        Otherwise, the property holds the object path of
        the Msvm_VirtualSystemSettingData object on which
        this instance is based. When building a snapshot
        tree hierarchy for the virtual machine, this
        property references the object from which the
        current instance is derived (the current instance
        is the child node and the object referenced in this
        property is the parent node.)"
    ::= { msvmVirtualSystemSetDataEntry 19 }

msvmvssdSettingType OBJECT-TYPE
    SYNTAX     INTEGER {
        input(1),
        recorded(2),
        current(3),
        capability(4),
        snapshot(5)
    }
    MAX-ACCESS read-only
    STATUS     current
    DESCRIPTION
        "SettingType describes a usage context of the
        instance. A value of 1 - Input designates an
        instance reflecting the virtual aspects of a input
        virtual system configuration, a value of 2 -
        Recorded designates an instance reflecting the
        virtual aspects of a virtual system definition, a
        value of 3 - Current designates an instance
        reflecting a virtual aspects of a currently active
        virtual, a value of 4 - Capability designates an
        instance reflecting virtual system capabilities,
        and a value of 5 - Snapshot designates an instance
        reflecting virtual aspects of a snapshot of a
        virtual system."
    ::= { msvmVirtualSystemSetDataEntry 20 }

msvmvssdSystemName OBJECT-TYPE
    SYNTAX     WtcsDisplayString
    MAX-ACCESS read-only
    STATUS     current
    DESCRIPTION
        "SystemName shall reflect a unique name for the
        system as it is used within the virtualization
        platform. Note that the SystemName is not the
        hostname assigned to the operating system instance
        running within the virtual system, nor is it an IP
        address or MAC address assigned to any of its
        network ports."
    ::= { msvmVirtualSystemSetDataEntry 21 }

msvmvssdVirtualSystemType OBJECT-TYPE
    SYNTAX     INTEGER {
        unknown(0),
        other(1),
        emcvmWare(101),
        ibmPowerIVM(201),
        ibmPowerVIOS(202),
        ibmPoweri5OS(203),
        ibmSystemzLPARESA390(204),
        ibmSystemzLPARESA390TPF(205),
        ibmSystemzLPARCF(206),
        ibmSystemzLPARLinux(207),
        ibmSystemzzVMESA(208),
        ibmSystemzzVMXA(209),
        ibmSYstemzzVMXC(210),
        microsoftVirtualServer(301),
        xenSoftXen(401)
    }
    MAX-ACCESS read-only
    STATUS     current
    DESCRIPTION
        "Virtualization platforms may provide various types
        of virtual systems, some of which may be
        specifically tailored for the use by a particular
        operating system. A management application may
        learn about the set of types supported by a
        virtualization platform by analyzing class
        information provided by the virtualization platform
        specific subclass of this class. During virtual
        system creation a management applicaton may request
        a particular virtual system type by setting this
        property accordingly."
    ::= { msvmVirtualSystemSetDataEntry 22 }

msvmVirtualSystemDataComponTable OBJECT-TYPE
    SYNTAX     SEQUENCE OF MsvmVirtualSystemDataComponent
    MAX-ACCESS not-accessible
    STATUS     current
    DESCRIPTION
        "A generic association used to establish 'part of'
        relationships between one instance of
        VirtualSystemSettingData and one or more instances
        of ResourceAllocationSettingData."
    ::= { msvmVirtualSystem 10 }

msvmVirtualSystemDataComponEntry OBJECT-TYPE
    SYNTAX     MsvmVirtualSystemDataComponent
    MAX-ACCESS not-accessible
    STATUS     current
    DESCRIPTION
        "None"
    INDEX      { msvmvssdcIndex }
    ::= { msvmVirtualSystemDataComponTable 1 }

MsvmVirtualSystemDataComponent ::= SEQUENCE {
    msvmvssdcIndex Integer32,
    msvmvssdcGroupComponent WtcsDisplayString,
    msvmvssdcPartComponent WtcsDisplayString
}

msvmvssdcIndex OBJECT-TYPE
    SYNTAX     Integer32 (1..2147483647)
    MAX-ACCESS read-only
    STATUS     current
    DESCRIPTION
        "The value of this object uniquely identifies the
        instance entry for this class."
    ::= { msvmVirtualSystemDataComponEntry 1 }

msvmvssdcGroupComponent OBJECT-TYPE
    SYNTAX     WtcsDisplayString
    MAX-ACCESS read-only
    STATUS     current
    DESCRIPTION
        "The parent element in the association."
    ::= { msvmVirtualSystemDataComponEntry 2 }

msvmvssdcPartComponent OBJECT-TYPE
    SYNTAX     WtcsDisplayString
    MAX-ACCESS read-only
    STATUS     current
    DESCRIPTION
        "The child element in the association."
    ::= { msvmVirtualSystemDataComponEntry 3 }

msvmVirtualSystemManagement OBJECT-IDENTITY
    STATUS     current
    DESCRIPTION
        "The following are virtualization WMI classes
        related to virtual system management."
    ::= { informantHyperV 13 }

msvmAffectedJobElementTable OBJECT-TYPE
    SYNTAX     SEQUENCE OF MsvmAffectedJobElement
    MAX-ACCESS not-accessible
    STATUS     current
    DESCRIPTION
        "Represents an association between a Job and the
        ManagedElement(s) that may be affected by its
        execution."
    ::= { msvmVirtualSystemManagement 1 }

msvmAffectedJobElementEntry OBJECT-TYPE
    SYNTAX     MsvmAffectedJobElement
    MAX-ACCESS not-accessible
    STATUS     current
    DESCRIPTION
        "None"
    INDEX      { msvmajeIndex }
    ::= { msvmAffectedJobElementTable 1 }

MsvmAffectedJobElement ::= SEQUENCE {
    msvmajeIndex Integer32,
    msvmajeAffectedElement WtcsDisplayString,
    msvmajeAffectingElement WtcsDisplayString,
    msvmajeElementEffects INTEGER,
    msvmajeOtherElementEffectsDescr WtcsDisplayString
}

msvmajeIndex OBJECT-TYPE
    SYNTAX     Integer32 (1..2147483647)
    MAX-ACCESS read-only
    STATUS     current
    DESCRIPTION
        "The value of this object uniquely identifies the
        instance entry for this class."
    ::= { msvmAffectedJobElementEntry 1 }

msvmajeAffectedElement OBJECT-TYPE
    SYNTAX     WtcsDisplayString
    MAX-ACCESS read-only
    STATUS     current
    DESCRIPTION
        "The ManagedElement affected by the execution of
        the Job."
    ::= { msvmAffectedJobElementEntry 2 }

msvmajeAffectingElement OBJECT-TYPE
    SYNTAX     WtcsDisplayString
    MAX-ACCESS read-only
    STATUS     current
    DESCRIPTION
        "The Job that is affecting the ManagedElement."
    ::= { msvmAffectedJobElementEntry 3 }

msvmajeElementEffects OBJECT-TYPE
    SYNTAX     INTEGER {
        unknown(0),
        other(1),
        exclusiveUse(2),
        performanceImpact(3),
        elementIntegrity(4)
    }
    MAX-ACCESS read-only
    STATUS     current
    DESCRIPTION
        "An enumeration describing the 'effect' on the
        ManagedElement. This array corresponds to the
        OtherElementEffectsDescriptions array, where the
        latter provides details related to the high-level
        'effects' enumerated by this property. Additional
        detail is required if the ElementEffects array
        contains the value 1, 'Other'."
    ::= { msvmAffectedJobElementEntry 4 }

msvmajeOtherElementEffectsDescr OBJECT-TYPE
    SYNTAX     WtcsDisplayString
    MAX-ACCESS read-only
    STATUS     current
    DESCRIPTION
        "Provides details for the 'effect' at the
        corresponding array position in ElementEffects.
        This information is required whenever
        ElementEffects contains the value 1 ('Other')."
    ::= { msvmAffectedJobElementEntry 5 }

msvmConcreteJobTable OBJECT-TYPE
    SYNTAX     SEQUENCE OF MsvmConcreteJob
    MAX-ACCESS not-accessible
    STATUS     current
    DESCRIPTION
        "A concrete version of Job. This class represents a
        generic and instantiable unit of work, such as a
        batch or a print job."
    ::= { msvmVirtualSystemManagement 2 }

msvmConcreteJobEntry OBJECT-TYPE
    SYNTAX     MsvmConcreteJob
    MAX-ACCESS not-accessible
    STATUS     current
    DESCRIPTION
        "None"
    INDEX      { msvmcjIndex }
    ::= { msvmConcreteJobTable 1 }

MsvmConcreteJob ::= SEQUENCE {
    msvmcjIndex Integer32,
    msvmcjCancellable TruthValue,
    msvmcjCaption WtcsDisplayString,
    msvmcjDeleteOnCompletion TruthValue,
    msvmcjDescription WtcsDisplayString,
    msvmcjElapsedTime DateAndTime,
    msvmcjElementName WtcsDisplayString,
    msvmcjErrorCode Integer32,
    msvmcjErrorDescription WtcsDisplayString,
    msvmcjErrorSummaryDescription WtcsDisplayString,
    msvmcjHealthState INTEGER,
    msvmcjInstallDate DateAndTime,
    msvmcjInstanceID WtcsDisplayString,
    msvmcjJobRunTimes Gauge32,
    msvmcjJobState INTEGER,
    msvmcjJobStatus WtcsDisplayString,
    msvmcjLocalOrUtcTime INTEGER,
    msvmcjName WtcsDisplayString,
    msvmcjNotify WtcsDisplayString,
    msvmcjOperationalStatus INTEGER,
    msvmcjOtherRecoveryAction WtcsDisplayString,
    msvmcjOwner WtcsDisplayString,
    msvmcjPercentComplete Integer32,
    msvmcjPriority Gauge32,
    msvmcjRecoveryAction INTEGER,
    msvmcjRunDay Integer32,
    msvmcjRunDayOfWeek Integer32,
    msvmcjRunMonth INTEGER,
    msvmcjRunStartInterval DateAndTime,
    msvmcjScheduledStartTime DateAndTime,
    msvmcjStartTime DateAndTime,
    msvmcjStatus WtcsDisplayString,
    msvmcjStatusDescriptions WtcsDisplayString,
    msvmcjTimeBeforeRemoval DateAndTime,
    msvmcjTimeOfLastStateChange DateAndTime,
    msvmcjTimeSubmitted DateAndTime,
    msvmcjUntilTime DateAndTime
}

msvmcjIndex OBJECT-TYPE
    SYNTAX     Integer32 (1..2147483647)
    MAX-ACCESS read-only
    STATUS     current
    DESCRIPTION
        "The value of this object uniquely identifies the
        instance entry for this class."
    ::= { msvmConcreteJobEntry 1 }

msvmcjCancellable OBJECT-TYPE
    SYNTAX     TruthValue
    MAX-ACCESS read-only
    STATUS     current
    DESCRIPTION
        "Indicates whether or not the job can be cancelled.
        The value of this property does not guarantee that
        a request to cancel the job will succeed."
    ::= { msvmConcreteJobEntry 2 }

msvmcjCaption OBJECT-TYPE
    SYNTAX     WtcsDisplayString (SIZE (0..64))
    MAX-ACCESS read-only
    STATUS     current
    DESCRIPTION
        "The Caption property is a short textual
        description (one- line string) of the object."
    ::= { msvmConcreteJobEntry 3 }

msvmcjDeleteOnCompletion OBJECT-TYPE
    SYNTAX     TruthValue
    MAX-ACCESS read-only
    STATUS     current
    DESCRIPTION
        "Indicates whether or not the job should be
        automatically deleted upon completion. Note that
        the 'completion' of a recurring job is defined by
        its JobRunTimes or UntilTime properties, or when
        the Job is terminated by manual intervention. If
        this property is set to false and the job
        completes, then the extrinsic method DeleteInstance
        must be used to delete the job instead of updating
        this property."
    ::= { msvmConcreteJobEntry 4 }

msvmcjDescription OBJECT-TYPE
    SYNTAX     WtcsDisplayString
    MAX-ACCESS read-only
    STATUS     current
    DESCRIPTION
        "The Description property provides a textual
        description of the object."
    ::= { msvmConcreteJobEntry 5 }

msvmcjElapsedTime OBJECT-TYPE
    SYNTAX     DateAndTime
    MAX-ACCESS read-only
    STATUS     current
    DESCRIPTION
        "The time interval that the Job has been executing
        or the total execution time if the Job is complete.
        Note that this property is also present in the
        JobProcessingStatistics class. This class is
        necessary to capture the processing information for
        recurring Jobs, because only the 'last' run time
        can be stored in this single-valued property."
    ::= { msvmConcreteJobEntry 6 }

msvmcjElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmConcreteJobEntry 7 }

msvmcjErrorCode OBJECT-TYPE
    SYNTAX     Integer32
    MAX-ACCESS read-only
    STATUS     current
    DESCRIPTION
        "A vendor-specific error code. The value must be
        set to zero if the Job completed without error.
        Note that this property is also present in the
        JobProcessingStatistics class. This class is
        necessary to capture the processing information for
        recurring Jobs, because only the 'last' run error
        can be stored in this single-valued property."
    ::= { msvmConcreteJobEntry 8 }

msvmcjErrorDescription OBJECT-TYPE
    SYNTAX     WtcsDisplayString
    MAX-ACCESS read-only
    STATUS     current
    DESCRIPTION
        "A free-form string that contains the vendor error
        description. Note that this property is also
        present in the JobProcessingStatistics class. This
        class is necessary to capture the processing
        information for recurring Jobs, because only the
        'last' run error can be stored in this
        single-valued property."
    ::= { msvmConcreteJobEntry 9 }

msvmcjErrorSummaryDescription OBJECT-TYPE
    SYNTAX     WtcsDisplayString
    MAX-ACCESS read-only
    STATUS     current
    DESCRIPTION
        "A free-form string that contains the vendor
        summary error description. Note that this property
        is also present in the JobProcessingStatistics
        class. This class is necessary to capture the
        processing information for recurring Jobs, because
        only the 'last' run error can be stored in this
        single-valued property."
    ::= { msvmConcreteJobEntry 10 }

msvmcjHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmConcreteJobEntry 11 }

msvmcjInstallDate OBJECT-TYPE
    SYNTAX     DateAndTime
    MAX-ACCESS read-only
    STATUS     current
    DESCRIPTION
        "A datetime value that indicates when the object
        was installed. Lack of a value does not indicate
        that the object is not installed."
    ::= { msvmConcreteJobEntry 12 }

msvmcjInstanceID OBJECT-TYPE
    SYNTAX     WtcsDisplayString
    MAX-ACCESS read-only
    STATUS     current
    DESCRIPTION
        "Within the scope of the instantiating Namespace,
        InstanceID opaquely and uniquely identifies an
        instance of this class. In order to ensure
        uniqueness within the NameSpace, the value of
        InstanceID SHOULD be constructed using the
        following 'preferred' algorithm: 
        <OrgID>:<LocalID> 
        Where <OrgID> and <LocalID> are separated by a
        colon ':', and where <OrgID> must include a
        copyrighted, trademarked or otherwise unique name
        that is owned by the business entity that is
        creating or defining the InstanceID, or that is a
        registered ID that is assigned to the business
        entity by a recognized global authority. (This
        requirement is similar to the <Schema Name>_<Class
        Name> structure of Schema class names.) In
        addition, to ensure uniqueness <OrgID> must not
        contain a colon (':'). When using this algorithm,
        the first colon to appear in InstanceID must appear
        between <OrgID> and <LocalID>. 
        <LocalID> is chosen by the business entity and
        should not be re-used to identify different
        underlying (real-world) elements. If the above
        'preferred' algorithm is not used, the defining
        entity must assure that the resulting InstanceID is
        not re-used across any InstanceIDs produced by this
        or other providers for the NameSpace of this
        instance. 
        For DMTF defined instances, the 'preferred'
        algorithm must be used with the <OrgID> set to
        'CIM'."
    ::= { msvmConcreteJobEntry 13 }

msvmcjJobRunTimes OBJECT-TYPE
    SYNTAX     Gauge32
    MAX-ACCESS read-only
    STATUS     current
    DESCRIPTION
        "The number of times that the Job should be run. A
        value of 1 indicates that the Job is not recurring,
        while any non-zero value indicates a limit to the
        number of times that the Job will recur. Zero
        indicates that there is no limit to the number of
        times that the Job can be processed, but that it is
        terminated either after the UntilTime or by manual
        intervention. By default, a Job is processed once."
    ::= { msvmConcreteJobEntry 14 }

msvmcjJobState OBJECT-TYPE
    SYNTAX     INTEGER {
        new(2),
        starting(3),
        running(4),
        suspended(5),
        shuttingDown(6),
        completed(7),
        terminated(8),
        killed(9),
        exception(10),
        service(11)
    }
    MAX-ACCESS read-only
    STATUS     current
    DESCRIPTION
        "JobState is an integer enumeration that indicates
        the operational state of a Job. It can also
        indicate transitions between these states, for
        example, 'Shutting Down' and 'Starting'. Following
        is a brief description of the states: 
        New (2) indicates that the job has never been
        started. 
        Starting (3) indicates that the job is moving from
        the 'New', 'Suspended', or 'Service' states into
        the 'Running' state. 
        Running (4) indicates that the Job is running. 
        Suspended (5) indicates that the Job is stopped,
        but can be restarted in a seamless manner. 
        Shutting Down (6) indicates that the job is moving
        to a 'Completed', 'Terminated', or 'Killed' state. 
        Completed (7) indicates that the job has completed
        normally. 
        Terminated (8) indicates that the job has been
        stopped by a 'Terminate' state change request. The
        job and all its underlying processes are ended and
        can be restarted (this is job-specific) only as a
        new job. 
        Killed (9) indicates that the job has been stopped
        by a 'Kill' state change request. Underlying
        processes might have been left running, and cleanup
        might be required to free up resources. 
        Exception (10) indicates that the Job is in an
        abnormal state that might be indicative of an error
        condition. Actual status might be displayed though
        job-specific objects. 
        Service (11) indicates that the Job is in a
        vendor-specific state that supports problem
        discovery, or resolution, or both."
    ::= { msvmConcreteJobEntry 15 }

msvmcjJobStatus OBJECT-TYPE
    SYNTAX     WtcsDisplayString
    MAX-ACCESS read-only
    STATUS     current
    DESCRIPTION
        "A free-form string that represents the status of
        the job. The primary status is reflected in the
        inherited OperationalStatus property. JobStatus
        provides additional, implementation-specific
        details."
    ::= { msvmConcreteJobEntry 16 }

msvmcjLocalOrUtcTime OBJECT-TYPE
    SYNTAX     INTEGER {
        localTime(1),
        utcTime(2)
    }
    MAX-ACCESS read-only
    STATUS     current
    DESCRIPTION
        "This property indicates whether the times
        represented in the RunStartInterval and UntilTime
        properties represent local times or UTC times. Time
        values are synchronized worldwide by using the
        enumeration value 2, 'UTC Time'."
    ::= { msvmConcreteJobEntry 17 }

msvmcjName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmConcreteJobEntry 18 }

msvmcjNotify OBJECT-TYPE
    SYNTAX     WtcsDisplayString
    MAX-ACCESS read-only
    STATUS     current
    DESCRIPTION
        "The User who is to be notified upon the Job
        completion or failure."
    ::= { msvmConcreteJobEntry 19 }

msvmcjOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmConcreteJobEntry 20 }

msvmcjOtherRecoveryAction OBJECT-TYPE
    SYNTAX     WtcsDisplayString
    MAX-ACCESS read-only
    STATUS     current
    DESCRIPTION
        "A string describing the recovery action when the
        RecoveryAction property of the instance is 1
        ('Other')."
    ::= { msvmConcreteJobEntry 21 }

msvmcjOwner OBJECT-TYPE
    SYNTAX     WtcsDisplayString
    MAX-ACCESS read-only
    STATUS     current
    DESCRIPTION
        "The User that submitted the Job, or the Service or
        method name that caused the job to be created."
    ::= { msvmConcreteJobEntry 22 }

msvmcjPercentComplete OBJECT-TYPE
    SYNTAX     Integer32
    UNITS "Percent"
    MAX-ACCESS read-only
    STATUS     current
    DESCRIPTION
        "The percentage of the job that has completed at
        the time that this value is requested. Note that
        this property is also present in the
        JobProcessingStatistics class. This class is
        necessary to capture the processing information for
        recurring Jobs, because only the 'last' run data
        can be stored in this single-valued property. 
        Note that the value 101 is undefined and will be
        not be allowed in the next major revision of the
        specification."
    ::= { msvmConcreteJobEntry 23 }

msvmcjPriority OBJECT-TYPE
    SYNTAX     Gauge32
    MAX-ACCESS read-only
    STATUS     current
    DESCRIPTION
        "Indicates the urgency or importance of execution
        of the Job. The lower the number, the higher the
        priority. Note that this property is also present
        in the JobProcessingStatistics class. This class is
        necessary to capture the setting information that
        would influence the results of a job."
    ::= { msvmConcreteJobEntry 24 }

msvmcjRecoveryAction OBJECT-TYPE
    SYNTAX     INTEGER {
        unknown(0),
        other(1),
        doNotContinue(2),
        continueWithNextJob(3),
        rerunJob(4),
        runRecoveryJob(5)
    }
    MAX-ACCESS read-only
    STATUS     current
    DESCRIPTION
        "Describes the recovery action to be taken for an
        unsuccessfully run Job. The possible values are: 
        0 = 'Unknown', meaning it is unknown as to what
        recovery action to take 
        1 = 'Other', indicating that the recovery action
        will be specified in the OtherRecoveryAction
        property 
        2 = 'Do Not Continue', meaning stop the execution
        of the job and appropriately update its status 
        3 = 'Continue With Next Job', meaning continue with
        the next job in the queue 
        4 = 'Re-run Job', indicating that the job should be
        re-run 
        5 = 'Run Recovery Job', meaning run the Job
        associated using the RecoveryJob relationship. Note
        that the recovery Job must already be in the queue
        from which it will run."
    ::= { msvmConcreteJobEntry 25 }

msvmcjRunDay OBJECT-TYPE
    SYNTAX     Integer32
    MAX-ACCESS read-only
    STATUS     current
    DESCRIPTION
        "The day in the month on which the Job should be
        processed. There are two different interpretations
        for this property, depending on the value of
        DayOfWeek. In one case, RunDay defines the
        day-in-month on which the Job is processed. This
        interpretation is used when the DayOfWeek is 0. A
        positive or negative integer indicates whether the
        RunDay should be calculated from the beginning or
        end of the month. For example, 5 indicates the
        fifth day in the RunMonth and -1 indicates the last
        day in the RunMonth. 
        
        When RunDayOfWeek is not 0, RunDay is the
        day-in-month on which the Job is processed, defined
        in conjunction with RunDayOfWeek. For example, if
        RunDay is 15 and RunDayOfWeek is Saturday, then the
        Job is processed on the first Saturday on or after
        the 15th day in the RunMonth (for example, the
        third Saturday in the month). If RunDay is 20 and
        RunDayOfWeek is -Saturday, then this indicates the
        first Saturday on or before the 20th day in the
        RunMonth. If RunDay is -1 and RunDayOfWeek is
        -Sunday, then this indicates the last Sunday in the
        RunMonth."
    ::= { msvmConcreteJobEntry 26 }

msvmcjRunDayOfWeek OBJECT-TYPE
    SYNTAX     Integer32
    MAX-ACCESS read-only
    STATUS     current
    DESCRIPTION
        "A positive or negative integer used in conjunction
        with RunDay to indicate the day of the week on
        which the Job is processed. RunDayOfWeek is set to
        0 to indicate an exact day of the month, such as
        March 1. A positive integer (representing Sunday,
        Monday, ..., Saturday) means that the day of week
        is found on or after the specified RunDay. A
        negative integer (representing -Sunday, -Monday,
        ..., -Saturday) means that the day of week is found
        on or BEFORE the RunDay."
    ::= { msvmConcreteJobEntry 27 }

msvmcjRunMonth OBJECT-TYPE
    SYNTAX     INTEGER {
        january(0),
        february(1),
        march(2),
        april(3),
        may(4),
        june(5),
        july(6),
        august(7),
        september(8),
        october(9),
        november(10),
        december(11)
    }
    MAX-ACCESS read-only
    STATUS     current
    DESCRIPTION
        "The month during which the Job should be
        processed. Specify 0 for January, 1 for February,
        and so on."
    ::= { msvmConcreteJobEntry 28 }

msvmcjRunStartInterval OBJECT-TYPE
    SYNTAX     DateAndTime
    MAX-ACCESS read-only
    STATUS     current
    DESCRIPTION
        "The time interval after midnight when the Job
        should be processed. For example, 
        00000000020000.000000:000 
        indicates that the Job should be run on or after
        two o'clock, local time or UTC time (distinguished
        using the LocalOrUtcTime property."
    ::= { msvmConcreteJobEntry 29 }

msvmcjScheduledStartTime OBJECT-TYPE
    SYNTAX     DateAndTime
    MAX-ACCESS read-only
    STATUS     current
    DESCRIPTION
        "The time that the current Job is scheduled to
        start. This time can be represented by the actual
        date and time, or an interval relative to the time
        that this property is requested. A value of all
        zeroes indicates that the Job is already executing.
        The property is deprecated in lieu of the more
        expressive scheduling properties, RunMonth, RunDay,
        RunDayOfWeek, and RunStartInterval."
    ::= { msvmConcreteJobEntry 30 }

msvmcjStartTime OBJECT-TYPE
    SYNTAX     DateAndTime
    MAX-ACCESS read-only
    STATUS     current
    DESCRIPTION
        "The time that the Job was actually started. This
        time can be represented by an actual date and time,
        or by an interval relative to the time that this
        property is requested. Note that this property is
        also present in the JobProcessingStatistics class.
        This class is necessary to capture the processing
        information for recurring Jobs, because only the
        'last' run time can be stored in this single-valued
        property."
    ::= { msvmConcreteJobEntry 31 }

msvmcjStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmConcreteJobEntry 32 }

msvmcjStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmConcreteJobEntry 33 }

msvmcjTimeBeforeRemoval OBJECT-TYPE
    SYNTAX     DateAndTime
    MAX-ACCESS read-only
    STATUS     current
    DESCRIPTION
        "The amount of time that the Job is retained after
        it has finished executing, either succeeding or
        failing in that execution. The job must remain in
        existence for some period of time regardless of the
        value of the DeleteOnCompletion property. 
        The default is five minutes."
    ::= { msvmConcreteJobEntry 34 }

msvmcjTimeOfLastStateChange OBJECT-TYPE
    SYNTAX     DateAndTime
    MAX-ACCESS read-only
    STATUS     current
    DESCRIPTION
        "The date or time when the state of the Job last
        changed. If the state of the Job has not changed
        and this property is populated, then it must be set
        to a 0 interval value. If a state change was
        requested, but rejected or not yet processed, the
        property must not be updated."
    ::= { msvmConcreteJobEntry 35 }

msvmcjTimeSubmitted OBJECT-TYPE
    SYNTAX     DateAndTime
    MAX-ACCESS read-only
    STATUS     current
    DESCRIPTION
        "The time that the Job was submitted to execute. A
        value of all zeroes indicates that the owning
        element is not capable of reporting a date and
        time. Therefore, the ScheduledStartTime and
        StartTime are reported as intervals relative to the
        time their values are requested."
    ::= { msvmConcreteJobEntry 36 }

msvmcjUntilTime OBJECT-TYPE
    SYNTAX     DateAndTime
    MAX-ACCESS read-only
    STATUS     current
    DESCRIPTION
        "The time after which the Job is invalid or should
        be stopped. This time can be represented by an
        actual date and time, or by an interval relative to
        the time that this property is requested. A value
        of all nines indicates that the Job can run
        indefinitely."
    ::= { msvmConcreteJobEntry 37 }

msvmElementSettingDataTable OBJECT-TYPE
    SYNTAX     SEQUENCE OF MsvmElementSettingData
    MAX-ACCESS not-accessible
    STATUS     current
    DESCRIPTION
        "Associates a managed element with its
        configuration data. Some of the more notable
        applications of this association are its use in
        linking a virtual computer system and the logical
        devices that have been assigned to that system with
        their snapshot configuration information."
    ::= { msvmVirtualSystemManagement 3 }

msvmElementSettingDataEntry OBJECT-TYPE
    SYNTAX     MsvmElementSettingData
    MAX-ACCESS not-accessible
    STATUS     current
    DESCRIPTION
        "None"
    INDEX      { msvmesdIndex }
    ::= { msvmElementSettingDataTable 1 }

MsvmElementSettingData ::= SEQUENCE {
    msvmesdIndex Integer32,
    msvmesdIsCurrent INTEGER,
    msvmesdIsDefault INTEGER,
    msvmesdIsMaximum INTEGER,
    msvmesdIsMinimum INTEGER,
    msvmesdIsNext INTEGER,
    msvmesdManagedElement WtcsDisplayString,
    msvmesdSettingData WtcsDisplayString
}

msvmesdIndex OBJECT-TYPE
    SYNTAX     Integer32 (1..2147483647)
    MAX-ACCESS read-only
    STATUS     current
    DESCRIPTION
        "The value of this object uniquely identifies the
        instance entry for this class."
    ::= { msvmElementSettingDataEntry 1 }

msvmesdIsCurrent OBJECT-TYPE
    SYNTAX     INTEGER {
        unknown(0),
        isCurrent(1),
        isNotCurrent(2)
    }
    MAX-ACCESS read-only
    STATUS     current
    DESCRIPTION
        "An enumerated integer that indicates that the
        referenced setting is currently being used in the
        operation of the element or that this information
        is unknown. 
        For a given ManagedElement and all instances of a
        SettingData subclass, there shall be at most one
        instance of ElementSettingData which references the
        ManagedElement and an instance of the SettingData
        sub-class where there is a specified non-null,
        non-key property of the SettingData sub-class, and
        the IsMaximum property on the referencing
        ElementSettingData instance has a value of 'Is
        Maximum' or the IsMinimum property on the
        referencing ElementSettingData instance has a value
        of 'Is Minimum' and the IsCurrent property on the
        referencing ElementSettingData instance has a value
        of 'Is Current'. There shall be at most one
        instance of ElementSettingData which references a
        ManagedElement and an instance of a SettingData
        sub-class where the IsCurrent property has a value
        of 'Is Current' and the IsMinimum property does not
        have a value of 'Is Minimum' and the IsMaximum
        property does not have a value of 'Is Maximum'."
    ::= { msvmElementSettingDataEntry 2 }

msvmesdIsDefault OBJECT-TYPE
    SYNTAX     INTEGER {
        unknown(0),
        isDefault(1),
        isNotDefault(2)
    }
    MAX-ACCESS read-only
    STATUS     current
    DESCRIPTION
        "An enumerated integer that indicates that the
        referenced setting is a default setting for the
        element or that this information is unknown."
    ::= { msvmElementSettingDataEntry 3 }

msvmesdIsMaximum OBJECT-TYPE
    SYNTAX     INTEGER {
        unknown(0),
        notApplicable(1),
        isMaximum(2),
        isNotMaximum(3)
    }
    MAX-ACCESS read-only
    STATUS     current
    DESCRIPTION
        "This property affects the interpretation of all
        non-null, non-enumerated, non-binary, numeric,
        non-key properties of the associated SettingData
        instance. All other properties of the associated
        SettingData instance are not affected by this
        property. 
        Note: It is assumed that the semantics of each
        property of this set are designed to be compared
        mathematically. 
        When IsMaximum = 'Is Maxiumum', this property
        indicates that the affected property values
        specified in the associated SettingData instance
        shall define maximum setting values. 
        When IsMaximum = 'Is Not Maxiumum', this property
        indicates that the affected property values
        specified in the associated SettingData instance
        shall not define maximum setting values. 
        When IsMaximum = 'Unknown', this property indicates
        that the affected property values specified in the
        associated SettingData instance may correspond to
        maximum setting values. 
        When IsMaximum = 'Not Applicable', this property
        indicates that the affected property values
        specified in the associated SettingData instance
        shall not be interpreted with respect to whether
        each defines a maximum."
    ::= { msvmElementSettingDataEntry 4 }

msvmesdIsMinimum OBJECT-TYPE
    SYNTAX     INTEGER {
        unknown(0),
        notApplicable(1),
        isMinimum(2),
        isNotMinimum(3)
    }
    MAX-ACCESS read-only
    STATUS     current
    DESCRIPTION
        "This property affects the interpretation of all
        non-null, non-enumerated, non-binary, numeric,
        non-key properties of the associated SettingData
        instance. All other properties of the associated
        SettingData instance are not affected by this
        property. 
        Note: It is assumed that the semantics of each
        property of this set are designed to be compared
        mathematically. 
        When IsMinimum = 'Is Miniumum', this property
        indicates that the affected property values
        specified in the associated SettingData instance
        shall define minimum setting values. 
        When IsMinimum = 'Is Not Miniumum', this property
        indicates that the affected property values
        specified in the associated SettingData instance
        shall not define minimum setting values. 
        When IsMinimum = 'Unknown', this property indicates
        that the affected property values specified in the
        associated SettingData instance may correspond to
        minimum setting values. 
        When IsMinimum = 'Not Applicable', this property
        indicates that the affected property values
        specified in the associated SettingData instance
        shall not be interpreted with respect to whether
        each defines a minimum."
    ::= { msvmElementSettingDataEntry 5 }

msvmesdIsNext OBJECT-TYPE
    SYNTAX     INTEGER {
        unknown(0),
        isNext(1),
        isNotNext(2),
        isNextForSingleUse(3)
    }
    MAX-ACCESS read-only
    STATUS     current
    DESCRIPTION
        "An enumerated integer indicating whether or not
        the referenced setting is the next setting to be
        applied. For example, the application could take
        place on a re-initialization, reset,
        reconfiguration request. This could be a permanent
        setting, or a setting used only one time, as
        indicated by the flag. If it is a permanent setting
        then the setting is applied every time the managed
        element reinitializes, until this flag is manually
        reset. However, if it is single use, then the flag
        is automatically cleared after the settings are
        applied. Also note that if this flag is specified
        (i.e. set to value other than 'Unknown'), then this
        takes precedence over any SettingData that may have
        been specified as Default. For example: If the
        managed element is a computer system, and the value
        of this flag is 'Is Next', then the setting will be
        effective next time the system resets. And, unless
        this flag is changed, it will persist for
        subsequent system resets. However, if this flag is
        set to 'Is Next For Single Use', then this setting
        will only be used once and the flag would be reset
        after that to 'Is Not Next'. So, in the above
        example, if the system reboots in a quick
        succession, the setting will not be used at the
        second reboot."
    ::= { msvmElementSettingDataEntry 6 }

msvmesdManagedElement OBJECT-TYPE
    SYNTAX     WtcsDisplayString
    MAX-ACCESS read-only
    STATUS     current
    DESCRIPTION
        "The managed element."
    ::= { msvmElementSettingDataEntry 7 }

msvmesdSettingData OBJECT-TYPE
    SYNTAX     WtcsDisplayString
    MAX-ACCESS read-only
    STATUS     current
    DESCRIPTION
        "The SettingData object that is associated with the
        element."
    ::= { msvmElementSettingDataEntry 8 }

msvmErrorTable OBJECT-TYPE
    SYNTAX     SEQUENCE OF MsvmError
    MAX-ACCESS not-accessible
    STATUS     current
    DESCRIPTION
        "A specialized class that contains information
        about the severity, cause, recommended actions and
        other data related to the failure of a CIM
        Operation."
    ::= { msvmVirtualSystemManagement 4 }

msvmErrorEntry OBJECT-TYPE
    SYNTAX     MsvmError
    MAX-ACCESS not-accessible
    STATUS     current
    DESCRIPTION
        "None"
    INDEX      { msvmErrorIndex }
    ::= { msvmErrorTable 1 }

MsvmError ::= SEQUENCE {
    msvmErrorIndex Integer32,
    msvmErrorCIMStatusCode INTEGER,
    msvmErrorCIMStatusCodeDescr WtcsDisplayString,
    msvmErrorErrorSource WtcsDisplayString,
    msvmErrorErrorSourceFormat INTEGER,
    msvmErrorErrorType INTEGER,
    msvmErrorMessage WtcsDisplayString,
    msvmErrorMessageArguments WtcsDisplayString,
    msvmErrorMessageID WtcsDisplayString,
    msvmErrorOtherErrorSourceFormat WtcsDisplayString,
    msvmErrorOtherErrorType WtcsDisplayString,
    msvmErrorOwningEntity WtcsDisplayString,
    msvmErrorPerceivedSeverity INTEGER,
    msvmErrorProbableCause Integer32,
    msvmErrorProbableCauseDescr WtcsDisplayString,
    msvmErrorRecommendedActions WtcsDisplayString
}

msvmErrorIndex OBJECT-TYPE
    SYNTAX     Integer32 (1..2147483647)
    MAX-ACCESS read-only
    STATUS     current
    DESCRIPTION
        "The value of this object uniquely identifies the
        instance entry for this class."
    ::= { msvmErrorEntry 1 }

msvmErrorCIMStatusCode OBJECT-TYPE
    SYNTAX     INTEGER {
        cimERRFAILED(1),
        cimERRACCESSDENIED(2),
        cimERRINVALIDNAMESPACE(3),
        cimERRINVALIDPARAMETER(4),
        cimERRINVALIDCLASS(5),
        cimERRNOTFOUND(6),
        cimERRNOTSUPPORTED(7),
        cimERRCLASSHASCHILDREN(8),
        cimERRCLASSHASINSTANCES(9),
        cimERRINVALIDSUPERCLASS(10),
        cimERRALREADYEXISTS(11),
        cimERRNOSUCHPROPERTY(12),
        cimERRTYPEMISMATCH(13),
        cimERRQUERYLANGUAGENOTSUPPORTED(14),
        cimERRINVALIDQUERY(15),
        cimERRMETHODNOTAVAILABLE(16),
        cimERRMETHODNOTFOUND(17),
        cimERRUNEXPECTEDRESPONSE(18),
        cimERRINVALIDRESPONSEDESTINATION(19),
        cimERRNAMESPACENOTEMPTY(20)
    }
    MAX-ACCESS read-only
    STATUS     current
    DESCRIPTION
        "The CIM status code that characterizes this
        instance. This property defines the status codes
        that may be return by a conforming CIM Server or
        Listener. Note that not all status codes are valid
        for each operation. The specification for each
        operation should define the status codes that may
        be returned by that operation."
    ::= { msvmErrorEntry 2 }

msvmErrorCIMStatusCodeDescr OBJECT-TYPE
    SYNTAX     WtcsDisplayString
    MAX-ACCESS read-only
    STATUS     current
    DESCRIPTION
        "A free-form string containing a human-readable
        description of CIMStatusCode. This description may
        extend, but must be consistent with, the definition
        of CIMStatusCode. This property is inherited from
        CIM_Error."
    ::= { msvmErrorEntry 3 }

msvmErrorErrorSource OBJECT-TYPE
    SYNTAX     WtcsDisplayString
    MAX-ACCESS read-only
    STATUS     current
    DESCRIPTION
        "The identifying information of the entity (the
        instance) generating the error. If this entity is
        modeled in the CIM Schema, this property contains
        the path of the instance encoded as a string
        parameter. If not modeled, the property contains
        some identifying string that names the entity that
        generated the error. The path or identifying string
        is formatted per the ErrorSourceFormat property.
        This property is inherited from CIM_Error."
    ::= { msvmErrorEntry 4 }

msvmErrorErrorSourceFormat OBJECT-TYPE
    SYNTAX     INTEGER {
        unknown(0),
        other(1),
        cimobjectHandle(2)
    }
    MAX-ACCESS read-only
    STATUS     current
    DESCRIPTION
        "The format of the ErrorSource property is
        interpretable based on the value of this property.
        Values are defined as: 0 - Unknown. The format is
        unknown or not meaningfully interpretable by a CIM
        client application. 1 - Other. The format is
        defined by the value of the OtherErrorSourceFormat
        property. 2 - CIMObjectHandle. A CIM Object Handle,
        encoded using the MOF syntax defined for the
        objectHandle non-terminal, is used to identify the
        entity. This property is inherited from CIM_Error
        and is set to 0."
    ::= { msvmErrorEntry 5 }

msvmErrorErrorType OBJECT-TYPE
    SYNTAX     INTEGER {
        unknown(0),
        other(1),
        communicationsError(2),
        qualityofServiceError(3),
        softwareError(4),
        hardwareError(5),
        environmentalError(6),
        securityError(7),
        oversubscriptionError(8),
        unavailableResourceError(9),
        unsupportedOperationError(10)
    }
    MAX-ACCESS read-only
    STATUS     current
    DESCRIPTION
        "Primary classification of the error."
    ::= { msvmErrorEntry 6 }

msvmErrorMessage OBJECT-TYPE
    SYNTAX     WtcsDisplayString
    MAX-ACCESS read-only
    STATUS     current
    DESCRIPTION
        "The formatted message. This message is constructed
        by applying the dynamic content of the message,
        described in MessageArguments, to the format string
        uniquely identified, within the scope of the
        OwningEntity, by MessageID. This property is
        inherited from CIM_Error."
    ::= { msvmErrorEntry 7 }

msvmErrorMessageArguments OBJECT-TYPE
    SYNTAX     WtcsDisplayString
    MAX-ACCESS read-only
    STATUS     current
    DESCRIPTION
        "An array containing the dynamic content of the
        message. This property is inherited from
        CIM_Error."
    ::= { msvmErrorEntry 8 }

msvmErrorMessageID OBJECT-TYPE
    SYNTAX     WtcsDisplayString
    MAX-ACCESS read-only
    STATUS     current
    DESCRIPTION
        "An opaque string that uniquely identifies, within
        the scope of the OwningEntity, the format of the
        message. This property is inherited from
        CIM_Error."
    ::= { msvmErrorEntry 9 }

msvmErrorOtherErrorSourceFormat OBJECT-TYPE
    SYNTAX     WtcsDisplayString
    MAX-ACCESS read-only
    STATUS     current
    DESCRIPTION
        "A string defining 'Other' values for
        ErrorSourceFormat. This value must be set to a non
        NULL value when ErrorSourceFormat is set to a value
        of 1 ('Other'). For all other values of
        ErrorSourceFormat, the value of this string must be
        set to NULL. This property is inherited from
        CIM_Error."
    ::= { msvmErrorEntry 10 }

msvmErrorOtherErrorType OBJECT-TYPE
    SYNTAX     WtcsDisplayString
    MAX-ACCESS read-only
    STATUS     current
    DESCRIPTION
        "A free-form string describing the ErrorType when
        1, 'Other', is specified as the ErrorType. This
        property is inherited from CIM_Error."
    ::= { msvmErrorEntry 11 }

msvmErrorOwningEntity OBJECT-TYPE
    SYNTAX     WtcsDisplayString
    MAX-ACCESS read-only
    STATUS     current
    DESCRIPTION
        "A string that uniquely identifies the entity that
        owns the definition of the format of the message
        described in this instance. OwningEntitymust
        include a copyrighted, trademarked, or otherwise
        unique name that is owned by the business entity or
        standards body defining the format. This property
        is inherited from CIM_Error."
    ::= { msvmErrorEntry 12 }

msvmErrorPerceivedSeverity OBJECT-TYPE
    SYNTAX     INTEGER {
        unknown(0),
        low(2),
        medium(3),
        high(4),
        fatal(5)
    }
    MAX-ACCESS read-only
    STATUS     current
    DESCRIPTION
        "An enumerated value that describes the severity of
        the error from the notifier's point of view: 2 -
        Low should be used for noncritical issues such as
        invalid parameters, incorrect usage, unsupported
        functionality. 3 - Medium should be used to
        indicate action is needed, but the situation is not
        serious at this time. 4 - High should be used to
        indicate action is needed now. 5 - Fatal should be
        used to indicate a loss of data or unrecoverable
        system or service failure. This property is
        inherited from CIM_Error."
    ::= { msvmErrorEntry 13 }

msvmErrorProbableCause OBJECT-TYPE
    SYNTAX     Integer32
    MAX-ACCESS read-only
    STATUS     current
    DESCRIPTION
        "An enumerated value that describes the probable
        cause of the error. This property is inherited from
        CIM_Error."
    ::= { msvmErrorEntry 14 }

msvmErrorProbableCauseDescr OBJECT-TYPE
    SYNTAX     WtcsDisplayString
    MAX-ACCESS read-only
    STATUS     current
    DESCRIPTION
        "A free-form string describing the probable cause
        of the error. This property is inherited from
        CIM_Error."
    ::= { msvmErrorEntry 15 }

msvmErrorRecommendedActions OBJECT-TYPE
    SYNTAX     WtcsDisplayString
    MAX-ACCESS read-only
    STATUS     current
    DESCRIPTION
        "A free-form string describing recommended actions
        to take to resolve the error. This property is
        inherited from CIM_Error."
    ::= { msvmErrorEntry 16 }

msvmHostedDependencyTable OBJECT-TYPE
    SYNTAX     SEQUENCE OF MsvmHostedDependency
    MAX-ACCESS not-accessible
    STATUS     current
    DESCRIPTION
        "Associates a virtual computer system instance with
        the computer system object representing the
        physical, hosting system."
    ::= { msvmVirtualSystemManagement 5 }

msvmHostedDependencyEntry OBJECT-TYPE
    SYNTAX     MsvmHostedDependency
    MAX-ACCESS not-accessible
    STATUS     current
    DESCRIPTION
        "None"
    INDEX      { msvmhdIndex }
    ::= { msvmHostedDependencyTable 1 }

MsvmHostedDependency ::= SEQUENCE {
    msvmhdIndex Integer32,
    msvmhdAntecedent WtcsDisplayString,
    msvmhdDependent WtcsDisplayString
}

msvmhdIndex OBJECT-TYPE
    SYNTAX     Integer32 (1..2147483647)
    MAX-ACCESS read-only
    STATUS     current
    DESCRIPTION
        "The value of this object uniquely identifies the
        instance entry for this class."
    ::= { msvmHostedDependencyEntry 1 }

msvmhdAntecedent OBJECT-TYPE
    SYNTAX     WtcsDisplayString
    MAX-ACCESS read-only
    STATUS     current
    DESCRIPTION
        "Antecedent represents the independent object in
        this association."
    ::= { msvmHostedDependencyEntry 2 }

msvmhdDependent OBJECT-TYPE
    SYNTAX     WtcsDisplayString
    MAX-ACCESS read-only
    STATUS     current
    DESCRIPTION
        "Dependent represents the object that is dependent
        on the Antecedent."
    ::= { msvmHostedDependencyEntry 3 }

msvmHostedServiceTable OBJECT-TYPE
    SYNTAX     SEQUENCE OF MsvmHostedService
    MAX-ACCESS not-accessible
    STATUS     current
    DESCRIPTION
        "Associates a service with its hosting computer
        system."
    ::= { msvmVirtualSystemManagement 6 }

msvmHostedServiceEntry OBJECT-TYPE
    SYNTAX     MsvmHostedService
    MAX-ACCESS not-accessible
    STATUS     current
    DESCRIPTION
        "None"
    INDEX      { msvmhsIndex }
    ::= { msvmHostedServiceTable 1 }

MsvmHostedService ::= SEQUENCE {
    msvmhsIndex Integer32,
    msvmhsAntecedent WtcsDisplayString,
    msvmhsDependent WtcsDisplayString
}

msvmhsIndex OBJECT-TYPE
    SYNTAX     Integer32 (1..2147483647)
    MAX-ACCESS read-only
    STATUS     current
    DESCRIPTION
        "The value of this object uniquely identifies the
        instance entry for this class."
    ::= { msvmHostedServiceEntry 1 }

msvmhsAntecedent OBJECT-TYPE
    SYNTAX     WtcsDisplayString
    MAX-ACCESS read-only
    STATUS     current
    DESCRIPTION
        "Antecedent represents the independent object in
        this association."
    ::= { msvmHostedServiceEntry 2 }

msvmhsDependent OBJECT-TYPE
    SYNTAX     WtcsDisplayString
    MAX-ACCESS read-only
    STATUS     current
    DESCRIPTION
        "Dependent represents the object that is dependent
        on the Antecedent."
    ::= { msvmHostedServiceEntry 3 }

msvmServiceAffectsElementTable OBJECT-TYPE
    SYNTAX     SEQUENCE OF MsvmServiceAffectsElement
    MAX-ACCESS not-accessible
    STATUS     current
    DESCRIPTION
        "Associates a virtual computer system instance with
        the management service that controls its state."
    ::= { msvmVirtualSystemManagement 7 }

msvmServiceAffectsElementEntry OBJECT-TYPE
    SYNTAX     MsvmServiceAffectsElement
    MAX-ACCESS not-accessible
    STATUS     current
    DESCRIPTION
        "None"
    INDEX      { msvmsaeIndex }
    ::= { msvmServiceAffectsElementTable 1 }

MsvmServiceAffectsElement ::= SEQUENCE {
    msvmsaeIndex Integer32,
    msvmsaeAffectedElement WtcsDisplayString,
    msvmsaeAffectingElement WtcsDisplayString,
    msvmsaeElementEffects INTEGER,
    msvmsaeOtherElementEffectsDescr WtcsDisplayString
}

msvmsaeIndex OBJECT-TYPE
    SYNTAX     Integer32 (1..2147483647)
    MAX-ACCESS read-only
    STATUS     current
    DESCRIPTION
        "The value of this object uniquely identifies the
        instance entry for this class."
    ::= { msvmServiceAffectsElementEntry 1 }

msvmsaeAffectedElement OBJECT-TYPE
    SYNTAX     WtcsDisplayString
    MAX-ACCESS read-only
    STATUS     current
    DESCRIPTION
        "The Managed Element that is affected by the
        Service."
    ::= { msvmServiceAffectsElementEntry 2 }

msvmsaeAffectingElement OBJECT-TYPE
    SYNTAX     WtcsDisplayString
    MAX-ACCESS read-only
    STATUS     current
    DESCRIPTION
        "The Service that is affecting the ManagedElement."
    ::= { msvmServiceAffectsElementEntry 3 }

msvmsaeElementEffects OBJECT-TYPE
    SYNTAX     INTEGER {
        unknown(0),
        other(1),
        exclusiveUse(2),
        performanceImpact(3),
        elementIntegrity(4),
        manages(5),
        consumes(6),
        enhancesIntegrity(7),
        degradesIntegrity(8),
        enhancesPerformance(9),
        degradesPerformance(10)
    }
    MAX-ACCESS read-only
    STATUS     current
    DESCRIPTION
        "An enumeration that describes the effect on the
        ManagedElement. This array corresponds to the
        OtherElementEffectsDescriptions array, where the
        latter provides details that are related to the
        high-level effects enumerated by this property.
        Additional detail is required if the ElementEffects
        array contains the value 1 (Other). The values are
        defined as follows: 
        - Exclusive Use (2): No other Service may have this
        association to the element. 
        - Performance Impact (3): Deprecated in favor of
        'Consumes', 'Enhances Performance', or 'Degrades
        Performance'. Execution of the Service may enhance
        or degrade the performance of the element. This may
        be as a side-effect of execution or as an intended
        consequence of methods provided by the Service. 
        - Element Integrity (4): Deprecated in favor of
        'Consumes', 'Enhances Integrity', or 'Degrades
        Integrity'. Execution of the Service may enhance or
        degrade the integrity of the element. This may be
        as a side-effect of execution or as an intended
        consequence of methods provided by the Service. 
        - Manages (5): The Service manages the element. 
        - Consumes (6): Execution of the Service consumes
        some or all of the associated element as a
        consequence of running the Service. For example,
        the Service may consume CPU cycles, which may
        affect performance, or Storage which may affect
        both performance and integrity. (For instance, the
        lack of free storage can degrade integrity by
        reducing the ability to save state. ) 'Consumes'
        may be used alone or in conjunction with other
        values, in particular, 'Degrades Performance' and
        'Degrades Integrity'. 
        'Manages' and not 'Consumes' should be used to
        reflect allocation services that may be provided by
        a Service. 
        - Enhances Integrity (7): The Service may enhance
        integrity of the associated element. 
        - Degrades Integrity (8): The Service may degrade
        integrity of the associated element. 
        - Enhances Performance (9): The Service may enhance
        performance of the associated element. 
        - Degrades Performance (10): The Service may
        degrade performance of the associated element."
    ::= { msvmServiceAffectsElementEntry 4 }

msvmsaeOtherElementEffectsDescr OBJECT-TYPE
    SYNTAX     WtcsDisplayString
    MAX-ACCESS read-only
    STATUS     current
    DESCRIPTION
        "Provides details for the effect at the
        corresponding array position in ElementEffects.
        This information is required if ElementEffects
        contains the value 1 (Other)."
    ::= { msvmServiceAffectsElementEntry 5 }

msvmSettingsDefineStateTable OBJECT-TYPE
    SYNTAX     SEQUENCE OF MsvmSettingsDefineState
    MAX-ACCESS not-accessible
    STATUS     current
    DESCRIPTION
        "Associates a virtual system and its devices with
        an instance of Msvm_ComputerSystem."
    ::= { msvmVirtualSystemManagement 8 }

msvmSettingsDefineStateEntry OBJECT-TYPE
    SYNTAX     MsvmSettingsDefineState
    MAX-ACCESS not-accessible
    STATUS     current
    DESCRIPTION
        "None"
    INDEX      { msvmsdsIndex }
    ::= { msvmSettingsDefineStateTable 1 }

MsvmSettingsDefineState ::= SEQUENCE {
    msvmsdsIndex Integer32,
    msvmsdsManagedElement WtcsDisplayString,
    msvmsdsSettingData WtcsDisplayString
}

msvmsdsIndex OBJECT-TYPE
    SYNTAX     Integer32 (1..2147483647)
    MAX-ACCESS read-only
    STATUS     current
    DESCRIPTION
        "The value of this object uniquely identifies the
        instance entry for this class."
    ::= { msvmSettingsDefineStateEntry 1 }

msvmsdsManagedElement OBJECT-TYPE
    SYNTAX     WtcsDisplayString
    MAX-ACCESS read-only
    STATUS     current
    DESCRIPTION
        "The managed element."
    ::= { msvmSettingsDefineStateEntry 2 }

msvmsdsSettingData OBJECT-TYPE
    SYNTAX     WtcsDisplayString
    MAX-ACCESS read-only
    STATUS     current
    DESCRIPTION
        "The SettingData object that provides additional
        information about the current state and
        configuration of the ManagedElement."
    ::= { msvmSettingsDefineStateEntry 3 }

msvmVirtualSystemMgtServiceTable OBJECT-TYPE
    SYNTAX     SEQUENCE OF MsvmVirtualSysManagementService
    MAX-ACCESS not-accessible
    STATUS     current
    DESCRIPTION
        "Represents the virtualization service present on a
        single host system."
    ::= { msvmVirtualSystemManagement 9 }

msvmVirtualSystemMgtServiceEntry OBJECT-TYPE
    SYNTAX     MsvmVirtualSysManagementService
    MAX-ACCESS not-accessible
    STATUS     current
    DESCRIPTION
        "None"
    INDEX      { msvmvsmsIndex }
    ::= { msvmVirtualSystemMgtServiceTable 1 }

MsvmVirtualSysManagementService ::= SEQUENCE {
    msvmvsmsvIndex Integer32,
    msvmvsmsvCaption WtcsDisplayString,
    msvmvsmsvCreationClassName WtcsDisplayString,
    msvmvsmsvDescription WtcsDisplayString,
    msvmvsmsvElementName WtcsDisplayString,
    msvmvsmsvEnabledDefault INTEGER,
    msvmvsmsvEnabledState INTEGER,
    msvmvsmsvHealthState INTEGER,
    msvmvsmsvInstallDate DateAndTime,
    msvmvsmsvName WtcsDisplayString,
    msvmvsmsvOperationalStatus INTEGER,
    msvmvsmsvOtherEnabledState WtcsDisplayString,
    msvmvsmsvPrimaryOwnerContact WtcsDisplayString,
    msvmvsmsvPrimaryOwnerName WtcsDisplayString,
    msvmvsmsvRequestedState INTEGER,
    msvmvsmsvStartMode WtcsDisplayString,
    msvmvsmsvStarted TruthValue,
    msvmvsmsvStatus WtcsDisplayString,
    msvmvsmsvStatusDescriptions WtcsDisplayString,
    msvmvsmsvSystemCreationClassName WtcsDisplayString,
    msvmvsmsvSystemName WtcsDisplayString,
    msvmvsmsvTimeOfLastStateChange DateAndTime
}

msvmvsmsvIndex OBJECT-TYPE
    SYNTAX     Integer32 (1..2147483647)
    MAX-ACCESS read-only
    STATUS     current
    DESCRIPTION
        "The value of this object uniquely identifies the
        instance entry for this class."
    ::= { msvmVirtualSystemMgtServiceEntry 1 }

msvmvsmsvCaption OBJECT-TYPE
    SYNTAX     WtcsDisplayString (SIZE (0..64))
    MAX-ACCESS read-only
    STATUS     current
    DESCRIPTION
        "The Caption property is a short textual
        description (one- line string) of the object."
    ::= { msvmVirtualSystemMgtServiceEntry 2 }

msvmvsmsvCreationClassName OBJECT-TYPE
    SYNTAX     WtcsDisplayString (SIZE (0..256))
    MAX-ACCESS read-only
    STATUS     current
    DESCRIPTION
        "CreationClassName indicates the name of the class
        or the subclass that is used in the creation of an
        instance. When used with the other key properties
        of this class, this property allows all instances
        of this class and its subclasses to be uniquely
        identified."
    ::= { msvmVirtualSystemMgtServiceEntry 3 }

msvmvsmsvDescription OBJECT-TYPE
    SYNTAX     WtcsDisplayString
    MAX-ACCESS read-only
    STATUS     current
    DESCRIPTION
        "The Description property provides a textual
        description of the object."
    ::= { msvmVirtualSystemMgtServiceEntry 4 }

msvmvsmsvElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmVirtualSystemMgtServiceEntry 5 }

msvmvsmsvEnabledDefault OBJECT-TYPE
    SYNTAX     INTEGER {
        enabled(2),
        disabled(3),
        notApplicable(5),
        enabledbutOffline(6),
        noDefault(7)
    }
    MAX-ACCESS read-only
    STATUS     current
    DESCRIPTION
        "An enumerated value indicating an administrator's
        default or startup configuration for the Enabled
        State of an element. By default, the element is
        'Enabled' (value=2)."
    ::= { msvmVirtualSystemMgtServiceEntry 6 }

msvmvsmsvEnabledState OBJECT-TYPE
    SYNTAX     INTEGER {
        unknown(0),
        other(1),
        enabled(2),
        disabled(3),
        shuttingDown(4),
        notApplicable(5),
        enabledbutOffline(6),
        inTest(7),
        deferred(8),
        quiesce(9),
        starting(10)
    }
    MAX-ACCESS read-only
    STATUS     current
    DESCRIPTION
        "EnabledState is an integer enumeration that
        indicates the enabled and disabled states of an
        element. It can also indicate the transitions
        between these requested states. For example,
        shutting down (value=4) and starting (value=10) are
        transient states between enabled and disabled. The
        following text briefly summarizes the various
        enabled and disabled states: 
        Enabled (2) indicates that the element is or could
        be executing commands, will process any queued
        commands, and queues new requests. 
        Disabled (3) indicates that the element will not
        execute commands and will drop any new requests. 
        Shutting Down (4) indicates that the element is in
        the process of going to a Disabled state. 
        Not Applicable (5) indicates the element does not
        support being enabled or disabled. 
        Enabled but Offline (6) indicates that the element
        might be completing commands, and will drop any new
        requests. 
        Test (7) indicates that the element is in a test
        state. 
        Deferred (8) indicates that the element might be
        completing commands, but will queue any new
        requests. 
        Quiesce (9) indicates that the element is enabled
        but in a restricted mode. The behavior of the
        element is similar to the Enabled state, but it
        processes only a restricted set of commands. All
        other requests are queued. 
        Starting (10) indicates that the element is in the
        process of going to an Enabled state. New requests
        are queued."
    ::= { msvmVirtualSystemMgtServiceEntry 7 }

msvmvsmsvHealthState OBJECT-TYPE
    SYNTAX     INTEGER {
        unknown(0),
        ok(5),
        degradedWarning(10),
        minorfailure(15),
        majorfailure(20),
        criticalfailure(25),
        nonrecoverableerror(30)
    }
    MAX-ACCESS read-only
    STATUS     current
    DESCRIPTION
        "Indicates the current health of the element. This
        attribute expresses the health of this element but
        not necessarily that of its subcomponents. The
        possible values are 0 to 30, where 5 means the
        element is entirely healthy and 30 means the
        element is completely non-functional. The following
        continuum is defined: 
        'Non-recoverable Error' (30) - The element has
        completely failed, and recovery is not possible.
        All functionality provided by this element has been
        lost. 
        'Critical Failure' (25) - The element is
        non-functional and recovery might not be possible. 
        'Major Failure' (20) - The element is failing. It
        is possible that some or all of the functionality
        of this component is degraded or not working. 
        'Minor Failure' (15) - All functionality is
        available but some might be degraded. 
        'Degraded/Warning' (10) - The element is in working
        order and all functionality is provided. However,
        the element is not working to the best of its
        abilities. For example, the element might not be
        operating at optimal performance or it might be
        reporting recoverable errors. 
        'OK' (5) - The element is fully functional and is
        operating within normal operational parameters and
        without error. 
        'Unknown' (0) - The implementation cannot report on
        HealthState at this time. 
        DMTF has reserved the unused portion of the
        continuum for additional HealthStates in the
        future."
    ::= { msvmVirtualSystemMgtServiceEntry 8 }

msvmvsmsvInstallDate OBJECT-TYPE
    SYNTAX     DateAndTime
    MAX-ACCESS read-only
    STATUS     current
    DESCRIPTION
        "A datetime value that indicates when the object
        was installed. Lack of a value does not indicate
        that the object is not installed."
    ::= { msvmVirtualSystemMgtServiceEntry 9 }

msvmvsmsvName OBJECT-TYPE
    SYNTAX     WtcsDisplayString (SIZE (0..1024))
    MAX-ACCESS read-only
    STATUS     current
    DESCRIPTION
        "The Name property defines the label by which the
        object is known. When subclassed, the Name property
        can be overridden to be a Key property."
    ::= { msvmVirtualSystemMgtServiceEntry 10 }

msvmvsmsvOperationalStatus OBJECT-TYPE
    SYNTAX     INTEGER {
        unknown(0),
        other(1),
        ok(2),
        degraded(3),
        stressed(4),
        predictiveFailure(5),
        error(6),
        nonRecoverableError(7),
        starting(8),
        stopping(9),
        stopped(10),
        inService(11),
        noContact(12),
        lostCommunication(13),
        aborted(14),
        dormant(15),
        supportingEntityinError(16),
        completed(17),
        powerMode(18)
    }
    MAX-ACCESS read-only
    STATUS     current
    DESCRIPTION
        "Indicates the current statuses of the element.
        Various operational statuses are defined. Many of
        the enumeration's values are self-explanatory.
        However, a few are not and are described here in
        more detail. 
        'Stressed' indicates that the element is
        functioning, but needs attention. Examples of
        'Stressed' states are overload, overheated, and so
        on. 
        'Predictive Failure' indicates that an element is
        functioning nominally but predicting a failure in
        the near future. 
        'In Service' describes an element being configured,
        maintained, cleaned, or otherwise administered. 
        'No Contact' indicates that the monitoring system
        has knowledge of this element, but has never been
        able to establish communications with it. 
        'Lost Communication' indicates that the
        ManagedSystem Element is known to exist and has
        been contacted successfully in the past, but is
        currently unreachable. 
        'Stopped' and 'Aborted' are similar, although the
        former implies a clean and orderly stop, while the
        latter implies an abrupt stop where the state and
        configuration of the element might need to be
        updated. 
        'Dormant' indicates that the element is inactive or
        quiesced. 
        'Supporting Entity in Error' indicates that this
        element might be 'OK' but that another element, on
        which it is dependent, is in error. An example is a
        network service or endpoint that cannot function
        due to lower-layer networking problems. 
        'Completed' indicates that the element has
        completed its operation. This value should be
        combined with either OK, Error, or Degraded so that
        a client can tell if the complete operation
        Completed with OK (passed), Completed with Error
        (failed), or Completed with Degraded (the operation
        finished, but it did not complete OK or did not
        report an error). 
        'Power Mode' indicates that the element has
        additional power model information contained in the
        Associated PowerManagementService association. 
        OperationalStatus replaces the Status property on
        ManagedSystemElement to provide a consistent
        approach to enumerations, to address implementation
        needs for an array property, and to provide a
        migration path from today's environment to the
        future. This change was not made earlier because it
        required the deprecated qualifier. Due to the
        widespread use of the existing Status property in
        management applications, it is strongly recommended
        that providers or instrumentation provide both the
        Status and OperationalStatus properties. Further,
        the first value of OperationalStatus should contain
        the primary status for the element. When
        instrumented, Status (because it is single-valued)
        should also provide the primary status of the
        element."
    ::= { msvmVirtualSystemMgtServiceEntry 11 }

msvmvsmsvOtherEnabledState OBJECT-TYPE
    SYNTAX     WtcsDisplayString
    MAX-ACCESS read-only
    STATUS     current
    DESCRIPTION
        "A string that describes the enabled or disabled
        state of the element when the EnabledState property
        is set to 1 ('Other'). This property must be set to
        null when EnabledState is any value other than 1."
    ::= { msvmVirtualSystemMgtServiceEntry 12 }

msvmvsmsvPrimaryOwnerContact OBJECT-TYPE
    SYNTAX     WtcsDisplayString (SIZE (0..256))
    MAX-ACCESS read-only
    STATUS     current
    DESCRIPTION
        "A string that provides information on how the
        primary owner of the Service can be reached (for
        example, phone number, e-mail address, and so on)."
    ::= { msvmVirtualSystemMgtServiceEntry 13 }

msvmvsmsvPrimaryOwnerName OBJECT-TYPE
    SYNTAX     WtcsDisplayString (SIZE (0..64))
    MAX-ACCESS read-only
    STATUS     current
    DESCRIPTION
        "The name of the primary owner for the service, if
        one is defined. The primary owner is the initial
        support contact for the Service."
    ::= { msvmVirtualSystemMgtServiceEntry 14 }

msvmvsmsvRequestedState OBJECT-TYPE
    SYNTAX     INTEGER {
        enabled(2),
        disabled(3),
        shutDown(4),
        noChange(5),
        offline(6),
        test(7),
        deferred(8),
        quiesce(9),
        reboot(10),
        reset(11),
        notApplicable(12)
    }
    MAX-ACCESS read-only
    STATUS     current
    DESCRIPTION
        "RequestedState is an integer enumeration that
        indicates the last requested or desired state for
        the element. The actual state of the element is
        represented by EnabledState. This property is
        provided to compare the last requested and current
        enabled or disabled states. Note that when
        EnabledState is set to 5 ('Not Applicable'), then
        this property has no meaning. By default, the
        RequestedState of the element is 5 ('No Change').
        Refer to the EnabledState property description for
        explanations of the values in the RequestedState
        enumeration. 
        
        It should be noted that there are two new values in
        RequestedState that build on the statuses of
        EnabledState. These are 'Reboot' (10) and 'Reset'
        (11). Reboot refers to doing a 'Shut Down' and then
        moving to an 'Enabled' state. Reset indicates that
        the element is first 'Disabled' and then 'Enabled'.
        The distinction between requesting 'Shut Down' and
        'Disabled' should also be noted. Shut Down requests
        an orderly transition to the Disabled state, and
        might involve removing power, to completely erase
        any existing state. The Disabled state requests an
        immediate disabling of the element, such that it
        will not execute or accept any commands or
        processing requests. 
        
        This property is set as the result of a method
        invocation (such as Start or StopService on
        CIM_Service), or can be overridden and defined as
        WRITEable in a subclass. The method approach is
        considered superior to a WRITEable property,
        because it allows an explicit invocation of the
        operation and the return of a result code. 
        
        A particular instance of EnabledLogicalElement
        might not support RequestedStateChange. If this
        occurs, the value 12 ('Not Applicable') is used."
    ::= { msvmVirtualSystemMgtServiceEntry 15 }

msvmvsmsvStartMode OBJECT-TYPE
    SYNTAX     WtcsDisplayString (SIZE (0..10))
    MAX-ACCESS read-only
    STATUS     current
    DESCRIPTION
        "Note: The use of this element is deprecated in
        lieu of the EnabledDefault property that is
        inherited from EnabledLogicalElement. The
        EnabledLogicalElement addresses the same semantics.
        The change to a uint16 data type was discussed when
        CIM V2.0 was defined. However, existing V1.0
        implementations used the string property. To remain
        compatible with those implementations, StartMode
        was grandfathered into the schema. Use of the
        deprecated qualifier allows the maintenance of the
        existing property but also permits an improved,
        clarified definition using EnabledDefault. 
        Deprecated description: StartMode is a string value
        that indicates whether the Service is automatically
        started by a System, an Operating System, and so
        on, or is started only upon request."
    ::= { msvmVirtualSystemMgtServiceEntry 16 }

msvmvsmsvStarted OBJECT-TYPE
    SYNTAX     TruthValue
    MAX-ACCESS read-only
    STATUS     current
    DESCRIPTION
        "Started is a Boolean that indicates whether the
        Service has been started (TRUE), or stopped
        (FALSE)."
    ::= { msvmVirtualSystemMgtServiceEntry 17 }

msvmvsmsvStatus OBJECT-TYPE
    SYNTAX     WtcsDisplayString (SIZE (0..10))
    MAX-ACCESS read-only
    STATUS     current
    DESCRIPTION
        "A string indicating the current status of the
        object. Various operational and non-operational
        statuses are defined. This property is deprecated
        in lieu of OperationalStatus, which includes the
        same semantics in its enumeration. This change is
        made for 3 reasons: 
        1) Status is more correctly defined as an array.
        This definition overcomes the limitation of
        describing status using a single value, when it is
        really a multi-valued property (for example, an
        element might be OK AND Stopped. 
        2) A MaxLen of 10 is too restrictive and leads to
        unclear enumerated values. 
        3) The change to a uint16 data type was discussed
        when CIM V2.0 was defined. However, existing V1.0
        implementations used the string property and did
        not want to modify their code. Therefore, Status
        was grandfathered into the Schema. Use of the
        deprecated qualifier allows the maintenance of the
        existing property, but also permits an improved
        definition using OperationalStatus."
    ::= { msvmVirtualSystemMgtServiceEntry 18 }

msvmvsmsvStatusDescriptions OBJECT-TYPE
    SYNTAX     WtcsDisplayString
    MAX-ACCESS read-only
    STATUS     current
    DESCRIPTION
        "Strings describing the various OperationalStatus
        array values. For example, if 'Stopping' is the
        value assigned to OperationalStatus, then this
        property may contain an explanation as to why an
        object is being stopped. Note that entries in this
        array are correlated with those at the same array
        index in OperationalStatus."
    ::= { msvmVirtualSystemMgtServiceEntry 19 }

msvmvsmsvSystemCreationClassName OBJECT-TYPE
    SYNTAX     WtcsDisplayString (SIZE (0..256))
    MAX-ACCESS read-only
    STATUS     current
    DESCRIPTION
        "The CreationClassName of the scoping System."
    ::= { msvmVirtualSystemMgtServiceEntry 20 }

msvmvsmsvSystemName OBJECT-TYPE
    SYNTAX     WtcsDisplayString (SIZE (0..256))
    MAX-ACCESS read-only
    STATUS     current
    DESCRIPTION
        "The Name of the scoping System."
    ::= { msvmVirtualSystemMgtServiceEntry 21 }

msvmvsmsvTimeOfLastStateChange OBJECT-TYPE
    SYNTAX     DateAndTime
    MAX-ACCESS read-only
    STATUS     current
    DESCRIPTION
        "The date or time when the EnabledState of the
        element last changed. If the state of the element
        has not changed and this property is populated,
        then it must be set to a 0 interval value. If a
        state change was requested, but rejected or not yet
        processed, the property must not be updated."
    ::= { msvmVirtualSystemMgtServiceEntry 22 }

msvmVirtualSystemMgtSvcDataTable OBJECT-TYPE
    SYNTAX     SEQUENCE OF MsvmVirtualSysMgtSvcSettingData
    MAX-ACCESS not-accessible
    STATUS     current
    DESCRIPTION
        "Represents the settings for the virtualization
        service present on a single host system."
    ::= { msvmVirtualSystemManagement 10 }

msvmVirtualSystemMgtSvcDataEntry OBJECT-TYPE
    SYNTAX     MsvmVirtualSysMgtSvcSettingData
    MAX-ACCESS not-accessible
    STATUS     current
    DESCRIPTION
        "None"
    INDEX      { msvmvsmssdIndex }
    ::= { msvmVirtualSystemMgtSvcDataTable 1 }

MsvmVirtualSysMgtSvcSettingData ::= SEQUENCE {
    msvmvsmssdIndex Integer32,
    msvmvsmssdBiosLockString WtcsDisplayString,
    msvmvsmssdCaption WtcsDisplayString,
    msvmvsmssdDefaultExternDataRoot WtcsDisplayString,
    msvmvsmssdDefVirtualHardDiskPath WtcsDisplayString,
    msvmvsmssdDescription WtcsDisplayString,
    msvmvsmssdElementName WtcsDisplayString,
    msvmvsmssdInstanceID WtcsDisplayString,
    msvmvsmssdMaximumMacAddress WtcsDisplayString,
    msvmvsmssdMinimumMacAddress WtcsDisplayString,
    msvmvsmssdPrimaryOwnerContact WtcsDisplayString,
    msvmvsmssdPrimaryOwnerName WtcsDisplayString,
    msvmvsmssdScopeOfResidence WtcsDisplayString
}

msvmvsmssdIndex OBJECT-TYPE
    SYNTAX     Integer32 (1..2147483647)
    MAX-ACCESS read-only
    STATUS     current
    DESCRIPTION
        "The value of this object uniquely identifies the
        instance entry for this class."
    ::= { msvmVirtualSystemMgtSvcDataEntry 1 }

msvmvsmssdBiosLockString OBJECT-TYPE
    SYNTAX     WtcsDisplayString (SIZE (0..32))
    MAX-ACCESS read-only
    STATUS     current
    DESCRIPTION
        "Used by OEMs to allow BIOS-locked Windows
        operating systems to run in the virtual machine.
        This string must be exactly 32 characters in
        length."
    ::= { msvmVirtualSystemMgtSvcDataEntry 2 }

msvmvsmssdCaption OBJECT-TYPE
    SYNTAX     WtcsDisplayString (SIZE (0..64))
    MAX-ACCESS read-only
    STATUS     current
    DESCRIPTION
        "The Caption property is a short textual
        description (one- line string) of the object."
    ::= { msvmVirtualSystemMgtSvcDataEntry 3 }

msvmvsmssdDefaultExternDataRoot OBJECT-TYPE
    SYNTAX     WtcsDisplayString
    MAX-ACCESS read-only
    STATUS     current
    DESCRIPTION
        "The default external data root. By default,
        '<root>\ProgramData\Microsoft\
        Windows\Virtualization'."
    ::= { msvmVirtualSystemMgtSvcDataEntry 4 }

msvmvsmssdDefVirtualHardDiskPath OBJECT-TYPE
    SYNTAX     WtcsDisplayString
    MAX-ACCESS read-only
    STATUS     current
    DESCRIPTION
        "The default virtual hard disk path. By default,
        '<root>\Users\Public\Documents\Virtual Hard
        Disks'."
    ::= { msvmVirtualSystemMgtSvcDataEntry 5 }

msvmvsmssdDescription OBJECT-TYPE
    SYNTAX     WtcsDisplayString
    MAX-ACCESS read-only
    STATUS     current
    DESCRIPTION
        "The Description property provides a textual
        description of the object."
    ::= { msvmVirtualSystemMgtSvcDataEntry 6 }

msvmvsmssdElementName OBJECT-TYPE
    SYNTAX     WtcsDisplayString
    MAX-ACCESS read-only
    STATUS     current
    DESCRIPTION
        "A user-friendly name for the object. This property
        allows each instance to define a user-friendly name
        in addition to its key properties, identity data,
        and description information. 
        Note that the Name property of ManagedSystemElement
        is also defined as a user-friendly name. But, it is
        often subclassed to be a Key. It is not reasonable
        that the same property can convey both identity and
        a user-friendly name, without inconsistencies.
        Where Name exists and is not a Key (such as for
        instances of LogicalDevice), the same information
        can be present in both the Name and ElementName
        properties."
    ::= { msvmVirtualSystemMgtSvcDataEntry 7 }

msvmvsmssdInstanceID OBJECT-TYPE
    SYNTAX     WtcsDisplayString
    MAX-ACCESS read-only
    STATUS     current
    DESCRIPTION
        "Within the scope of the instantiating Namespace,
        InstanceID opaquely and uniquely identifies an
        instance of this class. To ensure uniqueness within
        the NameSpace, the value of InstanceID should be
        constructed using the following 'preferred'
        algorithm: 
        <OrgID>:<LocalID> 
        Where <OrgID> and <LocalID> are separated by a
        colon (:), and where <OrgID> must include a
        copyrighted, trademarked, or otherwise unique name
        that is owned by the business entity that is
        creating or defining the InstanceID or that is a
        registered ID assigned to the business entity by a
        recognized global authority. (This requirement is
        similar to the <Schema Name>_<Class Name> structure
        of Schema class names.) In addition, to ensure
        uniqueness, <OrgID> must not contain a colon (:).
        When using this algorithm, the first colon to
        appear in InstanceID must appear between <OrgID>
        and <LocalID>. 
        <LocalID> is chosen by the business entity and
        should not be reused to identify different
        underlying (real-world) elements. If the above
        'preferred' algorithm is not used, the defining
        entity must assure that the resulting InstanceID is
        not reused across any InstanceIDs produced by this
        or other providers for the NameSpace of this
        instance. 
        For DMTF-defined instances, the 'preferred'
        algorithm must be used with the <OrgID> set to
        CIM."
    ::= { msvmVirtualSystemMgtSvcDataEntry 8 }

msvmvsmssdMaximumMacAddress OBJECT-TYPE
    SYNTAX     WtcsDisplayString
    MAX-ACCESS read-only
    STATUS     current
    DESCRIPTION
        "Maximum MAC address for dynamically generated MAC
        addresses."
    ::= { msvmVirtualSystemMgtSvcDataEntry 9 }

msvmvsmssdMinimumMacAddress OBJECT-TYPE
    SYNTAX     WtcsDisplayString
    MAX-ACCESS read-only
    STATUS     current
    DESCRIPTION
        "Minimum MAC address for dynamically generated MAC
        addresses."
    ::= { msvmVirtualSystemMgtSvcDataEntry 10 }

msvmvsmssdPrimaryOwnerContact OBJECT-TYPE
    SYNTAX     WtcsDisplayString (SIZE (0..256))
    MAX-ACCESS read-only
    STATUS     current
    DESCRIPTION
        "Name of the primary system owner. By default,
        'Administrators'. This value may not exceed 64
        characters in length."
    ::= { msvmVirtualSystemMgtSvcDataEntry 11 }

msvmvsmssdPrimaryOwnerName OBJECT-TYPE
    SYNTAX     WtcsDisplayString (SIZE (0..64))
    MAX-ACCESS read-only
    STATUS     current
    DESCRIPTION
        "Name of the primary system owner. By default,
        'Administrators'. This value may not exceed 64
        characters in length."
    ::= { msvmVirtualSystemMgtSvcDataEntry 12 }

msvmvsmssdScopeOfResidence OBJECT-TYPE
    SYNTAX     WtcsDisplayString
    MAX-ACCESS read-only
    STATUS     current
    DESCRIPTION
        "The scope. By default, empty."
    ::= { msvmVirtualSystemMgtSvcDataEntry 13 }

siHyperVWmiVersion OBJECT-TYPE
    SYNTAX     OCTET STRING
    MAX-ACCESS read-only
    STATUS     current
    DESCRIPTION
        "Designates the version of this SNMP Informant
        agent."
    ::= { informantHyperV 999 }

END
