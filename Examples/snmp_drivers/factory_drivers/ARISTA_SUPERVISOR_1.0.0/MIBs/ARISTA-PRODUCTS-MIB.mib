-- ARISTA-PRODUCTS-MIB: Arista Networks product object identifier assignments
-- Copyright (c) 2008, 2009, 2010, 2011, 2012 Aristra Networks, Inc.  All rights reserved.

ARISTA-PRODUCTS-MIB DEFINITIONS ::= BEGIN

IMPORTS
    MODULE-IDENTITY
        FROM SNMPv2-SMI
    aristaModules,
    aristaProducts
        FROM ARISTA-SMI-MIB;

aristaProductsMIB MODULE-IDENTITY
    LAST-UPDATED    "201204170800Z"
    ORGANIZATION "Arista Networks, Inc."
    CONTACT-INFO
        "Arista Networks, Inc.

         Postal: 5470 Great America Parkway
                 Santa Clara, CA 95054

         Tel: +1 408 547-5500

         E-mail: snmp@aristanetworks.com"
    DESCRIPTION
        "This module defines the object identifiers returned as values for
         sysObjectID or entPhysicalVendorType for Arista Networks hardware."
        REVISION      "201204170800Z"
        DESCRIPTION
                "Revised to include DCS-7124FX-CL"
        REVISION      "201204030800Z"
        DESCRIPTION
                "Revised to include DCS-7050Q-16-SSD"
        REVISION      "201203090800Z"
        DESCRIPTION
                "Revised to include DCS-7124FX"
        REVISION      "201202200800Z"
        DESCRIPTION
                "Revised to include DCS-7050T-36"
        REVISION      "201202010800Z"
        DESCRIPTION
                "Revised to include DCS-7050T-52-SSD, and DCS-7050T-64-SSD"
        REVISION      "201109010800Z"
        DESCRIPTION
                "Revised to include DCS-7050Q-16"
        REVISION      "201108290800Z"
        DESCRIPTION
                "Revised to include DCS-7050S-52-SSD"
        REVISION      "201108040800Z"
        DESCRIPTION
                "Revised to include DCS-7050S-64-SSD"
        REVISION      "201107161400Z"
        DESCRIPTION
                "Revised to include DCS-7050T-52, and DCS-7050T-64"
        REVISION      "201106221800Z"
        DESCRIPTION
                "Revised to include DCS-7124SX-SSD"
        REVISION      "201103311300Z"
        DESCRIPTION
                "Updated postal address and telephone."
        REVISION      "201102240800Z"
        DESCRIPTION
                "Revised to include DCS-7050S-52 and DCS-7050S-64"
        REVISION      "201010241600Z"
        DESCRIPTION
                "Revised to include DCS-7048T-A"
        REVISION      "201009172040Z"
        DESCRIPTION
                "Revised to include DCS-7124SX."
        REVISION      "201004050942Z"
        DESCRIPTION
                "Revised to include DCS-7504."
        REVISION      "201004050941Z"
        DESCRIPTION
                "Revised to include DCS-7508."
        REVISION      "200906081558Z"
        DESCRIPTION
                "Revised to include DCS-7048T-4S."
        REVISION      "200904171505Z"
        DESCRIPTION
                "Revised to include DCS-7140T-8S and  DCS-7120T-4S."
        REVISION      "200809101415Z"
        DESCRIPTION
                "Revised to include DCS-7148S."
        REVISION      "200803031230Z"
        DESCRIPTION
                "Initial version."
    ::= { aristaModules 1 }
-- DCS-7124S 1RU 24-port SFP+ 10Gb Ethernet Switch
aristaDCS7124S OBJECT IDENTIFIER ::= { aristaProducts 3011 7124 3282 }
-- DCS-7148SX 1RU 48-port SFP+ 10Gb Ethernet Switch
aristaDCS7148SX OBJECT IDENTIFIER ::= { aristaProducts 3011 7148 3741 }
-- DCS-7148S 1RU 48-port SFP+ 10Gb Ethernet Switch
aristaDCS7148S OBJECT IDENTIFIER ::= { aristaProducts 3011 7148 3282 }
-- DCS-7120T-4S 1RU 20-port 10GBASE-T + 4 port SFP+ Ethernet Switch
aristaDCS7120T4S OBJECT IDENTIFIER ::= { aristaProducts 3011 7120 427 4 3282 }
-- DCS-7140T-8S 1RU 40-port 10GBASE-T + 8 port SFP+ Ethernet Switch
aristaDCS7140T8S OBJECT IDENTIFIER ::= { aristaProducts 3011 7140 427 8 3282 }
-- DCS-7048T-4S 1RU 48-port 1000BASE-T + 4 port SFP+ Ethernet Switch
aristaDCS7048T4S OBJECT IDENTIFIER ::= { aristaProducts 3011 7048 427 4 3282 }
-- DCS-7508 Switch Chassis. 2 Supervisor slots, 8 Linecard slots, 6 Fabric Module slots.
aristaDCS7508 OBJECT IDENTIFIER ::= { aristaProducts 3011 7508 }
-- DCS-7504 Switch Chassis. 2 Supervisor slots, 4 Linecard slots, 6 Fabric Module slots.
aristaDCS7504 OBJECT IDENTIFIER ::= { aristaProducts 3011 7504 }
-- DCS-7124SX 1RU 24-port SFP+ 10Gb Ethernet Switch
aristaDCS7124SX OBJECT IDENTIFIER ::= { aristaProducts 3011 7124 3741 }
-- DCS-7048T-A 1RU 48-port 1000BASE-T + 4 port SFP+ Ethernet Switch
aristaDCS7048TA OBJECT IDENTIFIER ::= { aristaProducts 3011 7048 427 3648 }
-- DCS-7050S-52 1RU 52-port SFP+ 10Gb Ethernet Switch
aristaDCS7050S52 OBJECT IDENTIFIER ::= { aristaProducts 3011 7050 3282 52 }
-- DCS-7050S-64 1RU 48-port SFP+ + 4-port QSFP+ Ethernet Switch
aristaDCS7050S64 OBJECT IDENTIFIER ::= { aristaProducts 3011 7050 3282 64 }
-- DCS-7124SX-SSD 1RU 24-port SFP+ 10Gb Ethernet Switch with SSD disk
aristaDCS7124SXSSD OBJECT IDENTIFIER ::= { aristaProducts 3011 7124 3741 761 }
-- DCS-7050T-52 1RU 48-port 10GBASE-T + 4 port SFP+ Ethernet Switch
aristaDCS7050T52 OBJECT IDENTIFIER ::= { aristaProducts 3011 7050 427 52 }
-- DCS-7050T-64 1RU 48-port 10GBASE-T + 4-port QSFP+ Ethernet Switch
aristaDCS7050T64 OBJECT IDENTIFIER ::= { aristaProducts 3011 7050 427 64 }
-- DCS-7050S-64-SSD 1RU 48-port SFP+ + 4-port QSFP+ Ethernet Switch with SSD disk
aristaDCS7050S64SSD OBJECT IDENTIFIER ::= { aristaProducts 3011 7050 3282 64 761 }
-- DCS-7050S-52-SSD 1RU 48-port SFP+ + 4-port SFP+ Ethernet Switch with SSD disk
aristaDCS7050S52SSD OBJECT IDENTIFIER ::= { aristaProducts 3011 7050 3282 52 761 }
-- DCS-7050Q-16 1RU 16-port QSFP+ + 4-port SFP+ Ethernet Switch
aristaDCS7050Q16 OBJECT IDENTIFIER ::= { aristaProducts 3011 7050 2512 16 }
-- DCS-7050T-52-SSD 1RU 48-port 10GBASE-T + 4 port SFP+ Ethernet Switch with SSD disk
aristaDCS7050T52SSD OBJECT IDENTIFIER ::= { aristaProducts 3011 7050 427 52 761 }
-- DCS-7050T-64-SSD 1RU 48-port 10GBASE-T + 4-port QSFP+ Ethernet Switch with SSD disk
aristaDCS7050T64SSD OBJECT IDENTIFIER ::= { aristaProducts 3011 7050 427 64 761 }
-- DCS-7050T-36 1RU 32-port 10GBASE-T + 4-port SFP+ Ethernet Switch
aristaDCS7050T36 OBJECT IDENTIFIER ::= { aristaProducts 3011 7050 427 36 }
-- DCS-7124FX 1RU 24-port SFP+ 10Gb Ethernet Switch with SSD disk and 160Gb Application Engine FPGA
aristaDCS7124FX OBJECT IDENTIFIER ::= { aristaProducts 3011 7124 2312 }
-- DCS-7050Q-16-SSD 1RU 16-port QSFP+ + 4-port SFP+ Ethernet Switch with SSD disk
aristaDCS7050Q16SSD OBJECT IDENTIFIER ::= { aristaProducts 3011 7050 2512 16 761 }
-- DCS-7124FX-CL 1RU 24-port SFP+ 10Gb Ethernet Switch with SSD disk, 160Gb Application Engine FPGA, and Clock module
aristaDCS7124FXCL OBJECT IDENTIFIER ::= { aristaProducts 3011 7124 2312 2745 }

END
