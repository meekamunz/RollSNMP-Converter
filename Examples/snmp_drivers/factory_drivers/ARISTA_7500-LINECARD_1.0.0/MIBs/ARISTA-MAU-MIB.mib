ARISTA-MAU-MIB DEFINITIONS ::= BEGIN

     IMPORTS
       MODULE-IDENTITY, OBJECT-IDENTITY
         FROM SNMPv2-SMI
       aristaMibs
         FROM ARISTA-SMI-MIB
       ;

     aristaMauMIB MODULE-IDENTITY
       LAST-UPDATED "201204100000Z"  -- April 10, 2012
       ORGANIZATION "Arista Networks, Inc."
       CONTACT-INFO
          "Arista Networks, Inc.

           Postal: 5470 Great America Parkway
                   Santa Clara, CA 95054

           Tel: +1 408 547-5500

           E-mail: snmp@aristanetworks.com"
       DESCRIPTION
         "This MIB module extends dot3MauType OBJECT-IDENTITIES
         defined in the IANA-MAU-MIB, covering all MAU types
         used by Arista Networks."

       REVISION     "201204100000Z"  -- April 10, 2012
       DESCRIPTION  "Revised to include aristaDot3MauType10GbaseDwdmZR
                    and renamed aristaDot3MauType10GbaseDWDM to
                    aristaDot3MauType10GbaseDwdmER."
                                   
       REVISION     "201102250000Z"  -- February 25, 2011
       DESCRIPTION  "Initial version of this MIB."

       ::= { aristaSnmpDot3MauMgt 2 }

     aristaSnmpDot3MauMgt OBJECT IDENTIFIER ::= { aristaMibs 4 }
     aristaDot3MauType OBJECT IDENTIFIER ::= { aristaSnmpDot3MauMgt 1 }

     aristaDot3MauType10GbaseCR OBJECT-IDENTITY
       STATUS      current
       DESCRIPTION "Passive copper cable"
       REFERENCE   "SFF-8472 (Rev. 11.0), Table 3.6b"
       ::= { aristaDot3MauType 1 }

     aristaDot3MauType10GbaseDwdmER OBJECT-IDENTITY
       STATUS      current
       DESCRIPTION "Dense Wavelength Division Multiplexing ER"
       ::= { aristaDot3MauType 2 }

     aristaDot3MauType40GbaseSR4 OBJECT-IDENTITY
       STATUS      current
       DESCRIPTION "Fiber over short-wavelength laser"
       REFERENCE   "[IEEE802.3ba], Section 86"
       ::= { aristaDot3MauType 3 }

     aristaDot3MauType40GbaseLR4 OBJECT-IDENTITY
       STATUS      current
       DESCRIPTION "Fiber over long-wavelength laser"
       REFERENCE   "[IEEE802.3ba], Section 87"
       ::= { aristaDot3MauType 4 }

     aristaDot3MauType40GbaseCR4 OBJECT-IDENTITY
       STATUS      current
       DESCRIPTION "Passive copper cable"
       REFERENCE   "[IEEE802.3ba], Section 85"
       ::= { aristaDot3MauType 5 }

     aristaDot3MauType10GbaseDwdmZR OBJECT-IDENTITY
       STATUS      current
       DESCRIPTION "Dense Wavelength Division Multiplexing ZR"
       ::= { aristaDot3MauType 6 }

     aristaDot3MauType10GbaseCRA OBJECT-IDENTITY
       STATUS      current
       DESCRIPTION "Active copper cable"
       REFERENCE   "SFF-8472 (Rev. 11.0), Table 3.6c"
       ::= { aristaDot3MauType 7 }


END
