-- MIB file created 22-May-2008 22:06:15, by
--   SMICng version 2.2.11-beta(PRO)(Solaris), January 20, 2001. Enterprise key cisco.com

CISCO-IF-EXTENSION-MIB DEFINITIONS ::= BEGIN

-- From file: "CISCO-IF-EXTENSION-MIB.my"
-- Compile options "4 7 F H N O W 03 06 0B 0G 0N 0T"

IMPORTS
    TruthValue, TimeStamp, DisplayString
            FROM SNMPv2-TC-v1
    ifIndex, InterfaceIndexOrZero, ifName, ifType, ifAdminStatus, 
    ifOperStatus
            FROM IF-MIB
    entPhysicalIndex
            FROM ENTITY-MIB
    SnmpAdminString
            FROM SNMP-FRAMEWORK-MIB
    Unsigned64, IfOperStatusReason
            FROM CISCO-TC
    ciscoMgmt
            FROM CISCO-SMI
    Counter, Gauge
            FROM RFC1155-SMI
    OBJECT-TYPE
            FROM RFC-1212
    TRAP-TYPE
            FROM RFC-1215;

ciscoIfExtensionMIB OBJECT IDENTIFIER ::= { ciscoMgmt 276 }
-- MODULE-IDENTITY
--  LastUpdated
--    200707230000Z
--  OrgName
--    Cisco Systems, Inc.
--  ContactInfo
--    Cisco Systems
--    Customer Service
--    
--    Postal: 170 West Tasman Drive
--    San Jose, CA  95134
--    USA
--    
--    Tel: +1 800 553-NETS
--    
--    E-mail: cs-core-mibs@cisco.com,
--    cs-lan-switch-snmp@cisco.com
--  Descr
--    A MIB module for extending the IF-MIB (RFC2863)
--    to add objects which provide additional information
--    about interfaces not available in other MIBS.
--    This MIB replaces the OLD-CISCO-INTERFACES-MIB.
--  RevDate
--    200707230000Z
--  RevDescr
--    Added cieIfInterval in cieIfUtilTable. Changed
--    the description of objects in cieIfUtilTable.
--    Added ciscoIfExtUtilIntervalGroup.
--  RevDate
--    200611010000Z
--  RevDescr
--    Add support for asymetrical interfaces speeds.
--    
--    - Added following objects in cieIfInterfaceTable 
--      cieIfSpeedReceive 
--      cieIfHighSpeedReceive 
--    - Added ciscoIfExtensionAsymmetricalSpeedGroup OBJECT-GROUP 
--    - Added ciscoIfExtensionMIBCompliance6 MODULE-COMPLIANCE
--  RevDate
--    200504280000Z
--  RevDescr
--    Added:
--    - cieLinkUp & cieLinkDown notifications.
--    - object to control sending: only standard 
--      linkUp/linkDown OR only cieLinkUp/cieLinkDown
--      OR both.
--    - object to control sending only standard defined
--      varbinds in linkUp/linkDown OR additional varbinds
--      in addition to standard defined.
--  RevDate
--    200501250000Z
--  RevDescr
--    Updated the description of cieIfDot1dBaseMappingEntry.
--  RevDate
--    200409080000Z
--  RevDescr
--    Added new objects 'cieIfOperStatusCause' and
--    'cieIfOperStatusCauseDescr' in cieIfInterfaceTable.
--    Added a new table 'cieIfStatusListTable'.
--  RevDate
--    200311140000Z
--  RevDescr
--    Added new objects cieIfName and cieIfIndex for the
--    'ifName' to 'ifIndex' mapping.  Deprecated the
--    ciscoIfExtensionMIBCompliance2 compliance.
--    Added ciscoIfExtensionMIBCompliance3 and
--    ciscoIfExtIfNameMappingGroup.
--  RevDate
--    200308120000Z
--  RevDescr
--    Added ciscoIfExtDot1dBaseMappingGroup.
--  RevDate
--    200307170000Z
--  RevDescr
--    Added ciscoIfExtUtilizationGroup.
--  RevDate
--    200306250000Z
--  RevDescr
--    Added the object cieSystemMtu and
--    ciscoIfExtSystemGroup.
--    Added ciscoIfExtDot1qCustomEtherType and
--    ciscoIfExtDot1qEtherTypeGroup.
--  RevDate
--    200210120000Z
--  RevDescr
--    Added the objects cieIfDhcpMode, cieIfMtu,
--    cieIfContextName to cieIfInterfaceTable.
--    Deprecated the ciscoIfExtensionMIBCompliance
--    compliance.  Added ciscoIfExtensionMIBCompliance1.
--    Added ciscoIfExtensionTableIntfGroup1.
--  RevDate
--    200207240000Z
--  RevDescr
--    Initial version of the MIB module.

ciscoIfExtensionMIBNotifications OBJECT IDENTIFIER ::= { ciscoIfExtensionMIB 0 }
ciscoIfExtensionMIBObjects OBJECT IDENTIFIER ::= { ciscoIfExtensionMIB 1 }
ciscoIfExtensionMIBConformance OBJECT IDENTIFIER ::= { ciscoIfExtensionMIB 2 }
ciscoIfExtensionStats OBJECT IDENTIFIER ::= { ciscoIfExtensionMIBObjects 1 }
ciscoIfExtSystemConfig OBJECT IDENTIFIER ::= { ciscoIfExtensionMIBObjects 2 }
ciscoIfExtDot1qCustomEtherType OBJECT IDENTIFIER ::= { ciscoIfExtensionMIBObjects 3 }
ciscoIfExtUtilization OBJECT IDENTIFIER ::= { ciscoIfExtensionMIBObjects 4 }
ciscoIfExtDot1dBaseMapping OBJECT IDENTIFIER ::= { ciscoIfExtensionMIBObjects 5 }
ciscoIfExtIfNameMapping OBJECT IDENTIFIER ::= { ciscoIfExtensionMIBObjects 6 }
ciscoIfExtensionMIBCompliances OBJECT IDENTIFIER ::= { ciscoIfExtensionMIBConformance 1 }
ciscoIfExtensionMIBGroups OBJECT IDENTIFIER ::= { ciscoIfExtensionMIBConformance 2 }

InterfaceIndexList ::= OCTET STRING(SIZE(0..256))
-- TEXTUAL-CONVENTION
--  Status
--    mandatory
--  Descr
--    This textual convention defines the 'ifIndex' for a
--    set of 64 interfaces in a module.
--    
--    Each 4 bytes within the value of an object of this
--    type is combined together to represent the interface
--    index of a particular port in the module (i.e., each
--    4 byte group represents the 'ifIndex' of an interface).
--    
--    The first 4 bytes (byte 1, byte 2, byte 3 and byte 4)
--    combined represent the 'ifIndex' of an interface.
--    While the second 4 bytes (byte 5, byte 6, byte 7 and
--    byte 8) represent the 'ifIndex' for the next interface
--    in the module, and so on.
--    
--    If there are only 'n' interfaces in a set of 64
--    interfaces in the module, then bytes after the '4n'
--    byte in this object are irrelevant.

InterfaceOperModeList ::= OCTET STRING(SIZE(0..64))
-- TEXTUAL-CONVENTION
--  Status
--    mandatory
--  Descr
--    This textual convention defines the operational mode
--    for a set of 64 interfaces in a module.
--    
--    The operational mode of an interface is represented
--    by the value defined in the textual convention
--    'InterfaceOperMode' (defined in CISCO-ST-TC).
--    
--    Each 'byte' within the value of an object of this
--    type, specifies the operational mode of an interface
--    in the module.
--    
--    The first byte (byte 1) represents the operational
--    mode of an interface in the module, whose 'ifIndex'
--    is represented by the corresponding instance of
--    'cieInterfacesIndex' object in its first 4 bytes.
--    
--    The second byte (byte 2) represents the operational
--    mode of an interface in the module, whose 'ifIndex'
--    is represented by the corresponding instance of
--    'cieInterfacesIndex' object in its second 4 bytes.
--    
--    If there are only 'n' interfaces in a set of 64
--    interfaces in the module, then bytes after the 'n'
--    byte in this object are irrelevant.

InterfaceOperCauseList ::= OCTET STRING(SIZE(0..128))
-- TEXTUAL-CONVENTION
--  Status
--    mandatory
--  Descr
--    This textual convention defines the operational
--    status cause for a set of 64 interfaces in a module.
--    
--    The operational status cause of an interface is
--    represented by the value defined in the textual
--    convention 'IfOperStatusReason' (defined in CISCO-TC).
--    
--    Each 2 bytes within the value of an object of this
--    type is combined together to represent the operational
--    status cause of a particular interface in the module
--    (i.e., each 2 byte group represents the
--    'cieIfOperStatusCause' of an interface).
--    
--    The first 2 bytes (byte 1 and byte 2) of this object,
--    represents the operational status cause of an
--    interface in the module, whose 'ifIndex' is
--    represented by the corresponding instance of
--    'cieInterfacesIndex' object in its first 4 bytes.
--    
--    The next 2 bytes (byte 3 and byte 4) of this object,
--    represents the operational status cause of an
--    interface in the module, whose 'ifIndex' is
--    represented by the corresponding instance of
--    'cieInterfacesIndex' object in the next 4 bytes
--    respectively.
--    
--    If there are only 'n' interfaces in a set of 64
--    interfaces in the module, then bytes after the
--    '2n' byte in this object are irrelevant.

cieIfPacketStatsTable OBJECT-TYPE
    SYNTAX SEQUENCE OF CieIfPacketStatsEntry
    ACCESS not-accessible
    STATUS mandatory
    DESCRIPTION
        "This  table contains interface packet
        statistics which are not available in 
        IF-MIB(RFC2863). 
        
        As an example, some interfaces to which
        objects in this table are applicable are
        as follows :
        
                o Ethernet
                o FastEthernet
                o ATM
                o BRI
                o Sonet
                o GigabitEthernet
        
        Some objects defined in this table may be 
        applicable to physical interfaces only.
        As a result, this table may be sparse for
        some logical interfaces."
    ::= { ciscoIfExtensionStats 1 }

cieIfPacketStatsEntry OBJECT-TYPE
    SYNTAX CieIfPacketStatsEntry
    ACCESS not-accessible
    STATUS mandatory
    DESCRIPTION
        "An entry into the cieIfPacketStatsTable."
    INDEX { ifIndex }
    ::= { cieIfPacketStatsTable 1 }

CieIfPacketStatsEntry ::= SEQUENCE {
    cieIfLastInTime Gauge,
    cieIfLastOutTime Gauge,
    cieIfLastOutHangTime Gauge,
    cieIfInRuntsErrs Counter,
    cieIfInGiantsErrs Counter,
    cieIfInFramingErrs Counter,
    cieIfInOverrunErrs Counter,
    cieIfInIgnored Counter,
    cieIfInAbortErrs Counter,
    cieIfInputQueueDrops Counter,
    cieIfOutputQueueDrops Counter,
    cieIfPacketDiscontinuityTime TimeStamp
    }

cieIfLastInTime OBJECT-TYPE
    SYNTAX Gauge
--  Units
--    milliseconds
    ACCESS read-only
    STATUS mandatory
    DESCRIPTION
        "This object represents the elapsed time in
        milliseconds since last protocol input 
        packet was received.
        
        Discontinuities in the value of this variable
        can occur at re-initialization of the
        management system, and at other times as 
        indicated by the values of 
        cieIfPacketDiscontinuityTime."
    ::= { cieIfPacketStatsEntry 1 }

cieIfLastOutTime OBJECT-TYPE
    SYNTAX Gauge
--  Units
--    milliseconds
    ACCESS read-only
    STATUS mandatory
    DESCRIPTION
        "This object represents the elapsed time in
        milliseconds since last protocol  output 
        packet was transmitted.
        
        Discontinuities in the value of this variable
        can occur at re-initialization of the
        management system, and at other times as 
        indicated by the values of 
        cieIfPacketDiscontinuityTime."
    ::= { cieIfPacketStatsEntry 2 }

cieIfLastOutHangTime OBJECT-TYPE
    SYNTAX Gauge
--  Units
--    milliseconds
    ACCESS read-only
    STATUS mandatory
    DESCRIPTION
        "This object represents the elapsed time in
        milliseconds since last protocol    output
        packet could not be successfully transmitted.
        
        Discontinuities in the value of this variable
        can occur at re-initialization of the
        management system, and at other times as 
        indicated by the values of 
        cieIfPacketDiscontinuityTime."
    ::= { cieIfPacketStatsEntry 3 }

cieIfInRuntsErrs OBJECT-TYPE
    SYNTAX Counter
    ACCESS read-only
    STATUS mandatory
    DESCRIPTION
        "The number of packets input on a particular
        physical interface which were dropped as
        they were smaller than the minimum allowable 
        physical media limit.
        
        Discontinuities in the value of this variable
        can occur at re-initialization of the
        management system, and at other times as 
        indicated by the values of 
        cieIfPacketDiscontinuityTime."
    ::= { cieIfPacketStatsEntry 4 }

cieIfInGiantsErrs OBJECT-TYPE
    SYNTAX Counter
    ACCESS read-only
    STATUS mandatory
    DESCRIPTION
        "The number of input packets on a particular
        physical interface which were dropped as 
        they were larger than the ifMtu (largest 
        permitted  size of a packet which can be 
        sent/received on an interface).
        
        Discontinuities in the value of this variable
        can occur at re-initialization of the
        management system, and at other times as 
        indicated by the values of 
        cieIfPacketDiscontinuityTime."
    ::= { cieIfPacketStatsEntry 5 }

cieIfInFramingErrs OBJECT-TYPE
    SYNTAX Counter
    ACCESS read-only
    STATUS mandatory
    DESCRIPTION
        "The number of input packets on a physical
        interface which were misaligned or had
        framing errors. This happens when the 
        format of the incoming packet on a physical
        interface is incorrect.
        
        Discontinuities in the value of this variable
        can occur at re-initialization of the
        management system, and at other times as 
        indicated by the values of 
        cieIfPacketDiscontinuityTime."
    ::= { cieIfPacketStatsEntry 6 }

cieIfInOverrunErrs OBJECT-TYPE
    SYNTAX Counter
    ACCESS read-only
    STATUS mandatory
    DESCRIPTION
        "The number of input packets which arrived
        on a particular physical interface which 
        were too quick for the hardware to receive
        and hence the receiver ran out of buffers.
        
        Discontinuities in the value of this variable
        can occur at re-initialization of the
        management system, and at other times as 
        indicated by the values of 
        cieIfPacketDiscontinuityTime."
    ::= { cieIfPacketStatsEntry 7 }

cieIfInIgnored OBJECT-TYPE
    SYNTAX Counter
    ACCESS read-only
    STATUS mandatory
    DESCRIPTION
        "The number of input packets which were simply
        ignored by this physical interface due to 
        insufficient resources to handle the incoming
        packets.
        
        For example, this could indicate that the input
        receive buffers are not available or that the
        receiver lost a packet.
        
        Discontinuities in the value of this variable
        can occur at re-initialization of the
        management system, and at other times as 
        indicated by the values of 
        cieIfPacketDiscontinuityTime."
    ::= { cieIfPacketStatsEntry 8 }

cieIfInAbortErrs OBJECT-TYPE
    SYNTAX Counter
    ACCESS read-only
    STATUS mandatory
    DESCRIPTION
        "Number of input packets which were dropped
        because the receiver aborted.
        
        Examples of this could be when an abort
        sequence aborted the input frame or when
        there is a collision in an ethernet segment.
        
        Discontinuities in the value of this variable
        can occur at re-initialization of the
        management system, and at other times as 
        indicated by the values of 
        cieIfPacketDiscontinuityTime."
    ::= { cieIfPacketStatsEntry 9 }

cieIfInputQueueDrops OBJECT-TYPE
    SYNTAX Counter
    ACCESS read-only
    STATUS mandatory
    DESCRIPTION
        "The number of input packets which were
        dropped.
        
        Some reasons why this object could be 
        incremented are:
        
        o  Input queue is full.
        o  Errors at the receiver hardware 
           while receiving the packet.
        
        Discontinuities in the value of this variable
        can occur at re-initialization of the
        management system, and at other times as 
        indicated by the values of 
        cieIfPacketDiscontinuityTime."
    ::= { cieIfPacketStatsEntry 10 }

cieIfOutputQueueDrops OBJECT-TYPE
    SYNTAX Counter
    ACCESS read-only
    STATUS mandatory
    DESCRIPTION
        "This object indicates the  number of output
        packets dropped by the interface even though
        no error had been detected to prevent them
        being transmitted. 
        
        The packet could be dropped for many reasons,
        which could range from the interface being
        down to errors in the format of the packet.
        
        Discontinuities in the value of this variable
        can occur at re-initialization of the
        management system, and at other times as 
        indicated by the values of 
        cieIfPacketDiscontinuityTime."
    ::= { cieIfPacketStatsEntry 11 }

cieIfPacketDiscontinuityTime OBJECT-TYPE
    SYNTAX TimeStamp
--    Rsyntax TimeTicks
    ACCESS read-only
    STATUS mandatory
    DESCRIPTION
        "The value of sysUpTime on the most recent
        occasion at which this interface's  counters
        suffered a discontinuity. 
        
        If no such discontinuities have occurred 
        since the last re-initialization of the 
        local management subsystem, then this 
        object contains a value of zero."
    ::= { cieIfPacketStatsEntry 12 }

cieIfInterfaceTable OBJECT-TYPE
    SYNTAX SEQUENCE OF CieIfInterfaceEntry
    ACCESS not-accessible
    STATUS mandatory
    DESCRIPTION
        "This  table contains objects which provide
        more information about interface  
        properties not available in IF-MIB
        (RFC 2863).
        
        Some objects defined in this table may be
        applicable to physical interfaces only.
        As a result, this table may be sparse for
        logical interfaces."
    ::= { ciscoIfExtensionStats 2 }

cieIfInterfaceEntry OBJECT-TYPE
    SYNTAX CieIfInterfaceEntry
    ACCESS not-accessible
    STATUS mandatory
    DESCRIPTION
        "An entry into the cieIfInterfaceTable."
    INDEX { ifIndex }
    ::= { cieIfInterfaceTable 1 }

CieIfInterfaceEntry ::= SEQUENCE {
    cieIfResetCount Counter,
    cieIfKeepAliveEnabled TruthValue,
    cieIfStateChangeReason SnmpAdminString,
    cieIfCarrierTransitionCount Counter,
    cieIfInterfaceDiscontinuityTime TimeStamp,
    cieIfDhcpMode TruthValue,
    cieIfMtu INTEGER,
    cieIfContextName OCTET STRING,
    cieIfOperStatusCause IfOperStatusReason,
    cieIfOperStatusCauseDescr SnmpAdminString,
    cieIfSpeedReceive Gauge,
    cieIfHighSpeedReceive Gauge
    }

cieIfResetCount OBJECT-TYPE
    SYNTAX Counter
    ACCESS read-only
    STATUS mandatory
    DESCRIPTION
        "The number of times the interface was
        internally reset and brought up.
        
        Some of the actions which can cause this
        counter to increment are :
        
        o  Bringing an interface up using the 
           interface CLI command.
        
        o  Clearing the interface with the exec
           CLI command.
        
        o  Bringing the interface up via SNMP.
        
        Discontinuities in the value of this variable
        can occur at re-initialization of the
        management system, and at other times as 
        indicated by the values of 
        cieIfInterfaceDiscontinuityTime."
    ::= { cieIfInterfaceEntry 1 }

cieIfKeepAliveEnabled OBJECT-TYPE
    SYNTAX TruthValue
--    Rsyntax INTEGER {
--        true(1),
--        false(2)
--        }
    ACCESS read-write
    STATUS mandatory
    DESCRIPTION
        "A keepalive is a small, layer-2 message
        that is transmitted by a network device 
        to let directly-connected network devices
        know of its presence.
        
        This object returns 'true' if keepalives
        are enabled on this interface. If keepalives
        are not enabled, 'false' is returned.
        
        Setting this object to TRUE or FALSE enables
        or disables (respectively) keepalive on this 
        interface."
    ::= { cieIfInterfaceEntry 2 }

cieIfStateChangeReason OBJECT-TYPE
    SYNTAX SnmpAdminString
--    Rsyntax OCTET STRING(SIZE(0..255))
    ACCESS read-only
    STATUS mandatory
    DESCRIPTION
        "This object displays a human-readable
        textual string which describes the 
        cause of the last state change of the 
        interface.
        
        Examples of the values this object
        can take are:
        
        o  'Lost Carrier'
        o  'administratively down'
        o  'up'
        o  'down'"
    ::= { cieIfInterfaceEntry 3 }

cieIfCarrierTransitionCount OBJECT-TYPE
    SYNTAX Counter
    ACCESS read-only
    STATUS mandatory
    DESCRIPTION
        "Number of times interface saw the carrier
        signal transition.
        
        For example, if a T1 line is unplugged, 
        then framer will detect the loss of signal 
        (LOS) on the line  and will count it as a
        transition.
        
        Discontinuities in the value of this variable
        can occur at re-initialization of the
        management system, and at other times as 
        indicated by the values of 
        cieIfInterfaceDiscontinuityTime."
    ::= { cieIfInterfaceEntry 4 }

cieIfInterfaceDiscontinuityTime OBJECT-TYPE
    SYNTAX TimeStamp
--    Rsyntax TimeTicks
    ACCESS read-only
    STATUS mandatory
    DESCRIPTION
        "The value of sysUpTime on the most recent
        occasion at which this interface's  counters 
        suffered  a discontinuity. 
        
        If no such discontinuities have occurred 
        since the last re-initialization of the 
        local management subsystem, then this 
        object contains a value of zero."
    ::= { cieIfInterfaceEntry 5 }

cieIfDhcpMode OBJECT-TYPE
    SYNTAX TruthValue
--    Rsyntax INTEGER {
--        true(1),
--        false(2)
--        }
    ACCESS read-write
    STATUS mandatory
    DESCRIPTION
        "The DHCP mode configured by the
        administrator.
        If 'true' the DHCP is enabled. In which
        case an IP address is requested in DHCP.
        This is in addition to any that are 
        configured by the administrator in
        'ciiIPAddressTable' or 'ciiIPIfAddressTable'
        in CISCO-IP-IF-MIB.
        If 'false' the DHCP is disabled. In which
        case all IP addresses are configured by the
        administrator in 'ciiIPAddressTable' or 
        'ciiIPIfAddressTable'.
        For interfaces, for which DHCP cannot be or
        is not supported, then this object has the
        value 'false'."
    DEFVAL { false }
    ::= { cieIfInterfaceEntry 6 }

cieIfMtu OBJECT-TYPE
    SYNTAX INTEGER(40..2147483647)
    ACCESS read-write
    STATUS mandatory
    DESCRIPTION
        "The MTU configured by the administrator.
        This object is exactly same as 'ifMtu' in 
        ifTable from IF-MIB for the same ifIndex
        value , except that it is configurable by the
        administrator. For more description of this
        object refer to 'ifMtu' in IF-MIB."
    DEFVAL { 1500 }
    ::= { cieIfInterfaceEntry 7 }

cieIfContextName OBJECT-TYPE
    SYNTAX OCTET STRING(SIZE(0..32))
    ACCESS read-only
    STATUS mandatory
    DESCRIPTION
        "The ContextName denotes the interface
        'context' and is used to logically separate
        the MIB management.
        RFC 2571 and RFC 2737 describe this approach.
        When the agent supports a different SNMP 
        context, as detailed in RFC 2571 and 
        RFC 2737, for different interfaces, then the
        value of this object specifies the context
        name used for this interface."
    DEFVAL { "" }
    ::= { cieIfInterfaceEntry 8 }

cieIfOperStatusCause OBJECT-TYPE
    SYNTAX IfOperStatusReason
--    Rsyntax INTEGER {
--        other(1),
--        none(2),
--        hwFailure(3),
--        loopbackDiagFailure(4),
--        errorDisabled(5),
--        swFailure(6),
--        linkFailure(7),
--        offline(8),
--        nonParticipating(9),
--        initializing(10),
--        vsanInactive(11),
--        adminDown(12),
--        channelAdminDown(13),
--        channelOperSuspended(14),
--        channelConfigurationInProgress(15),
--        rcfInProgress(16),
--        elpFailureIsolation(17),
--        escFailureIsolation(18),
--        domainOverlapIsolation(19),
--        domainAddrAssignFailureIsolation(20),
--        domainOtherSideEportIsolation(21),
--        domainInvalidRcfReceived(22),
--        domainManagerDisabled(23),
--        zoneMergeFailureIsolation(24),
--        vsanMismatchIsolation(25),
--        parentDown(26),
--        srcPortNotBound(27),
--        interfaceRemoved(28),
--        fcotNotPresent(29),
--        fcotVendorNotSupported(30),
--        incompatibleAdminMode(31),
--        incompatibleAdminSpeed(32),
--        suspendedByMode(33),
--        suspendedBySpeed(34),
--        suspendedByWWN(35),
--        domainMaxReTxFailure(36),
--        eppFailure(37),
--        portVsanMismatchIsolation(38),
--        loopbackIsolation(39),
--        upgradeInProgress(40),
--        incompatibleAdminRxBbCredit(41),
--        incompatibleAdminRxBufferSize(42),
--        portChannelMembersDown(43),
--        zoneRemoteNoRespIsolation(44),
--        firstPortUpAsEport(45),
--        firstPortNotUp(46),
--        peerFCIPPortClosedConnection(47),
--        peerFCIPPortResetConnection(48),
--        fcipPortMaxReTx(49),
--        fcipPortKeepAliveTimerExpire(50),
--        fcipPortPersistTimerExpire(51),
--        fcipPortSrcLinkDown(52),
--        fcipPortSrcAdminDown(53),
--        fcipPortAdminCfgChange(54),
--        fcipSrcPortRemoved(55),
--        fcipSrcModuleNotOnline(56),
--        invalidConfig(57),
--        portBindFailure(58),
--        portFabricBindFailure(59),
--        noCommonVsanIsolation(60),
--        ficonVsanDown(61),
--        invalidAttachment(62),
--        portBlocked(63),
--        incomAdminRxBbCreditPerBuf(64),
--        tooManyInvalidFlogis(65),
--        deniedDueToPortBinding(66),
--        elpFailureRevMismatch(67),
--        elpFailureClassFParamErr(68),
--        elpFailureClassNParamErr(69),
--        elpFailureUnknownFlowCtlCode(70),
--        elpFailureInvalidFlowCtlParam(71),
--        elpFailureInvalidPortName(72),
--        elpFailureInvalidSwitchName(73),
--        elpFailureRatovEdtovMismatch(74),
--        elpFailureLoopbackDetected(75),
--        elpFailureInvalidTxBbCredit(76),
--        elpFailureInvalidPayloadSize(77),
--        bundleMisCfg(78),
--        bitErrRuntimeThreshExceeded(79),
--        linkFailLinkReset(80),
--        linkFailPortInitFail(81),
--        linkFailPortUnusable(82),
--        linkFailLossOfSignal(83),
--        linkFailLossOfSync(84),
--        linkFailNosRcvd(85),
--        linkFailOlsRcvd(86),
--        linkFailDebounceTimeout(87),
--        linkFailLrRcvd(88),
--        linkFailCreditLoss(89),
--        linkFailRxQOverflow(90),
--        linkFailTooManyInterrupts(91),
--        linkFailLipRcvdBb(92),
--        linkFailBbCreditLoss(93),
--        linkFailOpenPrimSignalTimeout(94),
--        linkFailOpenPrimSignalReturned(95),
--        linkFailLipF8Rcvd(96),
--        linkFailLineCardPortShutdown(97),
--        fcspAuthenfailure(98),
--        fcotChecksumError(99),
--        ohmsExtLoopbackTest(100),
--        invalidFabricBindExchange(101),
--        tovMismatch(102),
--        ficonNotEnabled(103),
--        ficonNoPortNumber(104),
--        ficonBeingEnabled(105),
--        ePortProhibited(106),
--        portGracefulShutdown(107),
--        trunkNotFullyActive(108),
--        fabricBindingSwitchWwnNotFound(109),
--        fabricBindingDomainInvalid(110),
--        fabricBindingDbMismatch(111),
--        fabricBindingNoRspFromPeer(112),
--        dpvmVsanSuspended(113),
--        dpvmVsanNotFound(114),
--        trackedPortDown(115),
--        ecSuspendedOnLoop(116),
--        isolateBundleMisCfg(117),
--        noPeerBundleSupport(118),
--        portBringupIsolation(119),
--        domainNotAllowedIsolated(120),
--        virtualIvrDomainOverlapIsolation(121),
--        outOfService(122),
--        portAuthFailed(123),
--        bundleStandby(124),
--        portConnectorTypeErr(125),
--        errorDisabledReInitLmtReached(126),
--        ficonDupPortNum(127),
--        localRcf(128),
--        twoSwitchesWithSameWWN(129),
--        invalidOtherSidePrincEFPReqRecd(130),
--        domainOther(131),
--        elpFailureAllZeroPeerWWNRcvd(132),
--        preferredPathIsolation(133)
--        }
    ACCESS read-only
    STATUS mandatory
    DESCRIPTION
        "This object represents the detailed
        operational cause reason for the current 
        operational state of the interface. 
        The current operational state of the interface 
        is given by the 'ifOperStatus' defined 
        in IF-MIB. 
        
        The corresponding instance of 
        'cieIfOperStatusCauseDescr' must be used to 
        get the information about the operational 
        cause value mentioned in this object.
        
        For interfaces whose 'ifOperStatus' is 'down' 
        the objects 'cieIfOperStatusCause' and 
        'cieIfOperStatusCauseDescr' together provides 
        the information about the operational cause 
        reason and the description of the cause. 
        
        The value of this object will be 'none' for
        all the 'ifOperStatus' values except for 
        'down'. Its value will be one status cause 
        defined in the 'IfOperStatusReason' textual 
        convention if 'ifOperStatus' is 'down'. 
        
        The value of this object will be 'other' 
        if the operational status cause is not one 
        defined in 'IfOperStatusReason'."
    ::= { cieIfInterfaceEntry 9 }

cieIfOperStatusCauseDescr OBJECT-TYPE
    SYNTAX SnmpAdminString
--    Rsyntax OCTET STRING(SIZE(0..255))
    ACCESS read-only
    STATUS mandatory
    DESCRIPTION
        "The description for the cause of current
        operational state of the interface, given 
        by the object 'cieIfOperStatusCause'.
        
        For an interface whose 'ifOperStatus' is not
        'down' the value of this object will be 
        'none'."
    ::= { cieIfInterfaceEntry 10 }

cieIfSpeedReceive OBJECT-TYPE
    SYNTAX Gauge
    ACCESS read-only
    STATUS mandatory
    DESCRIPTION
        "An estimate of the interface's current receive bandwidth in
        bits per second.  This object is provided for interface with
        asymmetric interface speeds like ADSL and should be used in
        conjunction with ifSpeed object.  For interfaces which do not
        vary in bandwidth or for those where no accurate estimation can
        be made, this object should contain the nominal bandwidth. If
        the bandwidth of the interface is greater than the maximum value
        reportable by this object then this object should report its
        maximum value (4,294,967,295) and ifHighSpeed must be used to
        report the interace's speed.  For a sub-layer which has no
        concept of bandwidth, this object should be zero."
    ::= { cieIfInterfaceEntry 11 }

cieIfHighSpeedReceive OBJECT-TYPE
    SYNTAX Gauge
    ACCESS read-only
    STATUS mandatory
    DESCRIPTION
        "An estimate of the interface's current receive bandwidth in
        units of 1,000,000 bits per second.  If this object reports a
        value of `n' then the speed of the interface is somewhere in the
        range of `n-500,000' to `n+499,999'.  For interfaces which do
        not vary in bandwidth or for those where no accurate estimation
        can be made, this object should contain the nominal bandwidth. 
        For a sub-layer which has no concept of bandwidth, this object
        should be zero."
    ::= { cieIfInterfaceEntry 12 }

cieIfStatusListTable OBJECT-TYPE
    SYNTAX SEQUENCE OF CieIfStatusListEntry
    ACCESS not-accessible
    STATUS mandatory
    DESCRIPTION
        "This table contains objects for providing
        the 'ifIndex', interface operational mode and 
        interface operational cause for all the 
        interfaces in the modules.
        
        This table contains one entry for each 
        64 interfaces in an module.
        
        This table provides efficient way of encoding 
        'ifIndex', interface operational mode and
        interface operational cause, from the point 
        of retrieval, by combining the values a set 
        of 64 interfaces in a single MIB object."
    ::= { ciscoIfExtensionStats 3 }

cieIfStatusListEntry OBJECT-TYPE
    SYNTAX CieIfStatusListEntry
    ACCESS not-accessible
    STATUS mandatory
    DESCRIPTION
        "Each entry represents the 'ifIndex',
        interface operational mode and interface 
        operational cause for a set of 64 interfaces 
        in a module."
    INDEX { entPhysicalIndex, cieIfStatusListIndex }
    ::= { cieIfStatusListTable 1 }

CieIfStatusListEntry ::= SEQUENCE {
    cieIfStatusListIndex Gauge,
    cieInterfacesIndex InterfaceIndexList,
    cieInterfacesOperMode InterfaceOperModeList,
    cieInterfacesOperCause InterfaceOperCauseList
    }

cieIfStatusListIndex OBJECT-TYPE
    SYNTAX Gauge(1..33554432)
    ACCESS not-accessible
    STATUS mandatory
    DESCRIPTION
        "An arbitrary integer value, greater than
        zero, which identifies a list of 64 interfaces
        within a module."
    ::= { cieIfStatusListEntry 1 }

cieInterfacesIndex OBJECT-TYPE
    SYNTAX InterfaceIndexList
--    Rsyntax OCTET STRING(SIZE(0..256))
    ACCESS read-only
    STATUS mandatory
    DESCRIPTION
        "This object represents the 'ifIndex' for a
        set of 64 interfaces in the module."
    ::= { cieIfStatusListEntry 2 }

cieInterfacesOperMode OBJECT-TYPE
    SYNTAX InterfaceOperModeList
--    Rsyntax OCTET STRING(SIZE(0..64))
    ACCESS read-only
    STATUS mandatory
    DESCRIPTION
        "This object represents the operational mode
        for a set of 64 interfaces in the module."
    ::= { cieIfStatusListEntry 3 }

cieInterfacesOperCause OBJECT-TYPE
    SYNTAX InterfaceOperCauseList
--    Rsyntax OCTET STRING(SIZE(0..128))
    ACCESS read-only
    STATUS mandatory
    DESCRIPTION
        "This object represents the operational status
        cause for a set of 64 interfaces in the 
        module."
    ::= { cieIfStatusListEntry 4 }

cieSystemMtu OBJECT-TYPE
    SYNTAX INTEGER
    ACCESS read-write
    STATUS mandatory
    DESCRIPTION
        "Global system MTU in octets.
        This object specifies the MTU on all interfaces.
        However, the value specified by cieIfMtu
        takes precedence for an interface, which means
        that the interface's MTU uses the value
        specified by cieIfMtu, if it is configured."
    DEFVAL { 1500 }
    ::= { ciscoIfExtSystemConfig 1 }

cieLinkUpDownEnable OBJECT-TYPE
    SYNTAX OCTET STRING(SIZE(1..2))
        -- BITS are:
        --   standard(0)
        --   cisco(1)
    ACCESS read-write
    STATUS mandatory
    DESCRIPTION
        "Indicates whether cieLinkUp/cieLinkDown
        or standard mib-II defined linkUp/Down or
        both, notifications should be generated
        for the interfaces in the system.
        
        'standard'  - only generate standard defined
                      mib-II linkUp/linkDown notification
                      if 'ifLinkUpDownTrapEnable' for 
                      the interface is 'enabled'.
        'cisco'     - only generate cieLinkUp/cieLinkDown
                      notifications for an interface if
                      the 'ifLinkUpDownTrapEnable' for the
                      interface is 'enabled'.
        
        If both bits are selected then linkUp/linkDown and
        cieLinkUp/cieLinkDown are both generated for an 
        interface if the 'ifLinkUpDownTrapEnable' for the
        interface is 'enabled'."
    DEFVAL { '80'h }
    ::= { ciscoIfExtSystemConfig 2 }

cieStandardLinkUpDownVarbinds OBJECT-TYPE
    SYNTAX INTEGER {
        standard(1),
        additional(2)
        }
    ACCESS read-write
    STATUS mandatory
    DESCRIPTION
        "Indicates whether to send the extra
        varbinds in addition to the varbinds defined 
        in linkUp/linkDown notifications.
        
        'standard'   - only send the varbinds defined in
                       the standard linkUp/linkDown
                       notification.  
        'additional' - send the extra varbinds in addition 
                       to the defined ones."
    DEFVAL { additional }
    ::= { ciscoIfExtSystemConfig 3 }

cieIfDot1qCustomEtherTypeTable OBJECT-TYPE
    SYNTAX SEQUENCE OF CieIfDot1qCustomEtherTypeEntry
    ACCESS not-accessible
    STATUS mandatory
    DESCRIPTION
        "A list of the interfaces that support
        the 802.1q custom Ethertype feature."
    ::= { ciscoIfExtDot1qCustomEtherType 1 }

cieIfDot1qCustomEtherTypeEntry OBJECT-TYPE
    SYNTAX CieIfDot1qCustomEtherTypeEntry
    ACCESS not-accessible
    STATUS mandatory
    DESCRIPTION
        "An entry containing the custom EtherType
        information for the interface.
        
        Only interfaces with custom 802.1q
        ethertype control are listed in the 
        table."
    INDEX { ifIndex }
    ::= { cieIfDot1qCustomEtherTypeTable 1 }

CieIfDot1qCustomEtherTypeEntry ::= SEQUENCE {
    cieIfDot1qCustomAdminEtherType INTEGER,
    cieIfDot1qCustomOperEtherType INTEGER
    }

cieIfDot1qCustomAdminEtherType OBJECT-TYPE
    SYNTAX INTEGER(0..65535)
    ACCESS read-write
    STATUS mandatory
    DESCRIPTION
        "The Dot1qEtherType allow administrator
        to select a non-standard (other than 0x8100)
        2-byte ethertype for the interface to 
        interoperate with third party vendor's system
        that do not use the standard 0x8100 ethertype
        to identify 802.1q-tagged frames.
        
        The current administrative value of the 
        802.1q ethertype for the interface.  The
        administrative 802.1q ethertype value may 
        differ from the operational 802.1q ethertype
        value.  On some platforms, 802.1q ethertype
        may be assigned per group rather than per port.
        If multiple ports belong to a port group,
        the 802.1q ethertype assigned to any of
        the ports in such group will apply to all
        ports in the same group.
        
        To configure non-standard dot1q ethertype
        is only recommended when the Cisco device
        is connected to any third party vendor device.
        Also be advised that the custom ethertype value
        needs to be changed in the whole cloud of 
        Cisco device with the same custom ethertype 
        value if the third party device are separated 
        by number of Cisco device in the middle."
    ::= { cieIfDot1qCustomEtherTypeEntry 1 }

cieIfDot1qCustomOperEtherType OBJECT-TYPE
    SYNTAX INTEGER(0..65535)
    ACCESS read-only
    STATUS mandatory
    DESCRIPTION
        "The current operational value of the
        802.1q ethertype for the interface."
    ::= { cieIfDot1qCustomEtherTypeEntry 2 }

cieIfUtilTable OBJECT-TYPE
    SYNTAX SEQUENCE OF CieIfUtilEntry
    ACCESS not-accessible
    STATUS mandatory
    DESCRIPTION
        "This table contains the interface utilization
        rates for inbound and outbound traffic on an
        interface."
    ::= { ciscoIfExtUtilization 1 }

cieIfUtilEntry OBJECT-TYPE
    SYNTAX CieIfUtilEntry
    ACCESS not-accessible
    STATUS mandatory
    DESCRIPTION
        "An entry containing utilization rates for the
        interface.
        
        Every interface for which the  inbound and 
        outbound traffic information is available
        has a corresponding entry in this table."
    INDEX { ifIndex }
    ::= { cieIfUtilTable 1 }

CieIfUtilEntry ::= SEQUENCE {
    cieIfInPktRate Unsigned64,
    cieIfInOctetRate Unsigned64,
    cieIfOutPktRate Unsigned64,
    cieIfOutOctetRate Unsigned64,
    cieIfInterval Gauge
    }

cieIfInPktRate OBJECT-TYPE
    SYNTAX --?? syntax is not convertable to SMIv1
           Unsigned64
--    Rsyntax Counter64
--  Units
--    packets per second
    ACCESS read-only
    STATUS mandatory
    DESCRIPTION
        "By default, this is the five minute
        exponentially-decayed moving average of the
        inbound packet rate for this interface.
        However, if the corresponding instance of
        cieIfInterval is instantiated with a value
        which specifies an interval different from
        5-minutes, then cieIfInPktRate is the
        exponentially-decayed moving average of inbound
        packet rate over this different time interval."
    ::= { cieIfUtilEntry 1 }

cieIfInOctetRate OBJECT-TYPE
    SYNTAX --?? syntax is not convertable to SMIv1
           Unsigned64
--    Rsyntax Counter64
--  Units
--    octets per second
    ACCESS read-only
    STATUS mandatory
    DESCRIPTION
        "By default, this is the five minute
        exponentially-decayed moving average of the
        inbound octet rate for this interface.
        However, if the corresponding instance of
        cieIfInterval is instantiated with a value
        which specifies an interval different from
        5-minutes, then cieIfInOctetRate is the
        exponentially-decayed moving average of inbound
        octet rate over this different time interval."
    ::= { cieIfUtilEntry 2 }

cieIfOutPktRate OBJECT-TYPE
    SYNTAX --?? syntax is not convertable to SMIv1
           Unsigned64
--    Rsyntax Counter64
--  Units
--    packets per second
    ACCESS read-only
    STATUS mandatory
    DESCRIPTION
        "By default, this is the five minute
        exponentially-decayed moving average of the
        outbound packet rate for this interface.
        However, if the corresponding instance of
        cieIfInterval is instantiated with a value
        which specifies an interval different from
        5-minutes, then cieIfOutPktRate is the
        exponentially-decayed moving average of outbound
        packet rate over this different time interval."
    ::= { cieIfUtilEntry 3 }

cieIfOutOctetRate OBJECT-TYPE
    SYNTAX --?? syntax is not convertable to SMIv1
           Unsigned64
--    Rsyntax Counter64
--  Units
--    octets per second
    ACCESS read-only
    STATUS mandatory
    DESCRIPTION
        "By default, this is the five minute
        exponentially-decayed moving average of the
        outbound octet rate for this interface.
        However, if the corresponding instance of
        cieIfInterval is instantiated with a value
        which specifies an interval different from
        5-minutes, then cieIfOutOctetRate is the
        exponentially-decayed moving average of outbound
        octet rate over this different time interval."
    ::= { cieIfUtilEntry 4 }

cieIfInterval OBJECT-TYPE
    SYNTAX Gauge(1..4294967295)
--  Units
--    seconds
    ACCESS read-write
    STATUS mandatory
    DESCRIPTION
        "This object specifies the time interval over which
        the inbound and outbound traffic rates are
        calculated for this interface."
    ::= { cieIfUtilEntry 5 }

cieIfDot1dBaseMappingTable OBJECT-TYPE
    SYNTAX SEQUENCE OF CieIfDot1dBaseMappingEntry
    ACCESS not-accessible
    STATUS mandatory
    DESCRIPTION
        "This table contains the mappings of the
        ifIndex of an interface to its
        corresponding dot1dBasePort value."
    REFERENCE
        "dot1dBasePort is defined in BRIDGE-MIB."
    ::= { ciscoIfExtDot1dBaseMapping 1 }

cieIfDot1dBaseMappingEntry OBJECT-TYPE
    SYNTAX CieIfDot1dBaseMappingEntry
    ACCESS not-accessible
    STATUS mandatory
    DESCRIPTION
        "An entry containing the mapping between
        the ifIndex value of an interface and its
        corresponding dot1dBasePort value.
        
        Every interface which has been assigned
        a dot1dBasePort value by the system
        has a corresponding entry in this table."
    REFERENCE
        "dot1dBasePort is defined in BRIDGE-MIB."
    INDEX { ifIndex }
    ::= { cieIfDot1dBaseMappingTable 1 }

CieIfDot1dBaseMappingEntry ::= SEQUENCE {
    cieIfDot1dBaseMappingPort INTEGER
    }

cieIfDot1dBaseMappingPort OBJECT-TYPE
    SYNTAX INTEGER(1..65535)
    ACCESS read-only
    STATUS mandatory
    DESCRIPTION
        "The dot1dBasePort value for this interface."
    REFERENCE
        "dot1dBasePort is defined in BRIDGE-MIB."
    ::= { cieIfDot1dBaseMappingEntry 1 }

cieIfNameMappingTable OBJECT-TYPE
    SYNTAX SEQUENCE OF CieIfNameMappingEntry
    ACCESS not-accessible
    STATUS mandatory
    DESCRIPTION
        "This table contains objects for providing
        the 'ifName' to 'ifIndex' mapping.
        This table contains one entry for each
        valid 'ifName' available in the system.
        Upon the first request, the implementation
        of this table will get all the available
        ifNames, and it will populate the entries
        in this table, it maintains this ifNames
        in a cache for ~30 seconds."
    ::= { ciscoIfExtIfNameMapping 1 }

cieIfNameMappingEntry OBJECT-TYPE
    SYNTAX CieIfNameMappingEntry
    ACCESS not-accessible
    STATUS mandatory
    DESCRIPTION
        "An entry into the cieIfNameMappingTable."
    INDEX { cieIfName }
    ::= { cieIfNameMappingTable 1 }

CieIfNameMappingEntry ::= SEQUENCE {
    cieIfName DisplayString,
    cieIfIndex InterfaceIndexOrZero
    }

cieIfName OBJECT-TYPE
    SYNTAX DisplayString(SIZE(1..112))
--    Rsyntax OCTET STRING(SIZE(1..112))
    ACCESS not-accessible
    STATUS mandatory
    DESCRIPTION
        "Represents an interface name mentioned
        in the 'ifName' object of this system."
    ::= { cieIfNameMappingEntry 1 }

cieIfIndex OBJECT-TYPE
    SYNTAX InterfaceIndexOrZero
--    Rsyntax INTEGER(0..2147483647)
    ACCESS read-only
    STATUS mandatory
    DESCRIPTION
        "This object represents the 'ifIndex'
        corresponding to the interface name mentioned
        in the 'cieIfName' object of this instance.
        If the 'ifName' mentioned in the 'cieIfName' 
        object of this instance corresponds to multiple
        'ifIndex' values, then the value of this object
        is the numerically smallest of those multiple 
        'ifIndex' values."
    ::= { cieIfNameMappingEntry 2 }

cieLinkDown TRAP-TYPE
-- Reverse mappable trap
    ENTERPRISE ciscoIfExtensionMIB
    VARIABLES {
        ifIndex, ifAdminStatus, ifOperStatus, ifName, ifType }
--  Status
--    mandatory
    DESCRIPTION
        "A cisco specific linkDown notification
        signifies that the SNMP entity, acting in an
        agent role, has detected that the ifOperStatus
        object for one of its communication links is
        about to enter the down state from some other
        state (but not from the notPresent state).
        The varbinds for this notification indicate the
        interface information of the communication
        link."
    ::= 1

cieLinkUp TRAP-TYPE
-- Reverse mappable trap
    ENTERPRISE ciscoIfExtensionMIB
    VARIABLES {
        ifIndex, ifAdminStatus, ifOperStatus, ifName, ifType }
--  Status
--    mandatory
    DESCRIPTION
        "A cisco specific linkUp trap signifies that
        the SNMP entity, acting in an agent role, has
        detected that the ifOperStatus object for one
        of its communication links left the down state
        and transitioned into some other state (but not
        into the notPresent state). The varbinds for
        this notification indicate the interface
        information of the communication link."
    ::= 2

ciscoIfExtensionTablePacketGroup OBJECT IDENTIFIER ::= { ciscoIfExtensionMIBGroups 1 }
-- OBJECT-GROUP
--  Status
--    mandatory
--  Descr
--    A collection of objects containing packet
--    statistics for a given interface.
--  objects
--    cieIfLastInTime, cieIfLastOutTime, cieIfLastOutHangTime, 
--    cieIfInRuntsErrs, cieIfInGiantsErrs, cieIfInFramingErrs, 
--    cieIfInOverrunErrs, cieIfInIgnored, cieIfInAbortErrs, 
--    cieIfInputQueueDrops, cieIfOutputQueueDrops, 
--    cieIfPacketDiscontinuityTime

ciscoIfExtensionTableIntfGroup OBJECT IDENTIFIER ::= { ciscoIfExtensionMIBGroups 2 }
-- OBJECT-GROUP
--  Status
--    mandatory
--  Descr
--    A collection of objects containing
--    information about properties of 
--    interfaces.
--  objects
--    cieIfResetCount, cieIfKeepAliveEnabled, 
--    cieIfStateChangeReason, cieIfCarrierTransitionCount, 
--    cieIfInterfaceDiscontinuityTime

ciscoIfExtensionTableIntfGroup1 OBJECT IDENTIFIER ::= { ciscoIfExtensionMIBGroups 3 }
-- OBJECT-GROUP
--  Status
--    deprecated
--  Descr
--    A collection of objects containing
--    information about properties of 
--    interfaces.
--  objects
--    cieIfDhcpMode, cieIfMtu, cieIfContextName

ciscoIfExtensionSystemGroup OBJECT IDENTIFIER ::= { ciscoIfExtensionMIBGroups 4 }
-- OBJECT-GROUP
--  Status
--    mandatory
--  Descr
--    A collection of objects providing
--    global system-wise information about
--    interfaces.
--  objects
--    cieSystemMtu

ciscoIfExtDot1qEtherTypeGroup OBJECT IDENTIFIER ::= { ciscoIfExtensionMIBGroups 5 }
-- OBJECT-GROUP
--  Status
--    mandatory
--  Descr
--    A collection of objects providing
--    the information about 802.1q 
--    custom EtherType on the 
--    interface.
--  objects
--    cieIfDot1qCustomAdminEtherType, cieIfDot1qCustomOperEtherType

ciscoIfExtUtilizationGroup OBJECT IDENTIFIER ::= { ciscoIfExtensionMIBGroups 6 }
-- OBJECT-GROUP
--  Status
--    mandatory
--  Descr
--    A collection of objects containing
--    information about utilization rates of
--    interfaces.
--  objects
--    cieIfInPktRate, cieIfInOctetRate, cieIfOutPktRate, 
--    cieIfOutOctetRate

ciscoIfExtDot1dBaseMappingGroup OBJECT IDENTIFIER ::= { ciscoIfExtensionMIBGroups 7 }
-- OBJECT-GROUP
--  Status
--    mandatory
--  Descr
--    A collection of objects containing
--    mapping information about the ifIndex values
--    of interfaces and their dot1dBasePort 
--    values.
--  objects
--    cieIfDot1dBaseMappingPort

ciscoIfExtIfNameMappingGroup OBJECT IDENTIFIER ::= { ciscoIfExtensionMIBGroups 8 }
-- OBJECT-GROUP
--  Status
--    mandatory
--  Descr
--    A collection of objects for the
--    'ifName' to 'ifIndex' mapping.
--  objects
--    cieIfIndex

ciscoIfExtensionTableIntfGroup2 OBJECT IDENTIFIER ::= { ciscoIfExtensionMIBGroups 9 }
-- OBJECT-GROUP
--  Status
--    mandatory
--  Descr
--    A collection of objects containing
--    information about properties of 
--    interfaces.
--  objects
--    cieIfDhcpMode, cieIfMtu, cieIfContextName, 
--    cieIfOperStatusCause, cieIfOperStatusCauseDescr

cieIfStatusListGroup OBJECT IDENTIFIER ::= { ciscoIfExtensionMIBGroups 10 }
-- OBJECT-GROUP
--  Status
--    mandatory
--  Descr
--    A collection of objects containing
--    information about set of interfaces.
--  objects
--    cieInterfacesIndex, cieInterfacesOperMode, 
--    cieInterfacesOperCause

cieLinkUpDownNotifEnableGroup OBJECT IDENTIFIER ::= { ciscoIfExtensionMIBGroups 11 }
-- OBJECT-GROUP
--  Status
--    mandatory
--  Descr
--    A collection of objects to control
--    'cieLinkUp/cieLinkDown' and standard mib-II 
--    defined 'linkUp/linkDown' notifications.
--  objects
--    cieLinkUpDownEnable, cieStandardLinkUpDownVarbinds

ciscoIfExtensionAsymmetricalSpeedGroup OBJECT IDENTIFIER ::= { ciscoIfExtensionMIBGroups 13 }
-- OBJECT-GROUP
--  Status
--    mandatory
--  Descr
--    An optional group used to provide information on asymmetrical
--    interface speeds.
--  objects
--    cieIfSpeedReceive, cieIfHighSpeedReceive

ciscoIfExtUtilIntervalGroup OBJECT IDENTIFIER ::= { ciscoIfExtensionMIBGroups 14 }
-- OBJECT-GROUP
--  Status
--    mandatory
--  Descr
--    A collection of objects containing
--    information about calculation interval for 
--    utilization rate on interfaces.
--  objects
--    cieIfInterval

cieLinkUpDownNotifGroup OBJECT IDENTIFIER ::= { ciscoIfExtensionMIBGroups 12 }
-- NOTIFICATION-GROUP
--  Status
--    mandatory
--  Descr
--    A collection of cisco specific linkUp and
--    linkDown notifications.
--  notifications
--    cieLinkDown, cieLinkUp

ciscoIfExtensionMIBCompliance OBJECT IDENTIFIER ::= { ciscoIfExtensionMIBCompliances 1 }
-- MODULE-COMPLIANCE
--  Status
--    deprecated
--  Descr
--    The compliance statement for entities which
--    implement the CISCO-IF-EXTENSION-MIB.
--  Module
--    >>current<<
--   MandGroup
--    ciscoIfExtensionTablePacketGroup
--   MandGroup
--    ciscoIfExtensionTableIntfGroup

ciscoIfExtensionMIBCompliance1 OBJECT IDENTIFIER ::= { ciscoIfExtensionMIBCompliances 2 }
-- MODULE-COMPLIANCE
--  Status
--    deprecated
--  Descr
--    The compliance statement for entities which
--    implement the CISCO-IF-EXTENSION-MIB.
--  Module
--    >>current<<
--   OptGroup
--    ciscoIfExtensionTablePacketGroup
--   OptGroup
--    ciscoIfExtensionTableIntfGroup
--   OptGroup
--    ciscoIfExtensionTableIntfGroup1
--   OptGroup
--    ciscoIfExtensionSystemGroup
--   OptGroup
--    ciscoIfExtDot1qEtherTypeGroup
--   ObjVar
--    cieIfDhcpMode
--   ObjVar
--    cieIfMtu

ciscoIfExtensionMIBCompliance2 OBJECT IDENTIFIER ::= { ciscoIfExtensionMIBCompliances 3 }
-- MODULE-COMPLIANCE
--  Status
--    deprecated
--  Descr
--    The compliance statement for entities which
--    implement the CISCO-IF-EXTENSION-MIB.
--  Module
--    >>current<<
--   OptGroup
--    ciscoIfExtensionTablePacketGroup
--   OptGroup
--    ciscoIfExtensionTableIntfGroup
--   OptGroup
--    ciscoIfExtensionTableIntfGroup1
--   OptGroup
--    ciscoIfExtensionSystemGroup
--   OptGroup
--    ciscoIfExtDot1qEtherTypeGroup
--   OptGroup
--    ciscoIfExtUtilizationGroup
--   OptGroup
--    ciscoIfExtDot1dBaseMappingGroup
--   ObjVar
--    cieIfDhcpMode
--   ObjVar
--    cieIfMtu

ciscoIfExtensionMIBCompliance3 OBJECT IDENTIFIER ::= { ciscoIfExtensionMIBCompliances 4 }
-- MODULE-COMPLIANCE
--  Status
--    deprecated
--  Descr
--    The compliance statement for entities which
--    implement the CISCO-IF-EXTENSION-MIB.
--  Module
--    >>current<<
--   OptGroup
--    ciscoIfExtensionTablePacketGroup
--   OptGroup
--    ciscoIfExtensionTableIntfGroup
--   OptGroup
--    ciscoIfExtensionTableIntfGroup1
--   OptGroup
--    ciscoIfExtensionSystemGroup
--   OptGroup
--    ciscoIfExtDot1qEtherTypeGroup
--   OptGroup
--    ciscoIfExtUtilizationGroup
--   OptGroup
--    ciscoIfExtDot1dBaseMappingGroup
--   OptGroup
--    ciscoIfExtIfNameMappingGroup
--   ObjVar
--    cieIfDhcpMode
--   ObjVar
--    cieIfMtu

ciscoIfExtensionMIBCompliance4 OBJECT IDENTIFIER ::= { ciscoIfExtensionMIBCompliances 5 }
-- MODULE-COMPLIANCE
--  Status
--    deprecated
--  Descr
--    The compliance statement for entities which
--    implement the CISCO-IF-EXTENSION-MIB.
--  Module
--    >>current<<
--   OptGroup
--    ciscoIfExtensionTablePacketGroup
--   OptGroup
--    ciscoIfExtensionTableIntfGroup
--   OptGroup
--    ciscoIfExtensionTableIntfGroup2
--   OptGroup
--    ciscoIfExtensionSystemGroup
--   OptGroup
--    ciscoIfExtDot1qEtherTypeGroup
--   OptGroup
--    ciscoIfExtUtilizationGroup
--   OptGroup
--    ciscoIfExtDot1dBaseMappingGroup
--   OptGroup
--    ciscoIfExtIfNameMappingGroup
--   OptGroup
--    cieIfStatusListGroup
--   ObjVar
--    cieIfDhcpMode
--   ObjVar
--    cieIfMtu

ciscoIfExtensionMIBCompliance5 OBJECT IDENTIFIER ::= { ciscoIfExtensionMIBCompliances 6 }
-- MODULE-COMPLIANCE
--  Status
--    deprecated
--  Descr
--    The compliance statement for entities which
--    implement the CISCO-IF-EXTENSION-MIB.
--  Module
--    >>current<<
--   OptGroup
--    ciscoIfExtensionTablePacketGroup
--   OptGroup
--    ciscoIfExtensionTableIntfGroup
--   OptGroup
--    ciscoIfExtensionTableIntfGroup2
--   OptGroup
--    ciscoIfExtensionSystemGroup
--   OptGroup
--    ciscoIfExtDot1qEtherTypeGroup
--   OptGroup
--    ciscoIfExtUtilizationGroup
--   OptGroup
--    ciscoIfExtDot1dBaseMappingGroup
--   OptGroup
--    ciscoIfExtIfNameMappingGroup
--   OptGroup
--    cieIfStatusListGroup
--   OptGroup
--    cieLinkUpDownNotifEnableGroup
--   OptGroup
--    cieLinkUpDownNotifGroup
--   ObjVar
--    cieIfDhcpMode
--   ObjVar
--    cieIfMtu

ciscoIfExtensionMIBCompliance6 OBJECT IDENTIFIER ::= { ciscoIfExtensionMIBCompliances 7 }
-- MODULE-COMPLIANCE
--  Status
--    deprecated
--  Descr
--    The compliance statement for entities which
--    implement the CISCO-IF-EXTENSION-MIB.
--  Module
--    >>current<<
--   OptGroup
--    ciscoIfExtensionTablePacketGroup
--   OptGroup
--    ciscoIfExtensionTableIntfGroup
--   OptGroup
--    ciscoIfExtensionTableIntfGroup2
--   OptGroup
--    ciscoIfExtensionSystemGroup
--   OptGroup
--    ciscoIfExtDot1qEtherTypeGroup
--   OptGroup
--    ciscoIfExtUtilizationGroup
--   OptGroup
--    ciscoIfExtDot1dBaseMappingGroup
--   OptGroup
--    ciscoIfExtIfNameMappingGroup
--   OptGroup
--    cieIfStatusListGroup
--   OptGroup
--    cieLinkUpDownNotifEnableGroup
--   OptGroup
--    cieLinkUpDownNotifGroup
--   OptGroup
--    ciscoIfExtensionAsymmetricalSpeedGroup
--   ObjVar
--    cieIfDhcpMode
--   ObjVar
--    cieIfMtu

ciscoIfExtensionMIBCompliance7 OBJECT IDENTIFIER ::= { ciscoIfExtensionMIBCompliances 8 }
-- MODULE-COMPLIANCE
--  Status
--    mandatory
--  Descr
--    The compliance statement for entities which
--    implement the CISCO-IF-EXTENSION-MIB.
--  Module
--    >>current<<
--   OptGroup
--    ciscoIfExtensionTablePacketGroup
--   OptGroup
--    ciscoIfExtensionTableIntfGroup
--   OptGroup
--    ciscoIfExtensionTableIntfGroup2
--   OptGroup
--    ciscoIfExtensionSystemGroup
--   OptGroup
--    ciscoIfExtDot1qEtherTypeGroup
--   OptGroup
--    ciscoIfExtUtilizationGroup
--   OptGroup
--    ciscoIfExtDot1dBaseMappingGroup
--   OptGroup
--    ciscoIfExtIfNameMappingGroup
--   OptGroup
--    cieIfStatusListGroup
--   OptGroup
--    cieLinkUpDownNotifEnableGroup
--   OptGroup
--    cieLinkUpDownNotifGroup
--   OptGroup
--    ciscoIfExtensionAsymmetricalSpeedGroup
--   OptGroup
--    ciscoIfExtUtilIntervalGroup
--   ObjVar
--    cieIfDhcpMode
--   ObjVar
--    cieIfMtu


END
