-- MIB file created 22-May-2008 22:06:23, by
--   SMICng version 2.2.11-beta(PRO)(Solaris), January 20, 2001. Enterprise key cisco.com

CISCO-STACK-MIB DEFINITIONS ::= BEGIN

-- From file: "CISCO-STACK-MIB.my"
-- Compile options "4 7 F H N O W 03 06 0B 0G 0N 0T"

IMPORTS
    DisplayString, RowStatus, TruthValue, MacAddress
            FROM SNMPv2-TC-v1
    fddimibPORTSMTIndex, fddimibPORTIndex
            FROM FDDI-SMT73-MIB
    OwnerString, ifName, ifIndex
            FROM IF-MIB
    workgroup
            FROM CISCO-SMI
    ringStationMacAddress
            FROM TOKEN-RING-RMON-MIB
    PhysicalIndex
            FROM ENTITY-MIB
    VlanIndex
            FROM CISCO-VTP-MIB
    Counter, Gauge, IpAddress, TimeTicks
            FROM RFC1155-SMI
    OBJECT-TYPE
            FROM RFC-1212
    TRAP-TYPE
            FROM RFC-1215;

ciscoStackMIB OBJECT IDENTIFIER ::= { workgroup 1 }
-- MODULE-IDENTITY
--  LastUpdated
--    200712120000Z
--  OrgName
--    Cisco Systems, Inc.
--  ContactInfo
--           Cisco Systems
--            Customer Service
--    
--    Postal: 170 W Tasman Drive
--            San Jose, CA  95134
--            USA
--    
--       Tel: +1 800 553-NETS
--    
--    E-mail: cs-wbu@cisco.com,
--            cs-lan-switch-snmp@cisco.com
--  Descr
--    This MIB provides configuration and runtime status for
--     chassis, modules, ports, etc. on the Catalyst systems.
--  RevDate
--    200712120000Z
--  RevDescr
--    Modified chassisSysType for new hardwares:
--    'wsc6509ve'.
--    
--    Modified chassisComponentType for new hardwares:
--    'wsc6509veFan'.
--    
--    Modified chassisPs1Type and chassisPs2Type to include:
--    'pwr6000dc', 'pwr4500dc'.
--    
--    Modified moduleType to include:
--    'wssup32pge', 'wssup32p10ge', 'wssvcpisa32', 'wsf6kmsfc2a',
--    'wsSvcMwam1', 'wsSvcPsd1', 'wsSvcSamiBb', 'vss72010g',
--    'wsx671610ge'.
--    
--    Modified moduleSubType to include new hardwares:
--    'vsf6kpfc3cxl', 'vsf6kpfc3c'.
--    
--    Modified moduleSubType2 to include new hardwares:
--    'vsf6kmsfc3', 'me6524msfc2a', 'wssvcpisa32'.
--    
--    Modified portType to include:
--    'intrusionProtect', 'e1000BaseSvc', 'e10GBaseSvc',
--    'e10GBaseLRM', 'e10GBaseT'.
--    
--    Modified syslogMessageFacility to include:
--    'dom', 'mvrp'.
--    
--    Added ipPermitGroup3.
--  RevDate
--    200705290000Z
--  RevDescr
--    Modified moduleType to include 'wsx6066SlbSk9'.
--  RevDate
--    200705250000Z
--  RevDescr
--    Updated chassisPs1Type and chassisPs2Type to include:
--    'pwr1500dc'.
--    
--    Modified moduleType to include:
--    'osm12t3e3', 'osm4GeWanGbicPlus', 'm7600Sip600',
--    'm7600Sip200', 'm7600Sip400', 'c7600ssc400',
--    'c7600ssc600', 'esm2x10ge', 'rsp720', 'rsp720base', 
--    'c7600msfc4'.
--    
--    Updated moduleSubType to include new hardwares:
--    'm7600pfc3c', 'sip600earl', 'c7600esmdfc3cxl',
--    'c7600esmdfc3c'.
--    
--    Updated moduleSubType2 to include new hardwares:
--    'esm2x10ge', 'c7600msfc4'.
--  RevDate
--    200703300000Z
--  RevDescr
--    Modified chassisSysType to include:
--    'mec6524gs8s', 'mec6524gt8s', 'cisco7603s'.
--    
--    Updated chassisPs1Type and chassisPs2Type to include:
--    'pwr400dc', 'pwr400ac'.
--    
--    Updated chassisComponentType for new hardwares:
--    'fan6524', 'fanMod6Shs', 'fanMod9Shs', 'fanMod9St',
--    'fanMod3Hs'.
--    
--    Modified moduleType to include:
--    'mec6524gs8s', 'mec6524gt8s', 'me6524msfc2a',
--    'wsx670810ge'.
--    
--    Updated moduleSubType to include new hardwares:
--    'mec6524pfc3c', 'wsf6700dfc3c', 'wsf6700dfc3cxl'.
--    
--    Modified VendorIdType to compliance with SNMP v2
--    format
--  RevDate
--    200510280000Z
--  RevDescr
--    Modified chassisComponentType to include:
--    'fanMod4Hs'.
--    
--    Modified syslogMessageFacility to include:
--    'eou', 'backup', 'eoam', 'webauth'.
--    
--    Modified sysErrDisableTimeoutEnable to include:
--    'ethernetOam', 'gl2ptEoamThresholdExceed'.
--    
--    Updated chassisPs1Type and chassisPs2Type to include:
--    'pwr2700dc', 'pwr2700ac4', 'pwr2700dc4', and
--    'wscac8700we'.
--    
--    Modified moduleType to include:
--    'osm4oc3PosMM', 'wsx6196rj21', 
--    'wssup32ge3b', 'wsSvcIpSec1',
--    'wsx6148arj45', 'wsSvcWebVpnk9',
--    'ace106500k9', 'ace046500k9',
--    'wsSvcAdm1k9', 'wsSvcAgm1k9',
--    'wssup3210ge3b', 'osm2choc12T3SI',
--    'wsf6700cfc', 'osm8choc3DS0SI'.
--    
--    Updated portType to include:
--    'e10GBaseEdc1310', 'e10GBaseSW',
--    'sslVpn', 'adsm',
--    'agsm', 'aces',
--    'e10GBaseZR', 'e100BaseEX',
--    'e100BaseZX'.
--  RevDate
--    200504270000Z
--  RevDescr
--    Added support of the following objects:
--     cisco7604sysID, wsc6504esysID
--    
--     Modified sysEnableStpxTrap to include:
--     'enabledForInconOnly', 'enabledForRootOnly',
--     'enabledForLoopOnly', 'enabledForInconRootOnly',
--     'enabledForInconLoopOnly', 'enabledForRootLoopOnly'
--    
--     Modified sysErrDisableTimeoutEnable to include:
--     'camMonitor', 'gl2ptCdpThresholdExceed',
--     'gl2ptStpThresholdExceed', 'gl2ptVtpThresholdExceed',
--     'linkRxCrc', 'linkTxCrc',
--     'linkInErrors', 'packetBufferError'
--    
--     Updated chassisSysType for new hardwares:
--     cisco7604 and wsc6504e
--    
--     Updated chassisPs1Type and chassisPs2Type for new
--     hardwares:
--     wscac6000w and pwr2700ac
--    
--     Updated chassisComponentType for new hardwares:
--     wsc6506eFan, wsc6509eFan, wsc6503eFan, wsc6000vtte.
--    
--     Updated moduleType for hardware:
--     osm2oc48OneDptSSDual, osm2oc48OneDptSIDual,
--     osm2oc48OneDptSLDual, osm4choc12T3MM,
--     osm4choc12T3SI, osm8choc12T3MM,
--     osm8choc12T3SI, osm2choc48T3SS,
--     osm1choc48T3SI, osm2choc48T3SI,
--     osm4choc3DS0SI, osm1choc12T1SI,
--     osm12ct3T1, osm24t3e3,
--     osm2oc12AtmMMPlus, osm2oc12AtmSIPlus,
--     osm8oc3PosSLPlus, wsx6516aGbic,
--     wsx6148getx, wsSvcWlan1k9,
--     wsSvcAon1k9, wsx6148FeSfp,
--     wsx65822pa
--    
--     Updated moduleType for name changed:
--     wsx61821pa changed to wsx61822pa
--    
--     Updated moduleSubType to include new hardwares:
--     wsf6700dfc3a, wsf6kdfc3bxl,
--     wsf6kpfc3bxl, wsf6700dfc3bxl,
--     wsf6700dfc3b, wsf6kdfc3b
--    
--     Updated moduleSubType to include new hardwares:
--     wssvccmm6e1, wssvccmm6t1,
--     wssvccmm24fxs, wssvccmmact
--    
--     Updated portType to include:
--     e10GBaseWdm1550, e10GBaseLW,
--     e10GBaseEW, lwa,
--     aons, e100BaseEmpty,
--     e100BaseUnknown, e100BaseUnapproved,
--     e100BaseSX, e100BaseBX10D,
--     e100BaseBX10U, e1000BaseBX10D,
--     e1000BaseBX10U, e10GBaseBad
--    
--     Updated portType for name changed:
--     posOc48mm changed to posOc48sms
--    
--     Modified ipPermitAccessType, ipPermitDeniedAccess,
--     ipPermitAccessTypeEnable to include:
--     http
--    
--     Modified syslogMessageFacility to include:
--     diags
--    
--     Modified portCpbInlinePower to include:
--     static
--    
--     Deprecated sysEnableStpxTrap, replaced by
--           stpxNotificationEnable in
--           CISCO-STP-EXTENSIONS-MIB.my
--    
--     Deprecated radiusServerTable, replaced by
--           crRadiusServerTable in CISCO-RADIUS-MIB.my
--    
--     Added new conformance Groups:
--     optionalSystemTrapGroup1,
--     authenticationGroup2,
--     systemTrapGroup2,
--     notificationGroup.
--  RevDate
--    200405140000Z
--  RevDescr
--    Modified sysEnableBridgeTraps to include:
--     'enabledForNewRootOnly' and 'enabledForTopoChangeOnly'
--    
--     Updated moduleType for new hardwares:
--     wsx2948ggetx, wsx2948ggetxgbrj and wsx6748sfp
--    
--     Updated moduleSubType for the new harware:
--     wsf6kpfc3b
--    
--     Updated moduleSubType2 for the new harware:
--     wsf6kVpwrGe
--    
--     Updated portType to include:
--     e10GBaseSR, e10GBaseCX4,
--     e1000BaseUnknown and e10GBaseUnknown,
--     e10GBaseUnapproved, e1000BaseWdmRxOnly,
--     e1000BaseDwdm3033,e1000BaseDwdm3112,
--     e1000BaseDwdm3190,e1000BaseDwdm3268,
--     e1000BaseDwdm3425,e1000BaseDwdm3504,
--     e1000BaseDwdm3582,e1000BaseDwdm3661,
--     e1000BaseDwdm3819,e1000BaseDwdm3898,
--     e1000BaseDwdm3977,e1000BaseDwdm4056,
--     e1000BaseDwdm4214,e1000BaseDwdm4294,
--     e1000BaseDwdm4373,e1000BaseDwdm4453,
--     e1000BaseDwdm4612,e1000BaseDwdm4692,
--     e1000BaseDwdm4772,e1000BaseDwdm4851,
--     e1000BaseDwdm5012,e1000BaseDwdm5092,
--     e1000BaseDwdm5172,e1000BaseDwdm5252,
--     e1000BaseDwdm5413,e1000BaseDwdm5494,
--     e1000BaseDwdm5575,e1000BaseDwdm5655,
--     e1000BaseDwdm5817,e1000BaseDwdm5898,
--     e1000BaseDwdm5979,e1000BaseDwdm6061,
--     e10GBaseWdmRxOnly, e10GBaseDwdm3033,
--     e10GBaseDwdm3112, e10GBaseDwdm3190
--     e10GBaseDwdm3268, e10GBaseDwdm3425,
--     e10GBaseDwdm3504, e10GBaseDwdm3582,
--     e10GBaseDwdm3661, e10GBaseDwdm3819,
--     e10GBaseDwdm3898, e10GBaseDwdm3977,
--     e10GBaseDwdm4056, e10GBaseDwdm4214,
--     e10GBaseDwdm4294, e10GBaseDwdm4373,
--     e10GBaseDwdm4453, e10GBaseDwdm4612,
--     e10GBaseDwdm4692, e10GBaseDwdm4772,
--     e10GBaseDwdm4851, e10GBaseDwdm5012,
--     e10GBaseDwdm5092, e10GBaseDwdm5172,
--     e10GBaseDwdm5252, e10GBaseDwdm5413,
--     e10GBaseDwdm5494, e10GBaseDwdm5575,
--     e10GBaseDwdm5655, e10GBaseDwdm5817,
--     e10GBaseDwdm5898, e10GBaseDwdm5979 and
--     e10GBaseDwdm6061
--    
--     Modified portAdminSpeed to include:
--     'autoDetect10100'
--    
--     Modified syslogMessageFacility to include:
--     'dhcpsnooping'.
--  RevDate
--    200401150000Z
--  RevDescr
--    Updated workgroup for new hardware:
--     wsc2948ggetxsysID
--    
--     Updated chassisSysType for new hardware:
--     wsc2948ggetx
--    
--     Updated chassisPs1Type for new hardware:
--     w156
--    
--     Updated moduleType for new hardwares:
--     wsx4148lxmt, wsx4548gbrj45, wsx4548gbrj45v
--     wsx4248rj21v, wsx4302gb, wsx4248rj45v, wsx6748getx,
--     wsx670410ge, wsx6724sfp and wsx6148x2rj45
--    
--     Updated moduleSubType2 for new hardwares:
--     wsf6kmsfc, wsf6kmsfc2, wsf6kmsfc2a,
--     wsf6kFe48af, wsf6kGe48af and wsf6kFe48x2af,
--    
--     Updated moduleType for new hardwares:
--     e1000BaseUnknown and e10GBaseUnknown.
--    
--     Modified syslogMessageFacility to include 'callhome'.
--    
--     Modified sysErrDisableTimeoutEnable to include
--     'arpInspectionRate' and 'noStaticInlinePwr'.
--    
--     Modified Description clause for deprecated objects:
--     sysIpAddr, sysNetMask, sysBroadcast, sysReset,
--     sysConsolePrimaryLoginAuthentication,
--     sysConsolePrimaryEnableAuthentication,
--     sysTelnetPrimaryLoginAuthentication,
--     sysTelnetPrimaryEnableAuthentication,
--     sysPortFastBpduGuard, chassisSerialNumber,
--     chassisComponentTable, moduleSerialNumber,
--     moduleHwHiVersion, moduleHwLoVersion,
--     moduleFwHiVersion, moduleFwLoVersion,
--     moduleSwHiVersion, moduleSwLoVersion,
--     portSpantreeFastStart, monitorGrp and
--     vlanSpantreeEnable.
--    
--     Added new conformance Groups:
--     systemMiscGroup1,
--     systemTrapGroup1,
--     optionalSystemMiscGroup6,
--     optionalChassisGroup1,
--     portGroup4,
--     vlanGroup2,
--     ipPermitGroup2 and
--     optionalPortGroup1.
--  RevDate
--    200305290000Z
--  RevDescr
--    Change the ORGANIZATION clause. Deprecated
--     sysClearMacTime object.
--  RevDate
--    200305050000Z
--  RevDescr
--    Add support of the following objects: cisco7613sysID,
--     wsc6509nebasysID. ChassisType: wsc4507, wsc6509NEBA,
--     wsc65509, cisco7613. chassisPs1Type: pwr950dc,
--     pwr1900ac, pwr1900dc, wscac3000w,
--     pwrc451400dcp, wscdc3000w, pwr1400ac.
--     chassisPs2Type: pwr950dc, pwr1900ac, pwr1900dc,
--     wscac3000w,  wscdc3000w, pwr1400ac.
--     moduleTable: wsSvcIdsm2, wsSvcFwm1, wsSvcCe1,
--     wssvcSsl1, osm2oc12PosMMPlus, osm2oc12PosSIPlus,
--     osm16oc3PosSIPlus, osm1oc48PosSSPlus,osm1oc48PosSIPlus,
--     osm1oc48PosSLPlus, osm4oc3PosSIPlus, osm8oc3PosSIPlus,
--     osm4oc12PosSIPlus, wsx6548getx, wssup720, wssup720base.
--     moduleSubType: wsf6kpfc2a, wsf6kdfca, vsp300dfc,
--     wsf6kpfc3a, wsf6kdfc3a. moduleSubType2: wsg6489,
--     wsg6485, wsu4502gb, wssvcidsupg, wssup720.
--     portType: e100BaseLX.
--    
--     Deprecate the following objects: sysIpAddr, sysNetMask,
--     sysBroadcast, sysTrapReceiverTable, sysReset,
--     sysClearPortTime, sysClearMacTime,
--     sysPortFastBpduGuard, chassisComponentTable,
--     portSpantreeFastStart, vlanTable, portChannelTable.
--    
--     Remove the TC MacAddressType, and replaced other uses
--     by MacAddress.
--  RevDate
--    200209240000Z
--  RevDescr
--    Added more HW models.
--  RevDate
--    200106110000Z
--  RevDescr
--    Added cat6000 new HW chassis & modules.
--  RevDate
--    200104110000Z
--  RevDescr
--    Added more HW modules;
--     Added the following MIB objects under systemGrp:
--            sysMaxRmonMemory
--            sysMacReductionAdminEnable
--            sysMacReductionOperEnable
--     Added the following MIB object under fileCopyGrp:
--            fileCopyRuntimeConfigPart
--     Added the following MIB object under filterPortTable:
--            filterPortSuppressionOption
--     Added the following MIB object under syslogGrp:
--            syslogTelnetEnable
--  RevDate
--    200010100000Z
--  RevDescr
--    Added more HW modules;
--     Added the following objects in systemGrp
--         sshPublicKeySize
--     Added the vlanTrunkMappingTable in vlanGrp
--     Added portJumboFrameGrp
--     Added the following objects in portCpbTable:
--            portCpbCosRewrite
--            portCpbTosRewrite
--            portCpbCopsGrouping
--     Added copyTechReportFromRuntimeToHost in fileCopyAction
--     Added ssh(2) in ipPermitAccessType &
--     ipPermitDeniedAccess.
--  RevDate
--    200005160000Z
--  RevDescr
--    Added more HW models;
--     Added the following objects:
--            portInlinePowerDetect
--            vlanPortAuxiliaryVlan
--            portCpbInlinePower
--            portCpbAuxiliaryVlan
--            moduleAdditionalStatus
--            sysExtendedRmonNetflowModuleMask
--     Added the voiceGrp
--     Added the switchAccelerationGrp
--  RevDate
--    200002020000Z
--  RevDescr
--    Added the following objects:
--            sysPortFastBpduGuard
--            sysErrDisableTimeoutEnable
--            sysErrDisableTimeoutInterval
--            sysTrafficMonitorHighWaterMark
--            chassisPs3Type
--            chassisPs3Status
--            chassisPs3TestResult
--            chassisPEMInstalled
--            moduleEntPhysicalIndex
--            portAdditionalOperStatus
--            portEntPhysicalIndex
--            filterPortBroadcastThresholdFraction
--            mcastEnableRgmp
--            portCpbSpan.
--     modified ipPermitGrp for supporting IP Permit
--     Enhancement. Added more HW models.
--  RevDate
--    9909300000Z
--  RevDescr
--    Added more HW models.
--  RevDate
--    9903260000Z
--  RevDescr
--    Added traceRouteGrp.
--  RevDate
--    9902120000Z
--  RevDescr
--    Initial v2 version of this MIB module.

adapterCard     OBJECT IDENTIFIER ::= { workgroup 2 }
wsc1000sysID    OBJECT IDENTIFIER ::= { workgroup 3 }
wsc1100sysID    OBJECT IDENTIFIER ::= { workgroup 4 }
wsc1200sysID    OBJECT IDENTIFIER ::= { workgroup 5 }
wsc1400sysID    OBJECT IDENTIFIER ::= { workgroup 6 }
wsc5000sysID    OBJECT IDENTIFIER ::= { workgroup 7 }
wsc1600sysID    OBJECT IDENTIFIER ::= { workgroup 8 }
cpw1600sysID    OBJECT IDENTIFIER ::= { workgroup 9 }
wsc3000sysID    OBJECT IDENTIFIER ::= { workgroup 10 }
wsc2900sysID    OBJECT IDENTIFIER ::= { workgroup 12 }
cpw2200sysID    OBJECT IDENTIFIER ::= { workgroup 13 }
esStack         OBJECT IDENTIFIER ::= { workgroup 14 }
wsc3200sysID    OBJECT IDENTIFIER ::= { workgroup 15 }
cpw1900sysID    OBJECT IDENTIFIER ::= { workgroup 16 }
wsc5500sysID    OBJECT IDENTIFIER ::= { workgroup 17 }
wsc1900sysID    OBJECT IDENTIFIER ::= { workgroup 18 }
cpw1220sysID    OBJECT IDENTIFIER ::= { workgroup 19 }
wsc2820sysID    OBJECT IDENTIFIER ::= { workgroup 20 }
cpw1420sysID    OBJECT IDENTIFIER ::= { workgroup 21 }
dcd             OBJECT IDENTIFIER ::= { workgroup 22 }
wsc3100sysID    OBJECT IDENTIFIER ::= { workgroup 23 }
cpw1800sysID    OBJECT IDENTIFIER ::= { workgroup 24 }
cpw1601sysID    OBJECT IDENTIFIER ::= { workgroup 25 }
wsc3001sysID    OBJECT IDENTIFIER ::= { workgroup 26 }
cpw1220csysID   OBJECT IDENTIFIER ::= { workgroup 27 }
wsc1900csysID   OBJECT IDENTIFIER ::= { workgroup 28 }
wsc5002sysID    OBJECT IDENTIFIER ::= { workgroup 29 }
cpw1220isysID   OBJECT IDENTIFIER ::= { workgroup 30 }
wsc1900isysID   OBJECT IDENTIFIER ::= { workgroup 31 }
tsStack         OBJECT IDENTIFIER ::= { workgroup 32 }
wsc3900sysID    OBJECT IDENTIFIER ::= { workgroup 33 }
wsc5505sysID    OBJECT IDENTIFIER ::= { workgroup 34 }
wsc2926sysID    OBJECT IDENTIFIER ::= { workgroup 35 }
wsc5509sysID    OBJECT IDENTIFIER ::= { workgroup 36 }
wsc3920sysID    OBJECT IDENTIFIER ::= { workgroup 37 }
wsc6006sysID    OBJECT IDENTIFIER ::= { workgroup 38 }
wsc6009sysID    OBJECT IDENTIFIER ::= { workgroup 39 }
wsc4003sysID    OBJECT IDENTIFIER ::= { workgroup 40 }
wsc4912gsysID   OBJECT IDENTIFIER ::= { workgroup 41 }
wsc2948gsysID   OBJECT IDENTIFIER ::= { workgroup 42 }
wsc6509sysID    OBJECT IDENTIFIER ::= { workgroup 44 }
wsc6506sysID    OBJECT IDENTIFIER ::= { workgroup 45 }
wsc4006sysID    OBJECT IDENTIFIER ::= { workgroup 46 }
wsc6509nebsysID OBJECT IDENTIFIER ::= { workgroup 47 }
wsc6knamsysID   OBJECT IDENTIFIER ::= { workgroup 48 }
wsc2980gsysID   OBJECT IDENTIFIER ::= { workgroup 49 }
wsc6513sysID    OBJECT IDENTIFIER ::= { workgroup 50 }
wsc2980gasysID  OBJECT IDENTIFIER ::= { workgroup 51 }
cisco7603sysID  OBJECT IDENTIFIER ::= { workgroup 53 }
cisco7606sysID  OBJECT IDENTIFIER ::= { workgroup 54 }
cisco7609sysID  OBJECT IDENTIFIER ::= { workgroup 55 }
wsc6503sysID    OBJECT IDENTIFIER ::= { workgroup 56 }
wsc4503sysID    OBJECT IDENTIFIER ::= { workgroup 58 }
wsc4506sysID    OBJECT IDENTIFIER ::= { workgroup 59 }
cisco7613sysID  OBJECT IDENTIFIER ::= { workgroup 60 }
wsc6509nebasysID OBJECT IDENTIFIER ::= { workgroup 61 }
wsc2948ggetxsysID OBJECT IDENTIFIER ::= { workgroup 62 }
cisco7604sysID  OBJECT IDENTIFIER ::= { workgroup 63 }
wsc6504esysID   OBJECT IDENTIFIER ::= { workgroup 64 }
wsc1900LiteFxsysID OBJECT IDENTIFIER ::= { workgroup 175 }
systemGrp       OBJECT IDENTIFIER ::= { ciscoStackMIB 1 }
chassisGrp      OBJECT IDENTIFIER ::= { ciscoStackMIB 2 }
moduleGrp       OBJECT IDENTIFIER ::= { ciscoStackMIB 3 }
portGrp         OBJECT IDENTIFIER ::= { ciscoStackMIB 4 }
tftpGrp         OBJECT IDENTIFIER ::= { ciscoStackMIB 5 }
brouterGrp      OBJECT IDENTIFIER ::= { ciscoStackMIB 6 }
filterGrp       OBJECT IDENTIFIER ::= { ciscoStackMIB 7 }
monitorGrp      OBJECT IDENTIFIER ::= { ciscoStackMIB 8 }
vlanGrp         OBJECT IDENTIFIER ::= { ciscoStackMIB 9 }
securityGrp     OBJECT IDENTIFIER ::= { ciscoStackMIB 10 }
tokenRingGrp    OBJECT IDENTIFIER ::= { ciscoStackMIB 11 }
multicastGrp    OBJECT IDENTIFIER ::= { ciscoStackMIB 12 }
dnsGrp          OBJECT IDENTIFIER ::= { ciscoStackMIB 13 }
syslogGrp       OBJECT IDENTIFIER ::= { ciscoStackMIB 14 }
ntpGrp          OBJECT IDENTIFIER ::= { ciscoStackMIB 15 }
tacacsGrp       OBJECT IDENTIFIER ::= { ciscoStackMIB 16 }
ipPermitListGrp OBJECT IDENTIFIER ::= { ciscoStackMIB 17 }
portChannelGrp  OBJECT IDENTIFIER ::= { ciscoStackMIB 18 }
portCpbGrp      OBJECT IDENTIFIER ::= { ciscoStackMIB 19 }
portTopNGrp     OBJECT IDENTIFIER ::= { ciscoStackMIB 20 }
mdgGrp          OBJECT IDENTIFIER ::= { ciscoStackMIB 21 }
radiusGrp       OBJECT IDENTIFIER ::= { ciscoStackMIB 22 }
traceRouteGrp   OBJECT IDENTIFIER ::= { ciscoStackMIB 24 }
fileCopyGrp     OBJECT IDENTIFIER ::= { ciscoStackMIB 25 }
voiceGrp        OBJECT IDENTIFIER ::= { ciscoStackMIB 26 }
portJumboFrameGrp OBJECT IDENTIFIER ::= { ciscoStackMIB 27 }
switchAccelerationGrp OBJECT IDENTIFIER ::= { ciscoStackMIB 28 }
configGrp       OBJECT IDENTIFIER ::= { ciscoStackMIB 29 }
ciscoStackNotificationsPrefix OBJECT IDENTIFIER ::= { workgroup 0 }
ciscoStackMIBConformance OBJECT IDENTIFIER ::= { ciscoStackMIB 31 }
ciscoStackMIBCompliances OBJECT IDENTIFIER ::= { ciscoStackMIBConformance 1 }
ciscoStackMIBGroups OBJECT IDENTIFIER ::= { ciscoStackMIBConformance 2 }

VendorIdType ::= OCTET STRING(SIZE(3))
-- TEXTUAL-CONVENTION
--  Status
--    mandatory
--  Descr
--    Vendor ID Type

sysMgmtType OBJECT-TYPE
    SYNTAX INTEGER {
        other(1),
        snmpV1(2),
        smux(3),
        snmpV2V1(4),
        snmpV2cV1(5),
        snmpV3V2cV1(6)
        }
    ACCESS read-only
    STATUS mandatory
    DESCRIPTION
        "Type of network management running on this
         entity."
    ::= { systemGrp 1 }

sysIpAddr OBJECT-TYPE
    SYNTAX IpAddress
    ACCESS read-write
    STATUS deprecated
    DESCRIPTION
        "This entity's IP address.
        
        This object is deprecated and replaced by
        ciiIPAddressType and ciiIPAddress in
        CISCO-IP-IF-MIB."
    ::= { systemGrp 2 }

sysNetMask OBJECT-TYPE
    SYNTAX IpAddress
    ACCESS read-write
    STATUS deprecated
    DESCRIPTION
        "This entity's subnet mask.
        
        This object is deprecated and replaced by
        ciiIPAddressPrefixLength in CISCO-IP-IF-MIB."
    ::= { systemGrp 3 }

sysBroadcast OBJECT-TYPE
    SYNTAX IpAddress
    ACCESS read-write
    STATUS deprecated
    DESCRIPTION
        "This entity's broadcast address.
        
        This object is deprecated and replaced by
        ciiIPAddressBroadcast in CISCO-IP-IF-MIB."
    ::= { systemGrp 4 }

sysTrapReceiverTable OBJECT-TYPE
    SYNTAX SEQUENCE OF SysTrapReceiverEntry
    ACCESS not-accessible
    STATUS deprecated
    DESCRIPTION
        "The trap receiver table (0 to 20 entries). This
        table lists the addresses of Network Management
        Stations that should receive trap messages from
        this entity when an exception condition occurs.
        
        This table is deprecated and replaced by
        trapDestTable and other tables in SNMP-TARGET-
        MIB and SNMP-NOTIFICATION-MIB."
    ::= { systemGrp 5 }

sysTrapReceiverEntry OBJECT-TYPE
    SYNTAX SysTrapReceiverEntry
    ACCESS not-accessible
    STATUS deprecated
    DESCRIPTION
        "A trap receiver table entry."
    INDEX { sysTrapReceiverAddr }
    ::= { sysTrapReceiverTable 1 }

SysTrapReceiverEntry ::= SEQUENCE {
    sysTrapReceiverType INTEGER,
    sysTrapReceiverAddr IpAddress,
    sysTrapReceiverComm DisplayString
    }

sysTrapReceiverType OBJECT-TYPE
    SYNTAX INTEGER {
        valid(1),
        invalid(2)
        }
    ACCESS read-write
    STATUS deprecated
    DESCRIPTION
        "Setting this object to invalid(2) removes the
        corresponding entry from the sysTrapReceiverTable.
        To add a new entry to the sysTrapReceiverTable,
        set this object to valid(1) for an IpAddress which
        is not already in the table."
    ::= { sysTrapReceiverEntry 1 }

sysTrapReceiverAddr OBJECT-TYPE
    SYNTAX IpAddress
    ACCESS read-only
    STATUS deprecated
    DESCRIPTION
        "IP address for trap receiver."
    ::= { sysTrapReceiverEntry 2 }

sysTrapReceiverComm OBJECT-TYPE
    SYNTAX DisplayString(SIZE(0..20))
--    Rsyntax OCTET STRING(SIZE(0..20))
    ACCESS read-write
    STATUS deprecated
    DESCRIPTION
        "Community string used for trap messages to this
        trap receiver."
    ::= { sysTrapReceiverEntry 3 }

sysCommunityTable OBJECT-TYPE
    SYNTAX SEQUENCE OF SysCommunityEntry
    ACCESS not-accessible
    STATUS deprecated
    DESCRIPTION
        "The community table (4 entries). This table lists
        community strings and their access levels. When an
        SNMP message is received by this entity, the
        community string in the message is compared with
        this table to determine access rights of the
        sender.
        
        Note that this item is only accessible when using
        the community string defined in sysCommunityRwa."
    ::= { systemGrp 6 }

sysCommunityEntry OBJECT-TYPE
    SYNTAX SysCommunityEntry
    ACCESS not-accessible
    STATUS deprecated
    DESCRIPTION
        "A community table entry."
    INDEX { sysCommunityAccess }
    ::= { sysCommunityTable 1 }

SysCommunityEntry ::= SEQUENCE {
    sysCommunityAccess INTEGER,
    sysCommunityString DisplayString
    }

sysCommunityAccess OBJECT-TYPE
    SYNTAX INTEGER {
        other(1),
        readOnly(2),
        readWrite(3),
        readWriteAll(4)
        }
    ACCESS read-only
    STATUS deprecated
    DESCRIPTION
        "A value of readWriteAll(4) allows the community
        to read and write all objects in the MIB. A
        value of readWrite(3) allows the community to
        read and write all objects except restricted
        items such as community strings, which cannot
        be accessed at all. A value of readOnly(2) allows
        the community to read all objects except
        restricted items. A value of other(1) allows no
        access."
    ::= { sysCommunityEntry 1 }

sysCommunityString OBJECT-TYPE
    SYNTAX DisplayString(SIZE(0..20))
--    Rsyntax OCTET STRING(SIZE(0..20))
    ACCESS read-write
    STATUS deprecated
    DESCRIPTION
        "Configurable community string with access rights
        defined by the value of sysCommunityAccess."
    ::= { sysCommunityEntry 2 }

sysAttachType OBJECT-TYPE
    SYNTAX INTEGER {
        other(1),
        dualAttach(2),
        singleAttach(3),
        nullAttach(4),
        dualPrio(5)
        }
    ACCESS read-write
    STATUS mandatory
    DESCRIPTION
        "The requested concentrator attachment type. For a
        dual attachment concentrator which can be
        connected to the trunk ring, the first FDDI port
        is configured as A and the second FDDI port is
        configured as B.
        For a single attachment concentrator which can be
        connected beneath another concentrator, the first
        FDDI port is configured as M and the second FDDI
        port is configured as S. For a null attachment
        concentrator which can be located at the root of
        the tree, the first two FDDI ports are configured
        as M.
        This object does not take effect until the
        concentrator is reset. The current attachment
        type can be determined from snmpFddiPORTPCType
        for ports 1 and 2."
    DEFVAL { dualAttach }
    ::= { systemGrp 7 }

sysTraffic OBJECT-TYPE
    SYNTAX INTEGER(0..100)
    ACCESS read-only
    STATUS mandatory
    DESCRIPTION
        "Traffic meter value, i.e. the percentage of
        bandwidth utilization for the previous polling
        interval."
    ::= { systemGrp 8 }

sysReset OBJECT-TYPE
    SYNTAX INTEGER {
        other(1),
        reset(2),
        resetMinDown(3)
        }
    ACCESS read-write
    STATUS deprecated
    DESCRIPTION
        "Writing reset(2) to this object resets the
        control logic of all modules in the system.
        Writing resetMinDown(3) to this object resets the
        system with the minimal system down time. The
        resetMinDown(3) is only supported in systems with
        redundant supervisors.
        
        This object is deprecated and replaced by
        csyScheduledReset in CISCO-SYSTEM-MIB."
    ::= { systemGrp 9 }

sysBaudRate OBJECT-TYPE
    SYNTAX INTEGER {
        b600(600),
        b1200(1200),
        b2400(2400),
        b4800(4800),
        b9600(9600),
        b19200(19200),
        b38400(38400)
        }
    ACCESS read-write
    STATUS mandatory
    DESCRIPTION
        "The baud rate in bits per second of the RS-232
        port."
    DEFVAL { b9600 }
    ::= { systemGrp 10 }

sysInsertMode OBJECT-TYPE
    SYNTAX INTEGER {
        other(1),
        standard(2),
        scheduled(3),
        graceful(4)
        }
    ACCESS read-write
    STATUS mandatory
    DESCRIPTION
        "The mode for inserting M-ports into the
         concentrator ring."
    ::= { systemGrp 11 }

sysClearMacTime OBJECT-TYPE
    SYNTAX TimeTicks
    ACCESS read-write
    STATUS deprecated
    DESCRIPTION
        "The time (in hundredths of a second) since mac
        counters were last cleared. Writing a 0 to this
        object causes the mac counters to be cleared."
    ::= { systemGrp 12 }

sysClearPortTime OBJECT-TYPE
    SYNTAX TimeTicks
    ACCESS read-write
    STATUS deprecated
    DESCRIPTION
        "The time (in hundredths of a second) since port
        counters were last cleared. Writing a 0 to this
        object causes the port counters to be cleared."
    ::= { systemGrp 13 }

sysFddiRingTable OBJECT-TYPE
    SYNTAX SEQUENCE OF SysFddiRingEntry
    ACCESS not-accessible
    STATUS mandatory
    DESCRIPTION
        "The fddi ring map table. This table lists the
        nodes in the FDDI ring(s) to which the system
        belongs."
    ::= { systemGrp 14 }

sysFddiRingEntry OBJECT-TYPE
    SYNTAX SysFddiRingEntry
    ACCESS not-accessible
    STATUS mandatory
    DESCRIPTION
        "A FDDI Ring table entry."
    INDEX { sysFddiRingSMTIndex, sysFddiRingAddress }
    ::= { sysFddiRingTable 1 }

SysFddiRingEntry ::= SEQUENCE {
    sysFddiRingSMTIndex INTEGER,
    sysFddiRingAddress MacAddress,
    sysFddiRingNext MacAddress
    }

sysFddiRingSMTIndex OBJECT-TYPE
    SYNTAX INTEGER(1..65535)
    ACCESS read-only
    STATUS mandatory
    DESCRIPTION
        "The value of the SMT index associated with this
        ring."
    ::= { sysFddiRingEntry 1 }

sysFddiRingAddress OBJECT-TYPE
    SYNTAX MacAddress
--    Rsyntax OCTET STRING(SIZE(6))
    ACCESS read-only
    STATUS mandatory
    DESCRIPTION
        "The MAC address of this node in the FDDI ring."
    ::= { sysFddiRingEntry 2 }

sysFddiRingNext OBJECT-TYPE
    SYNTAX MacAddress
--    Rsyntax OCTET STRING(SIZE(6))
    ACCESS read-only
    STATUS mandatory
    DESCRIPTION
        "The MAC address of the next node in the FDDI
         ring."
    ::= { sysFddiRingEntry 3 }

sysEnableModem OBJECT-TYPE
    SYNTAX INTEGER {
        enabled(1),
        disabled(2)
        }
    ACCESS read-write
    STATUS mandatory
    DESCRIPTION
        "Indicates whether the RS-232 port modem control
        lines are enabled."
    DEFVAL { disabled }
    ::= { systemGrp 15 }

sysEnableRedirects OBJECT-TYPE
    SYNTAX INTEGER {
        enabled(1),
        disabled(2)
        }
    ACCESS read-write
    STATUS mandatory
    DESCRIPTION
        "Indicates whether ICMP redirect messages are sent
        or received by the system."
    DEFVAL { enabled }
    ::= { systemGrp 16 }

sysEnableRmon OBJECT-TYPE
    SYNTAX INTEGER {
        enabled(1),
        disabled(2)
        }
    ACCESS read-write
    STATUS mandatory
    DESCRIPTION
        "Indicates whether the SNMP agent supports the
        RMON MIB."
    DEFVAL { enabled }
    ::= { systemGrp 17 }

sysArpAgingTime OBJECT-TYPE
    SYNTAX INTEGER(0..1000000)
    ACCESS read-write
    STATUS mandatory
    DESCRIPTION
        "The aging time for the ARP table."
    DEFVAL { 1200 }
    ::= { systemGrp 18 }

sysTrafficPeak OBJECT-TYPE
    SYNTAX INTEGER(0..100)
    ACCESS read-only
    STATUS mandatory
    DESCRIPTION
        "Peak traffic meter value since the last time port
        counters were cleared or the system started (see
        sysClearPortTime)."
    ::= { systemGrp 19 }

sysTrafficPeakTime OBJECT-TYPE
    SYNTAX TimeTicks
    ACCESS read-only
    STATUS mandatory
    DESCRIPTION
        "The time (in hundredths of a second) since the
        peak traffic meter value occurred."
    ::= { systemGrp 20 }

sysCommunityRwa OBJECT-TYPE
    SYNTAX DisplayString(SIZE(0..20))
--    Rsyntax OCTET STRING(SIZE(0..20))
    ACCESS read-write
    STATUS mandatory
    DESCRIPTION
        "When an SNMP message is received by this entity,
        the community string in the message is compared
        with this string first. If it matches, read-write
        access is granted to all items in the MIB. If it
        doesn't match, the sysCommunityRw string is
        compared next.
        
        Note that this item is only accessible when using
        the community string defined in sysCommunityRwa."
    ::= { systemGrp 21 }

sysCommunityRw OBJECT-TYPE
    SYNTAX DisplayString(SIZE(0..20))
--    Rsyntax OCTET STRING(SIZE(0..20))
    ACCESS read-write
    STATUS mandatory
    DESCRIPTION
        "When an SNMP message is received by this entity,
        the community string in the message is compared
        with this string second. If it matches, read-write
        access is granted to all items in the MIB except
        restricted items such as community strings.
        (Restricted items appear empty when read and
        return a no such name error when an attempt is
        made to write them.)  If it doesn't match, the
        sysCommunityRo string is compared next.
        
        Note that this item is only accessible when using
        the community string defined in sysCommunityRwa."
    ::= { systemGrp 22 }

sysCommunityRo OBJECT-TYPE
    SYNTAX DisplayString(SIZE(0..20))
--    Rsyntax OCTET STRING(SIZE(0..20))
    ACCESS read-write
    STATUS mandatory
    DESCRIPTION
        "When an SNMP message is received by this entity,
        the community string in the message is compared
        with this string third. If it matches, read-only
        access is granted to all items in the MIB except
        restricted items such as community strings.
        (Restricted items appear empty when read.) If it
        doesn't match, no access is granted, no response
        is sent back to the SNMP requester, and an SNMP
        is sent to the SNMP trap receivers if configured.
        
        Note that this item is only accessible when using
        the community string defined in sysCommunityRwa."
    ::= { systemGrp 23 }

sysEnableChassisTraps OBJECT-TYPE
    SYNTAX INTEGER {
        enabled(1),
        disabled(2)
        }
    ACCESS read-write
    STATUS mandatory
    DESCRIPTION
        "Indicates whether chassisAlarmOn and
        chassisAlarmOff traps in this MIB should be
        generated."
    DEFVAL { disabled }
    ::= { systemGrp 24 }

sysEnableModuleTraps OBJECT-TYPE
    SYNTAX INTEGER {
        enabled(1),
        disabled(2)
        }
    ACCESS read-write
    STATUS mandatory
    DESCRIPTION
        "Indicates whether moduleUp and moduleDown traps
        in this MIB should be generated."
    DEFVAL { disabled }
    ::= { systemGrp 25 }

sysEnableBridgeTraps OBJECT-TYPE
    SYNTAX INTEGER {
        enabled(1),
        disabled(2),
        enabledForNewRootOnly(3),
        enabledForTopoChangeOnly(4)
        }
    ACCESS read-write
    STATUS deprecated
    DESCRIPTION
        "Indicates whether newRoot and topologyChange
        traps in the BRIDGE-MIB (RFC 1493) should be
        generated.
        
        enabled -- both newRoot and topologyChange
                   traps are enabled.
        
        disabled -- both of the newRoot and
                   topologyChange traps are disabled.
        
        enabledForNewRootOnly -- only the newRoot trap is
                   enabled. This value is read-only.
        
        enabledForTopoChangeOnly -- only the
                   topologyChange trap is enabled. This
                   value is read-only.
        
        This object is deprecated and replaced by
        stpxNotificationEnable in
        CISCO-STP-EXTENSIONS-MIB."
    DEFVAL { disabled }
    ::= { systemGrp 26 }

sysIpVlan OBJECT-TYPE
    SYNTAX VlanIndex
--    Rsyntax INTEGER(0..4095)
    ACCESS read-write
    STATUS mandatory
    DESCRIPTION
        "This entity's IP address Virtual LAN
        association."
    DEFVAL { 1 }
    ::= { systemGrp 27 }

sysConfigChangeTime OBJECT-TYPE
    SYNTAX TimeTicks
    ACCESS read-only
    STATUS mandatory
    DESCRIPTION
        "The time (in hundredths of a second) since the
        configuration of the system was last changed."
    ::= { systemGrp 28 }

sysEnableRepeaterTraps OBJECT-TYPE
    SYNTAX INTEGER {
        enabled(1),
        disabled(2)
        }
    ACCESS read-write
    STATUS mandatory
    DESCRIPTION
        "Indicates whether the traps in the REPEATER-MIB
        (RFC1516) should be generated."
    DEFVAL { disabled }
    ::= { systemGrp 29 }

sysBannerMotd OBJECT-TYPE
    SYNTAX DisplayString(SIZE(0..255))
--    Rsyntax OCTET STRING(SIZE(0..255))
    ACCESS read-write
    STATUS mandatory
    DESCRIPTION
        "Message of the day banner which is displayed on
        the Command Line Interface before log in."
    ::= { systemGrp 30 }

sysEnableIpPermitTraps OBJECT-TYPE
    SYNTAX INTEGER {
        enabled(1),
        disabled(2)
        }
    ACCESS read-write
    STATUS mandatory
    DESCRIPTION
        "Indicates whether the IP permit traps in this MIB
         should be generated."
    DEFVAL { disabled }
    ::= { systemGrp 31 }

sysTrafficMeterTable OBJECT-TYPE
    SYNTAX SEQUENCE OF SysTrafficMeterEntry
    ACCESS not-accessible
    STATUS mandatory
    DESCRIPTION
        "The system traffic meter table. This table
        lists the traffic meters available in the
        system."
    ::= { systemGrp 32 }

sysTrafficMeterEntry OBJECT-TYPE
    SYNTAX SysTrafficMeterEntry
    ACCESS not-accessible
    STATUS mandatory
    DESCRIPTION
        "A traffic meter table entry."
    INDEX { sysTrafficMeterType }
    ::= { sysTrafficMeterTable 1 }

SysTrafficMeterEntry ::= SEQUENCE {
    sysTrafficMeterType INTEGER,
    sysTrafficMeter INTEGER,
    sysTrafficMeterPeak INTEGER,
    sysTrafficMeterPeakTime TimeTicks
    }

sysTrafficMeterType OBJECT-TYPE
    SYNTAX INTEGER {
        systemSwitchingBus(1),
        switchingBusA(2),
        switchingBusB(3),
        switchingBusC(4)
        }
    ACCESS read-only
    STATUS mandatory
    DESCRIPTION
        "The type of traffic meter."
    ::= { sysTrafficMeterEntry 1 }

sysTrafficMeter OBJECT-TYPE
    SYNTAX INTEGER(0..100)
    ACCESS read-only
    STATUS mandatory
    DESCRIPTION
        "Traffic meter value, i.e. the percentage of
        bandwidth utilization for the previous polling
        interval."
    ::= { sysTrafficMeterEntry 2 }

sysTrafficMeterPeak OBJECT-TYPE
    SYNTAX INTEGER(0..100)
    ACCESS read-only
    STATUS mandatory
    DESCRIPTION
        "Peak traffic meter value since the system
        started."
    ::= { sysTrafficMeterEntry 3 }

sysTrafficMeterPeakTime OBJECT-TYPE
    SYNTAX TimeTicks
    ACCESS read-only
    STATUS mandatory
    DESCRIPTION
        "The time (in hundredths of a second) since the
        peak traffic meter value occurred."
    ::= { sysTrafficMeterEntry 4 }

sysEnableVmpsTraps OBJECT-TYPE
    SYNTAX INTEGER {
        enabled(1),
        disabled(2)
        }
    ACCESS read-write
    STATUS mandatory
    DESCRIPTION
        "Indicates whether the vmVmpsChange trap defined
        in CISCO-VLAN-MEMBERSHIP-MIB should be generated."
    DEFVAL { disabled }
    ::= { systemGrp 33 }

sysConfigChangeInfo OBJECT-TYPE
    SYNTAX DisplayString(SIZE(0..255))
--    Rsyntax OCTET STRING(SIZE(0..255))
    ACCESS read-only
    STATUS mandatory
    DESCRIPTION
        "Indicates which NVRAM block is changed by whom."
    ::= { systemGrp 34 }

sysEnableConfigTraps OBJECT-TYPE
    SYNTAX INTEGER {
        enabled(1),
        disabled(2)
        }
    ACCESS read-write
    STATUS mandatory
    DESCRIPTION
        "Indicates whether sysConfigChange trap in this
        MIB should be generated."
    DEFVAL { disabled }
    ::= { systemGrp 35 }

sysConfigRegister OBJECT-TYPE
    SYNTAX OCTET STRING(SIZE(2))
    ACCESS read-write
    STATUS mandatory
    DESCRIPTION
        "The value of configuration register that will be
        used by the supervisor module when the system is
        restarted.
        This MIB object is only supported in systems with
        supervisor modules having ROMMON support.
        
        The lowest four bits of the configuration register
        (bits 3,2,1, and 0) form the boot field and the
        boot field determines whether the system boots
        from as the following:
        0000  -- stay in ROM monitor
        0001  -- boot from the first bootable system
                 images on the bootflash
        0010 to 1111
              -- boot from the first bootable system
                 images specified in the sysBootVariable
        
        The bit 5(0x0020) indicates whether the
        configuration file specified in
        sysStartupConfigSourceFile will beused recurringly
        or not whenever the system resets. If this bit is
        not set, the configuration file(s) specified in
        sysStartupConfigSourceFile will only be used once
        and the value of sysStartupConfigSourceFile will
        be reset to empty string automatically during the
        next system reset.
        
        If the bit 6(0x0040) is set, the system will start
        with default configuration.
        
        The bits 11,12 (0x0800, 0x1000) are used to
        specify the console line speed in ROM monitor mode
        as the following:
        00   -- 9600
        01   -- 1200
        10   -- 4800
        11   -- 2400
        
        The unspecified bits are not used."
    DEFVAL { '010f'H }
    ::= { systemGrp 36 }

sysBootVariable OBJECT-TYPE
    SYNTAX DisplayString(SIZE(0..255))
--    Rsyntax OCTET STRING(SIZE(0..255))
    ACCESS read-write
    STATUS mandatory
    DESCRIPTION
        "A list of the system boot images in the BOOT
        environment variable on supervisor modules with
        ROMMON. The format of sysBootVariable should be:
        <device>:[<fileName>],1;{<device>:[<fileName>],1;...}
        If the [fileName] is not specified, the first file
        on the <device> will be used.
        
        This MIB object is only supported in systems
        having supervisor modules with ROMMON."
    ::= { systemGrp 37 }

sysBootedImage OBJECT-TYPE
    SYNTAX DisplayString(SIZE(0..255))
--    Rsyntax OCTET STRING(SIZE(0..255))
    ACCESS read-only
    STATUS mandatory
    DESCRIPTION
        "The name of the system boot image which the
        system booted from.
        This MIB object is only supported in the system
        with Supervisor module 3 present."
    ::= { systemGrp 38 }

sysEnableEntityTrap OBJECT-TYPE
    SYNTAX INTEGER {
        enabled(1),
        disabled(2)
        }
    ACCESS read-write
    STATUS mandatory
    DESCRIPTION
        "Indicates whether entConfigChange trap in the
        ENTITY-MIB should be generated."
    DEFVAL { disabled }
    ::= { systemGrp 39 }

sysEnableStpxTrap OBJECT-TYPE
    SYNTAX INTEGER {
        enabled(1),
        disabled(2),
        enabledForInconOnly(3),
        enabledForRootOnly(4),
        enabledForLoopOnly(5),
        enabledForInconRootOnly(6),
        enabledForInconLoopOnly(7),
        enabledForRootLoopOnly(8)
        }
    ACCESS read-write
    STATUS deprecated
    DESCRIPTION
        "Indicates whether stpxInconsistencyUpdate,
        stpxRootInconsistencyUpdate and
        stpxLoopInconsistencyUpdate notifications in
        CISCO-STP-EXTENSIONS-MIB should be generated.
        
        enabled -- the stpxInconsistencyUpdate,
                   stpxRootInconsistencyUpdate and
                   stpxLoopInconsistencyUpdate traps are
                   all enabled.
        
        disabled -- the stpxInconsistencyUpdate,
                   stpxRootInconsistencyUpdate and
                   stpxLoopInconsistencyUpdate traps
                   are all disabled.
        
        enabledForInconOnly -- only the
                   stpxInconsistencyUpdate trap is
                   enabled. This value is read-only.
        
        enabledForRootOnly -- only the
                   stpxRootInconsistencyUpdate trap is
                   enabled. This value is read-only.
        
        enabledForLoopOnly -- only the
                   stpxLoopInconsistencyUpdate trap is
                   enabled. This value is read-only.
        
        enabledForInconRootOnly -- only the
                   stpxInconsistencyUpdate and
                   stpxRootInconsistencyUpdate traps are
                   enabled. This value is read-only.
        
        enabledForInconLoopOnly -- only the
                   stpxInconsistencyUpdate and
                   stpxLoopInconsistencyUpdate traps are
                   enabled. This value is read-only.
        
        enabledForRootLoopOnly -- only the
                   stpxRootInconsistencyUpdate and
                   stpxLoopInconsistencyUpdate traps are
                   enabled. This value is read-only.
        
        This object is deprecated and replaced by
        stpxNotificationEnable in
        CISCO-STP-EXTENSIONS-MIB."
    DEFVAL { disabled }
    ::= { systemGrp 40 }

sysExtendedRmonVlanModeEnable OBJECT-TYPE
    SYNTAX INTEGER {
        enabled(1),
        disabled(2)
        }
    ACCESS read-write
    STATUS mandatory
    DESCRIPTION
        "Indicates whether the Extended RMON VlanMode
        feature is enabled or not. If it is set to
        enabled(1), hostTable (rmon 4) will provide the
        information of a list of VLANs instead of a list
        of MAC addresses for a monitored trunking port."
    DEFVAL { disabled }
    ::= { systemGrp 41 }

sysExtendedRmonNetflowPassword OBJECT-TYPE
    SYNTAX DisplayString(SIZE(0..20))
--    Rsyntax OCTET STRING(SIZE(0..20))
    ACCESS read-write
    STATUS mandatory
    DESCRIPTION
        "The password for enabling the Extended RMON
        Netflow feature and this object has to be set
        before setting sysExtendedRmonNetflowEnable to
        enabled(1). When reading this object, it will
        return empty string.
        
        If the platform supports
        sysExtendedRmonNetflowModuleMask object, this
        object will be not be supported."
    ::= { systemGrp 42 }

sysExtendedRmonNetflowEnable OBJECT-TYPE
    SYNTAX INTEGER {
        enabled(1),
        disabled(2)
        }
    ACCESS read-write
    STATUS mandatory
    DESCRIPTION
        "Indicates whether the Extended RMON Netflow
        feature is enabled or not. Setting this object to
        disabled(2), will clear
        sysExtendedRmonNetflowPassword automatically.
        Setting this object to enabled(1) will be rejected
        if sysExtendedRmonNetflowPassword does not contain
        a valid password.
        
        If the platform supports
        sysExtendedRmonNetflowModuleMask object, this
        object will not be supported."
    DEFVAL { disabled }
    ::= { systemGrp 43 }

sysExtendedRmonVlanAgentEnable OBJECT-TYPE
    SYNTAX INTEGER {
        enabled(1),
        disabled(2)
        }
    ACCESS read-write
    STATUS mandatory
    DESCRIPTION
        "Indicates whether the Extended RMON VlanAgent
        feature is enabled or not. If it is set to
        enabled(1), the extended RMON will also provide
        the information on VLAN based interface in
        addition to the port based interface for the
        monitored traffic.
        Setting this object to enabled(1), it will consume
        more CPU for processing each monitored frame and
        affect Extended RMON performance."
    DEFVAL { disabled }
    ::= { systemGrp 44 }

sysExtendedRmonEnable OBJECT-TYPE
    SYNTAX INTEGER {
        enabled(1),
        disabled(2),
        noNAMPresent(3)
        }
    ACCESS read-write
    STATUS mandatory
    DESCRIPTION
        "Indicates whether the SNMP agent supports the
        extended RMON feature. noNAMPresent(3) is a
        read-only value and the agent will return this
        value when the sysEnableExtendedRmon is set to
        enabled(1), but Network Analysis module is not
        present in the system."
    DEFVAL { enabled }
    ::= { systemGrp 45 }

sysConsolePrimaryLoginAuthentication OBJECT-TYPE
    SYNTAX INTEGER {
        tacacs(1),
        radius(2),
        local(3)
        }
    ACCESS read-write
    STATUS deprecated
    DESCRIPTION
        "Indicates whether TACACS+ or RADIUS is the
        primary login authentication, i.e which method
        will be tried first for a console session. If
        tacacsLoginAuthentication and
        radiusLoginAuthentication are set to disabled
        then sysConsolePrimaryLoginAuthentication will
        have a value of local(3).
        
        This object is deprecated and replaced by
        cacPriorityTable in CISCO-AAA-CLIENT-MIB."
    ::= { systemGrp 46 }

sysConsolePrimaryEnableAuthentication OBJECT-TYPE
    SYNTAX INTEGER {
        tacacs(1),
        radius(2),
        local(3)
        }
    ACCESS read-write
    STATUS deprecated
    DESCRIPTION
        "Indicates whether TACACS+ or RADIUS is the
        primary enable authentication, i.e which method
        will be  tried first for a console session. If
        tacacsEnableAuthentication and
        radiusEnableAuthentication are set to disabled
        then sysConsolePrimaryEnableAuthentication will
        have a value of local(3).
        
        This object is deprecated and replaced by
        cacPriorityTable in CISCO-AAA-CLIENT-MIB."
    ::= { systemGrp 47 }

sysTelnetPrimaryLoginAuthentication OBJECT-TYPE
    SYNTAX INTEGER {
        tacacs(1),
        radius(2),
        local(3)
        }
    ACCESS read-write
    STATUS deprecated
    DESCRIPTION
        "Indicates whether TACACS+ or RADIUS is the
        primary login authentication, i.e which method
        will be  tried first for a telnet session. If
        tacacsLoginAuthentication and
        radiusLoginAuthentication are set to disabled then
        sysTelnetPrimaryLoginAuthentication will have a
        value of local(3).
        
        This object is deprecated and replaced by
        cacPriorityTable in CISCO-AAA-CLIENT-MIB."
    ::= { systemGrp 48 }

sysTelnetPrimaryEnableAuthentication OBJECT-TYPE
    SYNTAX INTEGER {
        tacacs(1),
        radius(2),
        local(3)
        }
    ACCESS read-write
    STATUS deprecated
    DESCRIPTION
        "Indicates whether TACACS+ or RADIUS is the
        primary enable authentication, i.e which method
        will be tried first for a telnet session. If
        tacacsEnableAuthentication and
        radiusEnableAuthentication are set to disabled
        then sysTelnetPrimaryEnableAuthentication will
        have a value of local(3).
        
        This object is deprecated and replaced by
        cacPriorityTable in CISCO-AAA-CLIENT-MIB."
    ::= { systemGrp 49 }

sysStartupConfigSource OBJECT-TYPE
    SYNTAX INTEGER {
        flashFileRecurring(1),
        flashFileNonRecurring(2)
        }
    ACCESS read-write
    STATUS mandatory
    DESCRIPTION
        "Indicates whether the configuration file(s)
        specified in sysStartupConfigSourceFile will be
        used recurringly or not whenever the system
        resets.
        Setting this object to flashFileNonRecurring(2),
        the configuration file(s) specified in
        sysStartupConfigSourceFile will only be used once
        and the value of sysStartupConfigSourceFile will
        be reset to empty string automatically during the
        next system reset.
        
        This MIB object is only supported in systems with
        SupG supervisor models or supervisor models that
        have flash file system support."
    ::= { systemGrp 50 }

sysStartupConfigSourceFile OBJECT-TYPE
    SYNTAX DisplayString
--    Rsyntax OCTET STRING(SIZE(0..255))
    ACCESS read-write
    STATUS mandatory
    DESCRIPTION
        "Indicates which configuration file(s) on the
        flash device will be used during the next system
        startup.
        If the value of this MIB object contains one or
        multiple valid configuration file(s), then the
        valid configuration file(s) will reconfigure the
        system during the next system startup one by one
        in the order specified. If the value of this MIB
        object does not contain the valid configuration
        file(s) on the device, the NVRAM configuration
        will be used instead.
        
        For supervisor models wsx5540 and wsx5550, only
        'cfg1' and 'cfg2' are valid file names.
        
        For supervisor models with the flash file system
        support, the valid file name has the format of
        '<device:><file>[;<device:><file>...]'.
        
        This MIB object is only supported in systems with
        supervisor models wsx5540 and wsx5550 or
        supervisor models with the flash file system
        support."
    ::= { systemGrp 51 }

sysConfigSupervisorModuleNo OBJECT-TYPE
    SYNTAX INTEGER(1..16)
    ACCESS read-write
    STATUS mandatory
    DESCRIPTION
        "Indicates the supervisor module (active or
        standby, if applicable) that the MIB objects
        sysConfigRegister, sysBootVariable,
        sysStartupConfigSource, and
        sysStartupConfigSourceFile are specified for.
        
        This MIB object is only supported by the
        supervisor modules with the flash file system
        feature support. The default value for this MIB
        object is set to the active supervisor module
        number."
    ::= { systemGrp 52 }

sysStandbyPortEnable OBJECT-TYPE
    SYNTAX INTEGER {
        enabled(1),
        disabled(2)
        }
    ACCESS read-write
    STATUS mandatory
    DESCRIPTION
        "Indicates whether the standby port feature is
        enabled or not. If this object is set to
        enabled(1), the uplink ports on the standby
        supervisor module are activated; otherwise, the
        uplink ports on the standby supervisor remain
        inactive."
    DEFVAL { disabled }
    ::= { systemGrp 53 }

sysPortFastBpduGuard OBJECT-TYPE
    SYNTAX INTEGER {
        enabled(1),
        disabled(2)
        }
    ACCESS read-write
    STATUS deprecated
    DESCRIPTION
        "Indicates whether BPDU Guard for Spanning Tree
        Port Fast Start feature is enabled or not. If the
        value of this object is set to enabled(1), then
        when the switch receives a BPDU from a port with
        the value of portSpantreeFastStart object set to
        enabled(1), that port is immediately disabled.
        
        This object is deprecated and replaced by
        stpxFastStartBpduGuardEnable in
        CISCO-STP-EXTENSIONS-MIB."
    DEFVAL { disabled }
    ::= { systemGrp 54 }

sysErrDisableTimeoutEnable OBJECT-TYPE
    SYNTAX OCTET STRING(SIZE(1..3))
        -- BITS are:
        --   other(0)
        --   udld(1)
        --   duplexMismatch(2)
        --   bpduPortGuard(3)
        --   channelMisconfig(4)
        --   crossBarFallBack(5)
        --   gl2ptIngressLoop(6)
        --   gl2ptThresholdExceed(7)
        --   bcastSuppression(8)
        --   arpInspectionRate(9)
        --   noStaticInlinePwr(10)
        --   camMonitor(11)
        --   gl2ptCdpThresholdExceed(12)
        --   gl2ptStpThresholdExceed(13)
        --   gl2ptVtpThresholdExceed(14)
        --   linkRxCrc(15)
        --   linkTxCrc(16)
        --   linkInErrors(17)
        --   packetBufferError(18)
        --   ethernetOam(19)
        --   gl2ptEoamThresholdExceed(20)
    ACCESS read-write
    STATUS mandatory
    DESCRIPTION
        "Indicates whether errdisable timeout feature is
        enabled for each of the causes or not. The
        other(0) is for all causes other than:
        udld(1),
        duplexMismatch(2),
        bpduPortGuard(3),
        channelMisconfig(4),
        crossBarFallBack(5), (only supported on platforms
                              that support this errdisable
                              reason.)
        gl2ptIngressLoop(6), (only supported on platforms
                              that support this errdisable
                              reason.)
        gl2ptThresholdExceed(7), (only supported on
                              platforms that support this
                              errdisable reason.)
        bcastSuppression(8), (only supported on platforms
                              that support this errdisable
                              reason.)
        arpInspectionRate(9), (only supported on platforms
                              that support this errdisable
                              reason.)
        noStaticInlinePwr(10), (only supported on
                               platforms that support this
                               errdisable reason.)
        camMonitor(11),       (only supported on
                               platforms that support this
                               errdisable reason.)
        gl2ptCdpThresholdExceed(12), (only supported on
                               platforms that support this
                               errdisable reason.)
        gl2ptStpThresholdExceed(13), (only supported on
                               platforms that support this
                               errdisable reason.)
        gl2ptVtpThresholdExceed(14), (only supported on
                               platforms that support this
                               errdisable reason.)
        linkRxCrc(15),        (only supported on
                               platforms that support this
                               errdisable reason.)
        linkTxCrc(16),        (only supported on
                               platforms that support this
                               errdisable reason.)
        linkInErrors(17),     (only supported on
                               platforms that support this
                               errdisable reason.)
        packetBufferError(18), (only supported on
                               platforms that support this
                               errdisable reason.)
        ethernetOam(19),       (only supported on
                               platforms that support this
                               errdisable reason.)
        gl2ptEoamThresholdExceed(20), (only supported on
                               platforms that support this
                               errdisable reason.)
        
        A port is in errdisable state if ifAdminStatus of
        the port in the ifTable is up(1) while the port is
        shutdown during runtime by the system due to error
        detection. If the value of object
        portAdditionalOperStatus for the port is
        errdisable(11) then that port is in errdisable
        state.
        
        By setting the bit corresponding to a cause to
        '1', this errdisable timeout feature is enabled
        on the system for the ports that are put into
        errdisable state by that cause, then those ports
        can be re-enabled automatically during the timeout
        interval as specified by
        sysErrDisableTimeoutInterval object after they
        are put into errdisable state by that cause;
        otherwise, by setting the bit corresponding to a
        cause to '0', this errdisable timeout feature is
        disabled on the system for the ports that are put
        into errdisable state by that cause, then those
        ports will remain shutdown until the user
        re-enable it manually."
    DEFVAL { '000000'h }
    ::= { systemGrp 55 }

sysErrDisableTimeoutInterval OBJECT-TYPE
    SYNTAX INTEGER(30..86400)
--  Units
--    seconds
    ACCESS read-write
    STATUS mandatory
    DESCRIPTION
        "Indicates the timeout interval in seconds for
        errdisable timeout feature."
    DEFVAL { 300 }
    ::= { systemGrp 56 }

sysTrafficMonitorHighWaterMark OBJECT-TYPE
    SYNTAX INTEGER(0..100)
    ACCESS read-write
    STATUS mandatory
    DESCRIPTION
        "Indicates the high watermark for the switching
        bus traffic in percentage. Syslog messages will be
        generated if the switching bus traffic goes over
        this object value during the polling interval.
        Setting this object value to 100 would mean no
        syslog message would be generated. For systems
        with 3 switching buses, high watermark and syslog
        will be for each switching bus."
    DEFVAL { 100 }
    ::= { systemGrp 57 }

sysHighAvailabilityEnable OBJECT-TYPE
    SYNTAX TruthValue
--    Rsyntax INTEGER {
--        true(1),
--        false(2)
--        }
    ACCESS read-write
    STATUS mandatory
    DESCRIPTION
        "Indicates whether High System Availability
        feature is enabled or not. If this feature is
        enabled, the active supervisor's layer-2 protocol
        state will be synched to the standby supervisor
        module, thus maintaining an up-to-date protocol
        data on the standby supervisor whenever possible.
        
        This object is supported in systems with High
        System Availability feature support."
    DEFVAL { false }
    ::= { systemGrp 58 }

sysHighAvailabilityVersioningEnable OBJECT-TYPE
    SYNTAX TruthValue
--    Rsyntax INTEGER {
--        true(1),
--        false(2)
--        }
    ACCESS read-write
    STATUS mandatory
    DESCRIPTION
        "Indicates whether support for supervisor software
        image versioning (i.e., the capability to run
        different images on the active and standby
        supervisors) for the High System Availability
        feature is enabled or not.
        
        This object is supported in systems with High
        System Availability feature support."
    DEFVAL { false }
    ::= { systemGrp 59 }

sysHighAvailabilityOperStatus OBJECT-TYPE
    SYNTAX INTEGER {
        running(1),
        notRunning(2)
        }
    ACCESS read-only
    STATUS mandatory
    DESCRIPTION
        "Indicates the operational status of High System
        Availability feature. If the value of this object
        is notRunning(2), then the reason why this feature
        is actually not running is specified by the object
        sysHighAvailabilityNotRunningReason. If the value
        of this object is running(1), then the value of
        object sysHighAvailabilityOperReason is empty
        string.
        
        This object is supported in systems with High
        System Availability feature support."
    ::= { systemGrp 60 }

sysHighAvailabilityNotRunningReason OBJECT-TYPE
    SYNTAX DisplayString
--    Rsyntax OCTET STRING(SIZE(0..255))
    ACCESS read-only
    STATUS mandatory
    DESCRIPTION
        "Indicates the reason why High System Availability
        feature is not running when the value of
        sysHighAvailabilityOperStatus is notRunning(2).
         The value of this object is empty string when
        the value of sysHighAvailabilityOperStatus is
        running(1).
        
        This object is supported in systems with High
        System Availability feature support."
    ::= { systemGrp 61 }

sysExtendedRmonNetflowModuleMask OBJECT-TYPE
    SYNTAX OCTET STRING(SIZE(1..2))
        -- BITS are:
        --   module1(0)
        --   module2(1)
        --   module3(2)
        --   module4(3)
        --   module5(4)
        --   module6(5)
        --   module7(6)
        --   module8(7)
        --   module9(8)
        --   module10(9)
        --   module11(10)
        --   module12(11)
        --   module13(12)
        --   module14(13)
        --   module15(14)
        --   module16(15)
    ACCESS read-write
    STATUS mandatory
    DESCRIPTION
        "Indicates Netflow Export Data (NDE) to be sent to
        which Network Analysis Modules (NAM) in the same
        chassis.
        
        If users set a bit from off to on, the system will
        check the corresponding module is a NAM or not.
        If it is not, the system should return error.
        
        This mib object will only be supported by the
        system that can support the multiple NAM modules."
    ::= { systemGrp 62 }

sshPublicKeySize OBJECT-TYPE
    SYNTAX INTEGER(0|512..2048)
    ACCESS read-write
    STATUS mandatory
    DESCRIPTION
        "Indicates public key size in bits. In write, if
        a key does not exist, a value between 512 and 2048
        will generate a RSA public key with the value as
        its key size for secured shell access. If a key
        exists a value other than 0 is valid, indicating a
        clear key operation. In read, the current key size
        is returned if a key exists. If not,a 0 is
        returned."
    ::= { systemGrp 63 }

sysMaxRmonMemory OBJECT-TYPE
    SYNTAX INTEGER(0..100)
    ACCESS read-write
    STATUS mandatory
    DESCRIPTION
        "Indicates the maximum percentage of the memory
        usage for RMON."
    ::= { systemGrp 64 }

sysMacReductionAdminEnable OBJECT-TYPE
    SYNTAX TruthValue
--    Rsyntax INTEGER {
--        true(1),
--        false(2)
--        }
    ACCESS read-write
    STATUS mandatory
    DESCRIPTION
        "Indicates whether Mac Reduction feature (to
        reduce the number of MAC addresses used in
        bridge identifier) is administratively enabled
        on the device or not."
    ::= { systemGrp 65 }

sysMacReductionOperEnable OBJECT-TYPE
    SYNTAX TruthValue
--    Rsyntax INTEGER {
--        true(1),
--        false(2)
--        }
    ACCESS read-only
    STATUS mandatory
    DESCRIPTION
        "Indicates whether Mac Reduction feature (to
        reduce the number of MAC addresses used in
        bridge identifier) is operationaly enabled
        on the device or not.
        
        If the value of this object is true(1), then
        the accepted values for dot1dStpPriority
        in BRIDGE-MIB should be multiples of 4096 plus
        bridge instance ID, such as VlanIndex. Changing
        this object value might cause the values of
        dot1dBaseBridgeAddress and dot1dStpPriority
        in BRIDGE-MIB to be changed also."
    ::= { systemGrp 66 }

sysStatus OBJECT-TYPE
    SYNTAX INTEGER {
        other(1),
        ok(2),
        minorFault(3),
        majorFault(4)
        }
    ACCESS read-only
    STATUS mandatory
    DESCRIPTION
        "The operational status of the system."
    ::= { systemGrp 67 }

chassisSysType OBJECT-TYPE
    SYNTAX INTEGER {
        other(1),
        wsc1000(3),
        wsc1001(4),
        wsc1100(5),
        wsc5000(6),
        wsc2900(7),
        wsc5500(8),
        wsc5002(9),
        wsc5505(10),
        wsc1200(11),
        wsc1400(12),
        wsc2926(13),
        wsc5509(14),
        wsc6006(15),
        wsc6009(16),
        wsc4003(17),
        wsc5500e(18),
        wsc4912g(19),
        wsc2948g(20),
        wsc6509(22),
        wsc6506(23),
        wsc4006(24),
        wsc6509NEB(25),
        wsc2980g(26),
        wsc6513(27),
        wsc2980ga(28),
        cisco7603(30),
        cisco7606(31),
        cisco7609(32),
        wsc6503(33),
        wsc6509NEBA(34),
        wsc4507(35),
        wsc4503(36),
        wsc4506(37),
        wsc65509(38),
        cisco7613(40),
        wsc2948ggetx(41),
        cisco7604(42),
        wsc6504e(43),
        mec6524gs8s(45),
        mec6524gt8s(48),
        wsc6509ve(51),
        cisco7603s(52)
        }
    ACCESS read-only
    STATUS mandatory
    DESCRIPTION
        "The chassis system type."
    ::= { chassisGrp 1 }

chassisBkplType OBJECT-TYPE
    SYNTAX INTEGER {
        other(1),
        fddi(2),
        fddiEthernet(3),
        giga(4),
        giga3(5),
        giga3E(6),
        giga12(7),
        giga16(8),
        giga40(9)
        }
    ACCESS read-only
    STATUS mandatory
    DESCRIPTION
        "The chassis backplane type."
    ::= { chassisGrp 2 }

chassisPs1Type OBJECT-TYPE
    SYNTAX INTEGER {
        other(1),
        none(2),
        w50(3),
        w200(4),
        w600(5),
        w80(6),
        w130(7),
        wsc5008(8),
        wsc5008a(9),
        w175(10),
        wsc5068(11),
        wsc5508(12),
        wsc5568(13),
        wsc5508a(14),
        w155(15),
        w175pfc(16),
        w175dc(17),
        wsc5008b(18),
        wsc5008c(19),
        wsc5068b(20),
        wscac1000(21),
        wscac1300(22),
        wscdc1000(23),
        wscdc1360(24),
        wsx4008(25),
        wsc5518(26),
        wsc5598(27),
        w120(28),
        externalPS(29),
        wscac2500w(30),
        wscdc2500w(31),
        wsx4008dc(32),
        wscac4000w(33),
        pwr4000dc(34),
        pwr950ac(35),
        pwr950dc(36),
        pwr1900ac(37),
        pwr1900dc(38),
        pwr1900ac6(39),
        wsx4008ac650w(42),
        wsx4008dc650w(43),
        wscac3000w(44),
        pwrc451000ac(46),
        pwrc452800acv(47),
        pwrc451300acv(48),
        pwrc451400dcp(49),
        wscdc3000w(50),
        pwr1400ac(51),
        w156(52),
        wscac6000w(53),
        pwr2700ac(54),
        pwr2700dc(55),
        wscac8700we(58),
        pwr2700ac4(59),
        pwr2700dc4(60),
        pwr400dc(63),
        pwr400ac(64),
        pwr6000dc(105),
        pwr1500dc(106)
        }
    ACCESS read-only
    STATUS mandatory
    DESCRIPTION
        "Type of power supply number 1."
    ::= { chassisGrp 3 }

chassisPs1Status OBJECT-TYPE
    SYNTAX INTEGER {
        other(1),
        ok(2),
        minorFault(3),
        majorFault(4)
        }
    ACCESS read-only
    STATUS mandatory
    DESCRIPTION
        "Status of power supply number 1. If the status is
        not ok, the value of chassisPs1TestResult gives
        more detailed information about the power supply's
        failure condition(s)."
    ::= { chassisGrp 4 }

chassisPs1TestResult OBJECT-TYPE
    SYNTAX INTEGER(0..65535)
    ACCESS read-only
    STATUS mandatory
    DESCRIPTION
        "Test result for power supply number 1. A zero
        indicates that the supply passed all tests. Bits
        set in the result indicate error conditions."
    ::= { chassisGrp 5 }

chassisPs2Type OBJECT-TYPE
    SYNTAX INTEGER {
        other(1),
        none(2),
        w50(3),
        w200(4),
        w600(5),
        w80(6),
        w130(7),
        wsc5008(8),
        wsc5008a(9),
        w175(10),
        wsc5068(11),
        wsc5508(12),
        wsc5568(13),
        wsc5508a(14),
        w155(15),
        w175pfc(16),
        w175dc(17),
        wsc5008b(18),
        wsc5008c(19),
        wsc5068b(20),
        wscac1000(21),
        wscac1300(22),
        wscdc1000(23),
        wscdc1360(24),
        wsx4008(25),
        wsc5518(26),
        wsc5598(27),
        w120(28),
        externalPS(29),
        wscac2500w(30),
        wscdc2500w(31),
        wsx4008dc(32),
        wscac4000w(33),
        pwr4000dc(34),
        pwr950ac(35),
        pwr950dc(36),
        pwr1900ac(37),
        pwr1900dc(38),
        pwr1900ac6(39),
        wsx4008ac650w(42),
        wsx4008dc650w(43),
        wscac3000w(44),
        pwrc451000ac(46),
        pwrc452800acv(47),
        pwrc451300acv(48),
        pwrc451400dcp(49),
        wscdc3000w(50),
        pwr1400ac(51),
        w156(52),
        wscac6000w(53),
        pwr2700ac(54),
        pwr2700dc(55),
        wscac8700we(58),
        pwr2700ac4(59),
        pwr2700dc4(60),
        pwr400dc(63),
        pwr400ac(64),
        pwr6000dc(105),
        pwr1500dc(106)
        }
    ACCESS read-only
    STATUS mandatory
    DESCRIPTION
        "Type of power supply number 2."
    ::= { chassisGrp 6 }

chassisPs2Status OBJECT-TYPE
    SYNTAX INTEGER {
        other(1),
        ok(2),
        minorFault(3),
        majorFault(4)
        }
    ACCESS read-only
    STATUS mandatory
    DESCRIPTION
        "Status of power supply number 2. If the status is
        not ok, the value of chassisPs2TestResult gives
        more detailed information about the power supply's
        failure condition(s)."
    ::= { chassisGrp 7 }

chassisPs2TestResult OBJECT-TYPE
    SYNTAX INTEGER(0..65535)
    ACCESS read-only
    STATUS mandatory
    DESCRIPTION
        "Test result for power supply number 2. A zero
        indicates that the supply passed all tests. Bits
        set in the result indicate error conditions."
    ::= { chassisGrp 8 }

chassisFanStatus OBJECT-TYPE
    SYNTAX INTEGER {
        other(1),
        ok(2),
        minorFault(3),
        majorFault(4)
        }
    ACCESS read-only
    STATUS mandatory
    DESCRIPTION
        "Status of the chassis fan. If the status is not
        ok, the value of chassisFanTestResult gives more
        detailed information about the fan's failure
        condition(s)."
    ::= { chassisGrp 9 }

chassisFanTestResult OBJECT-TYPE
    SYNTAX INTEGER(0..65535)
    ACCESS read-only
    STATUS mandatory
    DESCRIPTION
        "Test result for the chassis fan. A zero indicates
        that the fan passed all tests. Bits set in the
        result indicate error conditions."
    ::= { chassisGrp 10 }

chassisMinorAlarm OBJECT-TYPE
    SYNTAX INTEGER {
        off(1),
        on(2)
        }
    ACCESS read-only
    STATUS mandatory
    DESCRIPTION
        "The chassis minor alarm status."
    ::= { chassisGrp 11 }

chassisMajorAlarm OBJECT-TYPE
    SYNTAX INTEGER {
        off(1),
        on(2)
        }
    ACCESS read-only
    STATUS mandatory
    DESCRIPTION
        "The chassis major alarm status."
    ::= { chassisGrp 12 }

chassisTempAlarm OBJECT-TYPE
    SYNTAX INTEGER {
        off(1),
        on(2),
        critical(3)
        }
    ACCESS read-only
    STATUS mandatory
    DESCRIPTION
        "The chassis temperature alarm status."
    ::= { chassisGrp 13 }

chassisNumSlots OBJECT-TYPE
    SYNTAX INTEGER(1..16)
    ACCESS read-only
    STATUS mandatory
    DESCRIPTION
        "The number of slots in the chassis available for
        plug-in modules."
    ::= { chassisGrp 14 }

chassisSlotConfig OBJECT-TYPE
    SYNTAX INTEGER(0..65535)
    ACCESS read-only
    STATUS mandatory
    DESCRIPTION
        "An indication of which slots in the chassis have
        modules inserted. This is an integer value with
        bits set to indicate configured modules. It can be
        interpreted as a sum of f(x) as x goes from 1 to
        the number of slots, where f(x) = 0 for no module
        inserted and f(x) = exp(2, x-1) for a module
        inserted."
    ::= { chassisGrp 15 }

chassisModel OBJECT-TYPE
    SYNTAX DisplayString(SIZE(0..20))
--    Rsyntax OCTET STRING(SIZE(0..20))
    ACCESS read-only
    STATUS mandatory
    DESCRIPTION
        "The manufacturer's model number for the chassis."
    ::= { chassisGrp 16 }

chassisSerialNumber OBJECT-TYPE
    SYNTAX INTEGER(0..999999999)
    ACCESS read-only
    STATUS deprecated
    DESCRIPTION
        "The serial number of the chassis in a numeric
        format. If the chassis uses an alphanumeric
        serial number, this MIB object will return 0.
        
        This object is deprecated and replaced by
        entPhysicalSerialNum in ENTITY-MIB."
    ::= { chassisGrp 17 }

chassisComponentTable OBJECT-TYPE
    SYNTAX SEQUENCE OF ChassisComponentEntry
    ACCESS not-accessible
    STATUS deprecated
    DESCRIPTION
        "A list of the chassis related components in the
        chassis.
        
        This table is deprecated and replaced by
        entPhysicalTable in ENTITY-MIB."
    ::= { chassisGrp 18 }

chassisComponentEntry OBJECT-TYPE
    SYNTAX ChassisComponentEntry
    ACCESS not-accessible
    STATUS deprecated
    DESCRIPTION
        "Entry containing information about one component
        in the chassis."
    INDEX { chassisComponentIndex }
    ::= { chassisComponentTable 1 }

ChassisComponentEntry ::= SEQUENCE {
    chassisComponentIndex INTEGER,
    chassisComponentType INTEGER,
    chassisComponentSerialNumber DisplayString,
    chassisComponentHwVersion DisplayString,
    chassisComponentModel DisplayString
    }

chassisComponentIndex OBJECT-TYPE
    SYNTAX INTEGER(1..65535)
    ACCESS read-only
    STATUS deprecated
    DESCRIPTION
        "A unique value for each chassis related component
        within the chassis."
    ::= { chassisComponentEntry 1 }

chassisComponentType OBJECT-TYPE
    SYNTAX INTEGER {
        unknown(1),
        wsc6000cl(2),
        wsc6000vtt(3),
        wsc6000tempSensor(4),
        wsc6513Clock(5),
        clk7600(6),
        ws9SlotFan(7),
        fanMod9(8),
        wsc6506eFan(10),
        wsc6509eFan(11),
        wsc6503eFan(13),
        wsc6000vtte(14),
        fanMod4Hs(15),
        fan6524(16),
        fanMod6Shs(17),
        fanMod9Shs(18),
        fanMod9St(19),
        wsc6509veFan(20),
        fanMod3Hs(21)
        }
    ACCESS read-only
    STATUS deprecated
    DESCRIPTION
        "The type of the chassis component."
    ::= { chassisComponentEntry 2 }

chassisComponentSerialNumber OBJECT-TYPE
    SYNTAX DisplayString(SIZE(0..20))
--    Rsyntax OCTET STRING(SIZE(0..20))
    ACCESS read-only
    STATUS deprecated
    DESCRIPTION
        "The serial number of the chassis component."
    ::= { chassisComponentEntry 3 }

chassisComponentHwVersion OBJECT-TYPE
    SYNTAX DisplayString(SIZE(0..20))
--    Rsyntax OCTET STRING(SIZE(0..20))
    ACCESS read-only
    STATUS deprecated
    DESCRIPTION
        "The hardware version of the chassis component."
    ::= { chassisComponentEntry 4 }

chassisComponentModel OBJECT-TYPE
    SYNTAX DisplayString(SIZE(0..20))
--    Rsyntax OCTET STRING(SIZE(0..20))
    ACCESS read-only
    STATUS deprecated
    DESCRIPTION
        "The manufacturer's model number for the chassis
        component."
    ::= { chassisComponentEntry 5 }

chassisSerialNumberString OBJECT-TYPE
    SYNTAX DisplayString(SIZE(0..20))
--    Rsyntax OCTET STRING(SIZE(0..20))
    ACCESS read-only
    STATUS mandatory
    DESCRIPTION
        "The serial number of the chassis. This MIB object
        will return the chassis serial number for any
        chassis that either a numeric or an alphanumeric
        serial number is being used."
    ::= { chassisGrp 19 }

chassisPs3Type OBJECT-TYPE
    SYNTAX INTEGER {
        other(1),
        none(2),
        wsx4008(25),
        wsx4008dc(32),
        wsx4008ac650w(42),
        wsx4008dc650w(43)
        }
    ACCESS read-only
    STATUS mandatory
    DESCRIPTION
        "Type of power supply number 3. This object is
        only supported by systems that can have 3 or more
        power supplies."
    ::= { chassisGrp 20 }

chassisPs3Status OBJECT-TYPE
    SYNTAX INTEGER {
        other(1),
        ok(2),
        minorFault(3),
        majorFault(4)
        }
    ACCESS read-only
    STATUS mandatory
    DESCRIPTION
        "Status of power supply number 3. If the status is
        not ok, the value of chassisPs3TestResult gives
        more detailed information about the power supply's
        failure condition(s). This object is only
        supported by systems that can have 3 or more
        power supplies."
    ::= { chassisGrp 21 }

chassisPs3TestResult OBJECT-TYPE
    SYNTAX INTEGER(0..65535)
    ACCESS read-only
    STATUS mandatory
    DESCRIPTION
        "Test result for power supply number 3. A zero
        indicates that the supply passed all tests. Bits
        set in the result indicate error conditions. This
        object is only supported by systems that can
        have 3 or more power supplies."
    ::= { chassisGrp 22 }

chassisPEMInstalled OBJECT-TYPE
    SYNTAX TruthValue
--    Rsyntax INTEGER {
--        true(1),
--        false(2)
--        }
    ACCESS read-only
    STATUS mandatory
    DESCRIPTION
        "Indicates whether Power Entry Module is installed
        into the Chassis or not. Power Entry Module is a
        connection into the system for an external
        power supply of -48 Volts. This object is only
        supported by systems that can have 3 or more power
        supplies."
    ::= { chassisGrp 23 }

moduleTable OBJECT-TYPE
    SYNTAX SEQUENCE OF ModuleEntry
    ACCESS not-accessible
    STATUS mandatory
    DESCRIPTION
        "A list of module entries. The number of entries
        is the number of modules in the chassis."
    ::= { moduleGrp 1 }

moduleEntry OBJECT-TYPE
    SYNTAX ModuleEntry
    ACCESS not-accessible
    STATUS mandatory
    DESCRIPTION
        "Entry containing information about one module in
        the chassis."
    INDEX { moduleIndex }
    ::= { moduleTable 1 }

ModuleEntry ::= SEQUENCE {
    moduleIndex INTEGER,
    moduleType INTEGER,
    moduleSerialNumber INTEGER,
    moduleHwHiVersion INTEGER,
    moduleHwLoVersion INTEGER,
    moduleFwHiVersion INTEGER,
    moduleFwLoVersion INTEGER,
    moduleSwHiVersion INTEGER,
    moduleSwLoVersion INTEGER,
    moduleStatus INTEGER,
    moduleTestResult INTEGER,
    moduleAction INTEGER,
    moduleName DisplayString,
    moduleNumPorts INTEGER,
    modulePortStatus OCTET STRING,
    moduleSubType INTEGER,
    moduleModel DisplayString,
    moduleHwVersion DisplayString,
    moduleFwVersion DisplayString,
    moduleSwVersion DisplayString,
    moduleStandbyStatus INTEGER,
    moduleIPAddress IpAddress,
    moduleIPAddressVlan VlanIndex,
    moduleSubType2 INTEGER,
    moduleSlotNum INTEGER,
    moduleSerialNumberString DisplayString,
    moduleEntPhysicalIndex PhysicalIndex,
    moduleAdditionalStatus OCTET STRING
    }

moduleIndex OBJECT-TYPE
    SYNTAX INTEGER(1..16)
    ACCESS read-only
    STATUS mandatory
    DESCRIPTION
        "A unique value for each module within the
         chassis."
    ::= { moduleEntry 1 }

moduleType OBJECT-TYPE
    SYNTAX INTEGER {
        other(1),
        empty(2),
        wsc1000(3),
        wsc1001(4),
        wsc1100(5),
        wsc1200(11),
        wsc1400(12),
        wsx1441(13),
        wsx1444(14),
        wsx1450(15),
        wsx1483(16),
        wsx1454(17),
        wsx1455(18),
        wsx1431(19),
        wsx1465(20),
        wsx1436(21),
        wsx1434(22),
        wsx5009(23),
        wsx5013(24),
        wsx5011(25),
        wsx5010(26),
        wsx5113(27),
        wsx5101(28),
        wsx5103(29),
        wsx5104(30),
        wsx5155(32),
        wsx5154(33),
        wsx5153(34),
        wsx5111(35),
        wsx5213(36),
        wsx5020(37),
        wsx5006(38),
        wsx5005(39),
        wsx5509(40),
        wsx5506(41),
        wsx5505(42),
        wsx5156(43),
        wsx5157(44),
        wsx5158(45),
        wsx5030(46),
        wsx5114(47),
        wsx5223(48),
        wsx5224(49),
        wsx5012(50),
        wsx5302(52),
        wsx5213a(53),
        wsx5380(54),
        wsx5201(55),
        wsx5203(56),
        wsx5530(57),
        wsx5161(61),
        wsx5162(62),
        wsx5165(65),
        wsx5166(66),
        wsx5031(67),
        wsx5410(68),
        wsx5403(69),
        wsx5201r(73),
        wsx5225r(74),
        wsx5014(75),
        wsx5015(76),
        wsx5236(77),
        wsx5540(78),
        wsx5234(79),
        wsx5012a(81),
        wsx5167(82),
        wsx5239(83),
        wsx5168(84),
        wsx5305(85),
        wsx5550(87),
        wsf5541(88),
        wsx5534(91),
        wsx5536(92),
        wsx5237(96),
        wsx6ksup12ge(200),
        wsx6408gbic(201),
        wsx6224mmmt(202),
        wsx6248rj45(203),
        wsx6248tel(204),
        wsx6302msm(206),
        wsf6kmsfc(207),
        wsx6024flmt(208),
        wsx6101oc12mmf(209),
        wsx6101oc12smf(210),
        wsx6416gemt(211),
        wsx61822pa(212),
        osm2oc12AtmMM(213),
        osm2oc12AtmSI(214),
        osm4oc12PosMM(216),
        osm4oc12PosSI(217),
        osm4oc12PosSL(218),
        wsx6ksup1a2ge(219),
        wsx6302amsm(220),
        wsx6416gbic(221),
        wsx6224ammmt(222),
        wsx6380nam(223),
        wsx6248arj45(224),
        wsx6248atel(225),
        wsx6408agbic(226),
        wsx6608t1(229),
        wsx6608e1(230),
        wsx6624fxs(231),
        wsx6316getx(233),
        wsf6kmsfc2(234),
        wsx6324mmmt(235),
        wsx6348rj45(236),
        wsx6ksup22ge(237),
        wsx6324sm(238),
        wsx6516gbic(239),
        osm4geWanGbic(240),
        osm1oc48PosSS(241),
        osm1oc48PosSI(242),
        osm1oc48PosSL(243),
        wsx6381ids(244),
        wsc6500sfm(245),
        osm16oc3PosMM(246),
        osm16oc3PosSI(247),
        osm16oc3PosSL(248),
        osm2oc12PosMM(249),
        osm2oc12PosSI(250),
        osm2oc12PosSL(251),
        wsx650210ge(252),
        osm8oc3PosMM(253),
        osm8oc3PosSI(254),
        osm8oc3PosSL(255),
        wsx6548rj45(258),
        wsx6524mmmt(259),
        wsx6066SlbApc(260),
        wsx6516getx(261),
        osm2oc48OneDptSS(265),
        osm2oc48OneDptSI(266),
        osm2oc48OneDptSL(267),
        osm2oc48OneDptSSDual(268),
        osm2oc48OneDptSIDual(269),
        osm2oc48OneDptSLDual(270),
        wsx6816gbic(271),
        osm4choc12T3MM(272),
        osm4choc12T3SI(273),
        osm8choc12T3MM(274),
        osm8choc12T3SI(275),
        osm1choc48T3SS(276),
        osm2choc48T3SS(277),
        wsx6500sfm2(278),
        osm1choc48T3SI(279),
        osm2choc48T3SI(280),
        wsx6348rj21(281),
        wsx6548rj21(282),
        wsSvcCmm(284),
        wsx650110gex4(285),
        osm4oc3PosSI(286),
        osm4oc3PosMM(289),
        wsSvcIdsm2(290),
        wsSvcNam2(291),
        wsSvcFwm1(292),
        wsSvcCe1(293),
        wsSvcSsl1(294),
        osm8choc3DS0SI(295),
        osm4choc3DS0SI(296),
        osm1choc12T1SI(297),
        wsx4012(300),
        wsx4148rj(301),
        wsx4232gbrj(302),
        wsx4306gb(303),
        wsx4418gb(304),
        wsx44162gbtx(305),
        wsx4912gb(306),
        wsx2948gbrj(307),
        wsx2948(309),
        wsx4912(310),
        wsx4424sxmt(311),
        wsx4232rjxx(312),
        wsx4148rj21(313),
        wsx4124fxmt(317),
        wsx4013(318),
        wsx4232l3(319),
        wsx4604gwy(320),
        wsx44122Gbtx(321),
        wsx2980(322),
        wsx2980rj(323),
        wsx2980gbrj(324),
        wsx4019(325),
        wsx4148rj45v(326),
        wsx4424gbrj45(330),
        wsx4148fxmt(331),
        wsx4448gblx(332),
        wsx4448gbrj45(334),
        wsx4148lxmt(337),
        wsx4548gbrj45(339),
        wsx4548gbrj45v(340),
        wsx4248rj21v(341),
        wsx4302gb(342),
        wsx4248rj45v(343),
        wsx2948ggetx(345),
        wsx2948ggetxgbrj(346),
        wsx6516aGbic(502),
        wsx6148getx(503),
        wsx6148x2rj45(506),
        wsx6196rj21(507),
        wssup32ge3b(509),
        wssup3210ge3b(510),
        mec6524gs8s(511),
        mec6524gt8s(512),
        wssup32pge(515),
        wssup32p10ge(516),
        wssvcpisa32(597),
        me6524msfc2a(598),
        wsf6kmsfc2a(599),
        osm12ct3T1(600),
        osm12t3e3(601),
        osm24t3e3(602),
        osm4GeWanGbicPlus(603),
        osm1choc12T3SI(604),
        osm2choc12T3SI(605),
        osm2oc12AtmMMPlus(606),
        osm2oc12AtmSIPlus(607),
        osm2oc12PosMMPlus(608),
        osm2oc12PosSIPlus(609),
        osm16oc3PosSIPlus(610),
        osm1oc48PosSSPlus(611),
        osm1oc48PosSIPlus(612),
        osm1oc48PosSLPlus(613),
        osm4oc3PosSIPlus(614),
        osm8oc3PosSLPlus(615),
        osm8oc3PosSIPlus(616),
        osm4oc12PosSIPlus(617),
        wsSvcIpSec1(903),
        wsSvcMwam1(910),
        wsSvcCsg1(911),
        wsx6148rj45v(912),
        wsx6148rj21v(913),
        wsSvcNam1(914),
        wsx6548getx(915),
        wsSvcPsd1(919),
        wsx6066SlbSk9(920),
        wsx6148agetx(921),
        wsx6148arj45(923),
        wsSvcWlan1k9(924),
        wsSvcAon1k9(925),
        ace106500k9(926),
        wsSvcWebVpnk9(927),
        wsx6148FeSfp(928),
        wsSvcAdm1k9(929),
        wsSvcAgm1k9(930),
        ace046500k9(936),
        wsSvcSamiBb(940),
        wssup720(1001),
        wssup720base(1002),
        m7600Sip600(1004),
        wsx6748getx(1007),
        wsx670410ge(1008),
        wsx6748sfp(1009),
        wsx6724sfp(1010),
        wsx670810ge(1016),
        vss72010g(1021),
        wsx671610ge(1027),
        wsx65822pa(1101),
        m7600Sip200(1102),
        m7600Sip400(1103),
        c7600ssc400(1104),
        c7600ssc600(1105),
        esm2x10ge(1106),
        rsp720(1800),
        rsp720base(1801),
        c7600msfc4(1805)
        }
    ACCESS read-only
    STATUS mandatory
    DESCRIPTION
        "The type of module."
    ::= { moduleEntry 2 }

moduleSerialNumber OBJECT-TYPE
    SYNTAX INTEGER(0..999999999)
    ACCESS read-only
    STATUS deprecated
    DESCRIPTION
        "The serial number of the module in a numeric
        format. If the module uses an alphanumeric serial
        number, this MIB object will return 0.
        
        This object is deprecated and replaced by
        entPhysicalSerialNum in ENTITY-MIB."
    ::= { moduleEntry 3 }

moduleHwHiVersion OBJECT-TYPE
    SYNTAX INTEGER(0..65535)
    ACCESS read-only
    STATUS deprecated
    DESCRIPTION
        "The high part of the hardware version of the
        module.
        For example, if the hardware version is 3.1, the
        value of moduleHwHiVersion is 3.
        
        This object is deprecated and replaced by
        entPhysicalHardwareRev in ENTITY-MIB."
    ::= { moduleEntry 4 }

moduleHwLoVersion OBJECT-TYPE
    SYNTAX INTEGER(0..65535)
    ACCESS read-only
    STATUS deprecated
    DESCRIPTION
        "The low part of the hardware version of the
        module.
        For example, if the hardware version is 3.1, the
        value of moduleHwLoVersion is 1.
        
        This object is deprecated and replaced by
        entPhysicalHardwareRev in ENTITY-MIB."
    ::= { moduleEntry 5 }

moduleFwHiVersion OBJECT-TYPE
    SYNTAX INTEGER(0..65535)
    ACCESS read-only
    STATUS deprecated
    DESCRIPTION
        "The high part of the firmware version number. For
        example, if the firmware version is 3.1, the value
        of moduleFwHiVersion is 3.
        
        This object is deprecated and replaced by
        entPhysicalFirmwareRev in ENTITY-MIB."
    ::= { moduleEntry 6 }

moduleFwLoVersion OBJECT-TYPE
    SYNTAX INTEGER(0..65535)
    ACCESS read-only
    STATUS deprecated
    DESCRIPTION
        "The low part of the firmware version number. For
        example, if the firmware version is 3.1, the value
        of moduleFwLoVersion is 1.
        
        This object is deprecated and replaced by
        entPhysicalFirmwareRev in ENTITY-MIB."
    ::= { moduleEntry 7 }

moduleSwHiVersion OBJECT-TYPE
    SYNTAX INTEGER(0..65535)
    ACCESS read-only
    STATUS deprecated
    DESCRIPTION
        "The high part of the software version number. For
        example, if the software version is 3.1, the value
        of moduleSwHiVersion is 3.
        
        This object is deprecated and replaced by
        entPhysicalSoftwareRev in ENTITY-MIB."
    ::= { moduleEntry 8 }

moduleSwLoVersion OBJECT-TYPE
    SYNTAX INTEGER(0..65535)
    ACCESS read-only
    STATUS deprecated
    DESCRIPTION
        "The low part of the software version number. For
        example, if the software version is 3.1, the value
        of moduleSwLoVersion is 1.
        
        This object is deprecated and replaced by
        entPhysicalSoftwareRev in ENTITY-MIB."
    ::= { moduleEntry 9 }

moduleStatus OBJECT-TYPE
    SYNTAX INTEGER {
        other(1),
        ok(2),
        minorFault(3),
        majorFault(4)
        }
    ACCESS read-only
    STATUS mandatory
    DESCRIPTION
        "The operational status of the module. If the
        status is not ok, the value of moduleTestResult
        gives more detailed information about the
        module's failure condition(s)."
    ::= { moduleEntry 10 }

moduleTestResult OBJECT-TYPE
    SYNTAX INTEGER(0..65535)
    ACCESS read-only
    STATUS mandatory
    DESCRIPTION
        "The result of the module's self test. A zero
        indicates that the module passed all tests. Bits
        set in the result indicate error conditions."
    ::= { moduleEntry 11 }

moduleAction OBJECT-TYPE
    SYNTAX INTEGER {
        other(1),
        reset(2),
        enable(3),
        disable(4)
        }
    ACCESS read-write
    STATUS mandatory
    DESCRIPTION
        "This object, when read, returns one of the
        following results:
            other(1):   module permanently enabled
            enable(3):  module currently enabled
            disable(4): module currently disabled
        Setting this object to one of the acceptable
        values gives the following results:
          other(1):  gives an error
          reset(2):  resets the module's control logic
          enable(3): if the module status is configurable,
                      enables the module, else gives error
          disable(4): if the module status is
                     configurable, disables the module,
                     else gives error.
        Setting this object to any other values results in
        an error."
    ::= { moduleEntry 12 }

moduleName OBJECT-TYPE
    SYNTAX DisplayString(SIZE(0..20))
--    Rsyntax OCTET STRING(SIZE(0..20))
    ACCESS read-write
    STATUS mandatory
    DESCRIPTION
        "A descriptive string used by the network
        administrator to name the module."
    ::= { moduleEntry 13 }

moduleNumPorts OBJECT-TYPE
    SYNTAX INTEGER(0..255)
    ACCESS read-only
    STATUS mandatory
    DESCRIPTION
        "The number of ports supported by the module."
    ::= { moduleEntry 14 }

modulePortStatus OBJECT-TYPE
    SYNTAX OCTET STRING
    ACCESS read-only
    STATUS mandatory
    DESCRIPTION
        "A series of bytes containing status information
        about the module and each of the ports on the
        module.
        The first byte contains the status for the module
        (same value as moduleStatus), and subsequent bytes
        contain status for the first through the last
        ports on the module (same value as
        portOperStatus)."
    ::= { moduleEntry 15 }

moduleSubType OBJECT-TYPE
    SYNTAX INTEGER {
        other(1),
        empty(2),
        wsf5510(3),
        wsf5511(4),
        wsx5304(6),
        wsf5520(7),
        wsf5521(8),
        wsf5531(9),
        wsf6020(100),
        wsf6020a(101),
        wsf6kpfc(102),
        wsf6kpfc2(103),
        wsf6kvpwr(104),
        wsf6kdfc(105),
        wsf6kpfc2a(106),
        wsf6kdfca(107),
        vsp300dfc(200),
        wsf6kpfc3a(201),
        wsf6kdfc3a(202),
        wsf6700dfc3a(203),
        wsf6kdfc3bxl(205),
        wsf6kpfc3bxl(206),
        wsf6700dfc3bxl(207),
        wsf6700cfc(208),
        m7600pfc3c(213),
        wsf6kpfc3b(216),
        wsf6700dfc3b(217),
        wsf6700dfc3c(218),
        wsf6700dfc3cxl(221),
        wsf6kdfc3b(223),
        mec6524pfc3c(224),
        sip600earl(225),
        vsf6kpfc3cxl(226),
        vsf6kpfc3c(227),
        c7600esmdfc3cxl(228),
        c7600esmdfc3c(230)
        }
    ACCESS read-only
    STATUS mandatory
    DESCRIPTION
        "The type of daughterboard attached to this
        module."
    ::= { moduleEntry 16 }

moduleModel OBJECT-TYPE
    SYNTAX DisplayString(SIZE(0..20))
--    Rsyntax OCTET STRING(SIZE(0..20))
    ACCESS read-only
    STATUS mandatory
    DESCRIPTION
        "The manufacturer's model number for the module."
    ::= { moduleEntry 17 }

moduleHwVersion OBJECT-TYPE
    SYNTAX DisplayString(SIZE(0..12))
--    Rsyntax OCTET STRING(SIZE(0..12))
    ACCESS read-only
    STATUS mandatory
    DESCRIPTION
        "The hardware version of the module."
    ::= { moduleEntry 18 }

moduleFwVersion OBJECT-TYPE
    SYNTAX DisplayString(SIZE(0..40))
--    Rsyntax OCTET STRING(SIZE(0..40))
    ACCESS read-only
    STATUS mandatory
    DESCRIPTION
        "The firmware version of the module."
    ::= { moduleEntry 19 }

moduleSwVersion OBJECT-TYPE
    SYNTAX DisplayString(SIZE(0..40))
--    Rsyntax OCTET STRING(SIZE(0..40))
    ACCESS read-only
    STATUS mandatory
    DESCRIPTION
        "The software version of the module."
    ::= { moduleEntry 20 }

moduleStandbyStatus OBJECT-TYPE
    SYNTAX INTEGER {
        other(1),
        active(2),
        standby(3),
        error(4)
        }
    ACCESS read-only
    STATUS mandatory
    DESCRIPTION
        "Redundant status of a module that supports
        redundancy."
    ::= { moduleEntry 21 }

moduleIPAddress OBJECT-TYPE
    SYNTAX IpAddress
    ACCESS read-only
    STATUS mandatory
    DESCRIPTION
        "If the module has a separate IP address to
         reach it by, then it is reported here.
         Otherwise, this object has a value of
         '00000000H'."
    ::= { moduleEntry 22 }

moduleIPAddressVlan OBJECT-TYPE
    SYNTAX VlanIndex
--    Rsyntax INTEGER(0..4095)
    ACCESS read-only
    STATUS mandatory
    DESCRIPTION
        "If the moduleIPAddress is valid then this
        object reports the VLAN to access that IP
        address on. Otherwise this object has a value
        of zero."
    ::= { moduleEntry 23 }

moduleSubType2 OBJECT-TYPE
    SYNTAX INTEGER {
        other(1),
        empty(2),
        wsu5531(3),
        wsu5533(5),
        wsu5534(6),
        wsu5535(7),
        wsu5536(8),
        wsu5537(9),
        wsu5538(10),
        wsu5539(11),
        wsg6488(102),
        wsg6489(103),
        wsg6483(104),
        wsg6485(105),
        wsf6kFe48af(106),
        wsf6kGe48af(107),
        wsf6kVpwrGe(108),
        wsf6kFe48x2af(109),
        wsf6kmsfc(207),
        wsf6kmsfc2(234),
        wsu4504fxmt(314),
        wsu4502gb(315),
        wssvcidsupg(402),
        wssvccmm6e1(403),
        wssvccmm6t1(404),
        wssvccmm24fxs(405),
        wssvccmmact(406),
        wssvcpisa32(597),
        me6524msfc2a(598),
        wsf6kmsfc2a(599),
        wssup720(1001),
        vsf6kmsfc3(1026),
        esm2x10ge(1701),
        c7600msfc4(1805)
        }
    ACCESS read-only
    STATUS mandatory
    DESCRIPTION
        "The type of daughterboard attached to this
        module."
    ::= { moduleEntry 24 }

moduleSlotNum OBJECT-TYPE
    SYNTAX INTEGER(1..16)
    ACCESS read-only
    STATUS mandatory
    DESCRIPTION
        "This value is determined by the chassis slot
        number where the module is located. Valid entries
        are 1 to the value of chassisNumSlots"
    ::= { moduleEntry 25 }

moduleSerialNumberString OBJECT-TYPE
    SYNTAX DisplayString(SIZE(0..20))
--    Rsyntax OCTET STRING(SIZE(0..20))
    ACCESS read-only
    STATUS mandatory
    DESCRIPTION
        "The serial number of the module. This MIB object
         will return the module serial number for any
         module that either a numeric or an alphanumeric
         serial number is being used."
    ::= { moduleEntry 26 }

moduleEntPhysicalIndex OBJECT-TYPE
    SYNTAX PhysicalIndex
--    Rsyntax INTEGER(1..2147483647)
    ACCESS read-only
    STATUS mandatory
    DESCRIPTION
        "The value of the instance of the entPhysicalIndex
        object, defined in ENTITY-MIB, for the entity
        physical index corresponding to this module."
    ::= { moduleEntry 27 }

moduleAdditionalStatus OBJECT-TYPE
    SYNTAX OCTET STRING(SIZE(1..2))
        -- BITS are:
        --   fruInstalled(0)
        --   powerDenied(1)
        --   faulty(2)
    ACCESS read-only
    STATUS mandatory
    DESCRIPTION
        "The additional status of the module.
        
         fruInstalled(0) indicates that whether or not
         FRU is installed on the module.
        
         powerDenied(1) indicates that whether phones
         connected to the ports of this module are
         denied of power.
        
         faulty(2) indicates hardware faulty."
    ::= { moduleEntry 28 }

portTable OBJECT-TYPE
    SYNTAX SEQUENCE OF PortEntry
    ACCESS not-accessible
    STATUS mandatory
    DESCRIPTION
        "A list of port entries. The number of entries is
        determined by the number of modules in the chassis
        and the number of ports on each module."
    ::= { portGrp 1 }

portEntry OBJECT-TYPE
    SYNTAX PortEntry
    ACCESS not-accessible
    STATUS mandatory
    DESCRIPTION
        "Entry containing information for a particular
        port on a module."
    INDEX { portModuleIndex, portIndex }
    ::= { portTable 1 }

PortEntry ::= SEQUENCE {
    portModuleIndex INTEGER,
    portIndex INTEGER,
    portCrossIndex INTEGER,
    portName DisplayString,
    portType INTEGER,
    portOperStatus INTEGER,
    portCrossGroupIndex INTEGER,
    portAdditionalStatus INTEGER,
    portAdminSpeed INTEGER,
    portDuplex INTEGER,
    portIfIndex INTEGER,
    portSpantreeFastStart INTEGER,
    portAdminRxFlowControl INTEGER,
    portOperRxFlowControl INTEGER,
    portAdminTxFlowControl INTEGER,
    portOperTxFlowControl INTEGER,
    portMacControlTransmitFrames Counter,
    portMacControlReceiveFrames Counter,
    portMacControlPauseTransmitFrames Counter,
    portMacControlPauseReceiveFrames Counter,
    portMacControlUnknownProtocolFrames Counter,
    portLinkFaultStatus INTEGER,
    portAdditionalOperStatus OCTET STRING,
    portInlinePowerDetect TruthValue,
    portEntPhysicalIndex PhysicalIndex,
    portErrDisableTimeOutEnable INTEGER
    }

portModuleIndex OBJECT-TYPE
    SYNTAX INTEGER(1..16)
    ACCESS read-only
    STATUS mandatory
    DESCRIPTION
        "An index value that uniquely identifies the
        module where this port is located."
    ::= { portEntry 1 }

portIndex OBJECT-TYPE
    SYNTAX INTEGER(1..255)
    ACCESS read-only
    STATUS mandatory
    DESCRIPTION
        "An index value that uniquely identifies this port
        within a module. The value is determined by the
        location of the port on the module. Valid entries
        are 1 to the value of moduleNumPorts for this
        module."
    ::= { portEntry 2 }

portCrossIndex OBJECT-TYPE
    SYNTAX INTEGER(1..4080)
    ACCESS read-only
    STATUS mandatory
    DESCRIPTION
        "A cross-reference to the port's index within
        another mib group. The value is dependent on the
        type of port. For an FDDI port, this corresponds
        to the snmpFddiPORTIndex."
    ::= { portEntry 3 }

portName OBJECT-TYPE
    SYNTAX DisplayString(SIZE(0..20))
--    Rsyntax OCTET STRING(SIZE(0..20))
    ACCESS read-write
    STATUS mandatory
    DESCRIPTION
        "A descriptive string used by the network
        administrator to name the port."
    ::= { portEntry 4 }

portType OBJECT-TYPE
    SYNTAX INTEGER {
        other(1),
        cddi(2),
        fddi(3),
        tppmd(4),
        mlt3(5),
        sddi(6),
        smf(7),
        e10BaseT(8),
        e10BaseF(9),
        scf(10),
        e100BaseTX(11),
        e100BaseT4(12),
        e100BaseF(13),
        atmOc3mmf(14),
        atmOc3smf(15),
        atmOc3utp(16),
        e100BaseFsm(17),
        e10a100BaseTX(18),
        mii(19),
        vlanRouter(20),
        remoteRouter(21),
        tokenring(22),
        atmOc12mmf(23),
        atmOc12smf(24),
        atmDs3(25),
        tokenringMmf(26),
        e1000BaseLX(27),
        e1000BaseSX(28),
        e1000BaseCX(29),
        networkAnalysis(30),
        e1000Empty(31),
        e1000BaseLH(32),
        e1000BaseT(33),
        e1000UnsupportedGbic(34),
        e1000BaseZX(35),
        depi2(36),
        t1(37),
        e1(38),
        fxs(39),
        fxo(40),
        transcoding(41),
        conferencing(42),
        atmOc12mm(43),
        atmOc12smi(44),
        atmOc12sml(45),
        posOc12mm(46),
        posOc12smi(47),
        posOc12sml(48),
        posOc48sms(49),
        posOc48smi(50),
        posOc48sml(51),
        posOc3mm(52),
        posOc3smi(53),
        posOc3sml(54),
        intrusionDetect(55),
        e10GBaseCPX(56),
        e10GBaseLX4(57),
        e10GBaseEX4(59),
        e10GEmpty(60),
        e10a100a1000BaseT(61),
        dptOc48mm(62),
        dptOc48smi(63),
        dptOc48sml(64),
        e10GBaseLR(65),
        chOc12smi(66),
        chOc12mm(67),
        chOc48ss(68),
        chOc48smi(69),
        e10GBaseSX4(70),
        e10GBaseER(71),
        contentEngine(72),
        ssl(73),
        firewall(74),
        vpnIpSec(75),
        ct3(76),
        e1000BaseCwdm1470(77),
        e1000BaseCwdm1490(78),
        e1000BaseCwdm1510(79),
        e1000BaseCwdm1530(80),
        e1000BaseCwdm1550(81),
        e1000BaseCwdm1570(82),
        e1000BaseCwdm1590(83),
        e1000BaseCwdm1610(84),
        e1000BaseBT(85),
        e1000BaseUnapproved(86),
        chOc3smi(87),
        mcr(88),
        coe(89),
        mwa(90),
        psd(91),
        e100BaseLX(92),
        e10GBaseSR(93),
        e10GBaseCX4(94),
        e10GBaseWdm1550(95),
        e10GBaseEdc1310(96),
        e10GBaseSW(97),
        e10GBaseLW(98),
        e10GBaseEW(99),
        lwa(100),
        aons(101),
        sslVpn(102),
        e100BaseEmpty(103),
        adsm(104),
        agsm(105),
        aces(106),
        intrusionProtect(109),
        e1000BaseSvc(110),
        e10GBaseSvc(111),
        e1000BaseUnknown(1000),
        e10GBaseUnknown(1001),
        e10GBaseUnapproved(1002),
        e1000BaseWdmRxOnly(1003),
        e1000BaseDwdm3033(1004),
        e1000BaseDwdm3112(1005),
        e1000BaseDwdm3190(1006),
        e1000BaseDwdm3268(1007),
        e1000BaseDwdm3425(1008),
        e1000BaseDwdm3504(1009),
        e1000BaseDwdm3582(1010),
        e1000BaseDwdm3661(1011),
        e1000BaseDwdm3819(1012),
        e1000BaseDwdm3898(1013),
        e1000BaseDwdm3977(1014),
        e1000BaseDwdm4056(1015),
        e1000BaseDwdm4214(1016),
        e1000BaseDwdm4294(1017),
        e1000BaseDwdm4373(1018),
        e1000BaseDwdm4453(1019),
        e1000BaseDwdm4612(1020),
        e1000BaseDwdm4692(1021),
        e1000BaseDwdm4772(1022),
        e1000BaseDwdm4851(1023),
        e1000BaseDwdm5012(1024),
        e1000BaseDwdm5092(1025),
        e1000BaseDwdm5172(1026),
        e1000BaseDwdm5252(1027),
        e1000BaseDwdm5413(1028),
        e1000BaseDwdm5494(1029),
        e1000BaseDwdm5575(1030),
        e1000BaseDwdm5655(1031),
        e1000BaseDwdm5817(1032),
        e1000BaseDwdm5898(1033),
        e1000BaseDwdm5979(1034),
        e1000BaseDwdm6061(1035),
        e10GBaseWdmRxOnly(1036),
        e10GBaseDwdm3033(1037),
        e10GBaseDwdm3112(1038),
        e10GBaseDwdm3190(1039),
        e10GBaseDwdm3268(1040),
        e10GBaseDwdm3425(1041),
        e10GBaseDwdm3504(1042),
        e10GBaseDwdm3582(1043),
        e10GBaseDwdm3661(1044),
        e10GBaseDwdm3819(1045),
        e10GBaseDwdm3898(1046),
        e10GBaseDwdm3977(1047),
        e10GBaseDwdm4056(1048),
        e10GBaseDwdm4214(1049),
        e10GBaseDwdm4294(1050),
        e10GBaseDwdm4373(1051),
        e10GBaseDwdm4453(1052),
        e10GBaseDwdm4612(1053),
        e10GBaseDwdm4692(1054),
        e10GBaseDwdm4772(1055),
        e10GBaseDwdm4851(1056),
        e10GBaseDwdm5012(1057),
        e10GBaseDwdm5092(1058),
        e10GBaseDwdm5172(1059),
        e10GBaseDwdm5252(1060),
        e10GBaseDwdm5413(1061),
        e10GBaseDwdm5494(1062),
        e10GBaseDwdm5575(1063),
        e10GBaseDwdm5655(1064),
        e10GBaseDwdm5817(1065),
        e10GBaseDwdm5898(1066),
        e10GBaseDwdm5979(1067),
        e10GBaseDwdm6061(1068),
        e1000BaseBX10D(1069),
        e1000BaseBX10U(1070),
        e100BaseUnknown(1071),
        e100BaseUnapproved(1072),
        e100BaseSX(1073),
        e100BaseBX10D(1074),
        e100BaseBX10U(1075),
        e10GBaseBad(1076),
        e10GBaseZR(1077),
        e100BaseEX(1078),
        e100BaseZX(1079),
        e10GBaseLRM(1080),
        e10GBaseT(1081)
        }
    ACCESS read-only
    STATUS mandatory
    DESCRIPTION
        "The type of physical layer medium dependent
        interface on the port."
    ::= { portEntry 5 }

portOperStatus OBJECT-TYPE
    SYNTAX INTEGER {
        other(1),
        ok(2),
        minorFault(3),
        majorFault(4)
        }
    ACCESS read-only
    STATUS mandatory
    DESCRIPTION
        "The current operational status of the port."
    ::= { portEntry 6 }

portCrossGroupIndex OBJECT-TYPE
    SYNTAX INTEGER(1..16)
    ACCESS read-only
    STATUS mandatory
    DESCRIPTION
        "A cross-reference to another mib group for this
        port. The value is dependent on the type of port.
        For an FDDI port this corresponds to the
        snmpFddiPORTSMTIndex."
    ::= { portEntry 7 }

portAdditionalStatus OBJECT-TYPE
    SYNTAX INTEGER(0..7)
    ACCESS read-only
    STATUS mandatory
    DESCRIPTION
        "Additional status information for the port. The
        value is a sum. It initially takes the value zero,
        then for each state that is true, 2 raised to a
        power is added to the sum. The powers are
        according to the following table:
                 State    Power
              Transmit    0
               Receive    1
             Collision    2
        Transmit state indicates that at least one packet
        was transmitted by the port in the last polling
        period. Receive state indicates that at least one
        packet was received by the port in the last
        polling period. Collision state indicates that
        at least one collision was detected on the port
        in the last polling period.
        Note that if a state is not applicable to a
        particular port or additional status is not
        supported on a particular port, its value is
        always false for that port."
    ::= { portEntry 8 }

portAdminSpeed OBJECT-TYPE
    SYNTAX INTEGER {
        autoDetect(1),
        autoDetect10100(2),
        s4000000(4000000),
        s10000000(10000000),
        s16000000(16000000),
        s45000000(45000000),
        s64000000(64000000),
        s100000000(100000000),
        s155000000(155000000),
        s400000000(400000000),
        s622000000(622000000),
        s1000000000(1000000000),
        s1544000(1544000),
        s2000000(2000000),
        s2048000(2048000),
        s64000(64000),
        s10G(10)
        }
    ACCESS read-write
    STATUS mandatory
    DESCRIPTION
        "The desired speed of the port.
        The current operational speed of the port can be
        determined from ifSpeed."
    ::= { portEntry 9 }

portDuplex OBJECT-TYPE
    SYNTAX INTEGER {
        half(1),
        full(2),
        disagree(3),
        auto(4)
        }
    ACCESS read-write
    STATUS mandatory
    DESCRIPTION
        "Indicates whether the port is operating in half-
        duplex, full-duplex, disagree or auto negotiation
        mode. If the port could not agree with the far end
        on port duplex, the port will be in disagree(3)
        mode."
    ::= { portEntry 10 }

portIfIndex OBJECT-TYPE
    SYNTAX INTEGER(1..2147483647)
    ACCESS read-only
    STATUS mandatory
    DESCRIPTION
        "The value of the instance of the ifIndex object,
        defined in MIB-II, for the interface corresponding
        to this port."
    ::= { portEntry 11 }

portSpantreeFastStart OBJECT-TYPE
    SYNTAX INTEGER {
        enabled(1),
        disabled(2)
        }
    ACCESS read-write
    STATUS deprecated
    DESCRIPTION
        "Indicates whether the port is operating in
        spantree fast start mode. A port with fast start
        enabled is immediately put in spanning tree
        forwarding state on link up, rather than starting
        in blocking state which is the normal operation.
        This is useful when the port is known to be
        connected to a single station which has problems
        waiting for the normal spanning tree operation to
        put the port in forwarding state.
        
        This object is deprecated and replaced by
        stpxFastStartPortTable in
        CISCO-STP-EXTENSIONS-MIB."
    DEFVAL { disabled }
    ::= { portEntry 12 }

portAdminRxFlowControl OBJECT-TYPE
    SYNTAX INTEGER {
        on(1),
        off(2),
        desired(3)
        }
    ACCESS read-write
    STATUS mandatory
    DESCRIPTION
        "Indicates the receive flow control administrative
        status set on the port. If the status is set to
        on(1), the port will require the far end to send
        flow control. If the status is set to off(2), the
        port will not allow far end to send flow control.
        If the status is set to desired(3), the port will
        allow the far end to send the flow control."
    DEFVAL { off }
    ::= { portEntry 13 }

portOperRxFlowControl OBJECT-TYPE
    SYNTAX INTEGER {
        on(1),
        off(2),
        disagree(3)
        }
    ACCESS read-only
    STATUS mandatory
    DESCRIPTION
        "Indicates the receive flow control operational
        status of the port. If the port could not agree
        with the far end on a link protocol, its
        operational status will be disagree(3)."
    ::= { portEntry 14 }

portAdminTxFlowControl OBJECT-TYPE
    SYNTAX INTEGER {
        on(1),
        off(2),
        desired(3)
        }
    ACCESS read-write
    STATUS mandatory
    DESCRIPTION
        "Indicates the transmit flow control
        administrative status set on the port.
        If the status is set to on(1), the port will send
        flow control to the far end.
        If the status is set to off(2), the port will not
        send flow control to the far end. If the status is
        set to desired(3), the port will send flow control
        to the far end if the far end supports it."
    ::= { portEntry 15 }

portOperTxFlowControl OBJECT-TYPE
    SYNTAX INTEGER {
        on(1),
        off(2),
        disagree(3)
        }
    ACCESS read-only
    STATUS mandatory
    DESCRIPTION
        "Indicates the transmit flow control operational
        status of the port. If the port could not agree
        with the far end on a link protocol, its
        operational status will be disagree(3)."
    ::= { portEntry 16 }

portMacControlTransmitFrames OBJECT-TYPE
    SYNTAX Counter
    ACCESS read-only
    STATUS mandatory
    DESCRIPTION
        "The total number of MAC control frames passed to
        the MAC sublayer for transmission."
    ::= { portEntry 17 }

portMacControlReceiveFrames OBJECT-TYPE
    SYNTAX Counter
    ACCESS read-only
    STATUS mandatory
    DESCRIPTION
        "The total number of MAC control frames passed by
        the MAC sublayer to the MAC Control sublayer on
        receive."
    ::= { portEntry 18 }

portMacControlPauseTransmitFrames OBJECT-TYPE
    SYNTAX Counter
    ACCESS read-only
    STATUS mandatory
    DESCRIPTION
        "The total number of PAUSE frames passed to
        the MAC sublayer for transmission."
    ::= { portEntry 19 }

portMacControlPauseReceiveFrames OBJECT-TYPE
    SYNTAX Counter
    ACCESS read-only
    STATUS mandatory
    DESCRIPTION
        "The total number of PAUSE frames passed by
        the MAC sublayer to the MAC Control sublayer
        on receive."
    ::= { portEntry 20 }

portMacControlUnknownProtocolFrames OBJECT-TYPE
    SYNTAX Counter
    ACCESS read-only
    STATUS mandatory
    DESCRIPTION
        "The total number of MAC Control frames received
        with an opcode that is not supported by the
        device."
    ::= { portEntry 21 }

portLinkFaultStatus OBJECT-TYPE
    SYNTAX INTEGER {
        noFault(1),
        nearEndFault(2),
        nearEndConfigFail(3),
        farEndDisable(4),
        farEndFault(5),
        farEndConfigFail(6),
        notApplicable(7)
        }
    ACCESS read-only
    STATUS mandatory
    DESCRIPTION
        "Specifies additional link fault status on a
        gigabit link.
        
        noFault:
                Link is up and operational.
        nearEndFault:
                The port is enabled but there is no GBIC
                present or the local port cannot
                synchronize with the remote end.
        nearEndConfigFail:
                The local port has detected a
                configuration mismatch with the remote
                end.
        farEndDisable:
                The far end is in the disabled state.
        farEndFault:
                The remote port is cannot synchronize.
        farEndConfigFail:
                The remote port has detected a
                configuration mismatch with the local end.
        notApplicable:
                Link fault status is not applicable on
                this port."
    ::= { portEntry 22 }

portAdditionalOperStatus OBJECT-TYPE
    SYNTAX OCTET STRING(SIZE(1..2))
        -- BITS are:
        --   other(0)
        --   connected(1)
        --   standby(2)
        --   faulty(3)
        --   notConnected(4)
        --   inactive(5)
        --   shutdown(6)
        --   dripDis(7)
        --   disabled(8)
        --   monitor(9)
        --   errdisable(10)
        --   linkFaulty(11)
        --   onHook(12)
        --   offHook(13)
        --   reflector(14)
    ACCESS read-only
    STATUS mandatory
    DESCRIPTION
        "The current operational status of the port which
        is showing additional detailed information of the
        port."
    ::= { portEntry 23 }

portInlinePowerDetect OBJECT-TYPE
    SYNTAX TruthValue
--    Rsyntax INTEGER {
--        true(1),
--        false(2)
--        }
    ACCESS read-only
    STATUS mandatory
    DESCRIPTION
        "Indicate if the port detects an inline power capable
         device connected to it."
    ::= { portEntry 24 }

portEntPhysicalIndex OBJECT-TYPE
    SYNTAX PhysicalIndex
--    Rsyntax INTEGER(1..2147483647)
    ACCESS read-only
    STATUS mandatory
    DESCRIPTION
        "The value of the instance of the entPhysicalIndex
        object, defined in ENTITY-MIB, for the
        entity physical index corresponding to this port."
    ::= { portEntry 25 }

portErrDisableTimeOutEnable OBJECT-TYPE
    SYNTAX INTEGER {
        enabled(1),
        disabled(2)
        }
    ACCESS read-write
    STATUS mandatory
    DESCRIPTION
        "Indicates whether a port that is put into
        errdisable state by a cause as specified by
        sysErrDisableTimeoutEnable will be re-enabled
        automatically during the timeout interval as
        specified by sysErrDisableTimeoutInterval."
    DEFVAL { enabled }
    ::= { portEntry 26 }

tftpHost OBJECT-TYPE
    SYNTAX DisplayString(SIZE(0..64))
--    Rsyntax OCTET STRING(SIZE(0..64))
    ACCESS read-write
    STATUS mandatory
    DESCRIPTION
        "Name of source/destination host for the TFTP
        transfer or storage device transfer. If the name
        is for the TFTP transfer, it can be the IP
        address or the host name. If the name for the
        storage device transfer, it will be in the format
        of deviceName: (e.g. slot0:, slot1:)."
    ::= { tftpGrp 1 }

tftpFile OBJECT-TYPE
    SYNTAX DisplayString(SIZE(0..64))
--    Rsyntax OCTET STRING(SIZE(0..64))
    ACCESS read-write
    STATUS mandatory
    DESCRIPTION
        "Name of file for the TFTP transfer or for storage
         device transfer."
    ::= { tftpGrp 2 }

tftpModule OBJECT-TYPE
    SYNTAX INTEGER(0..16)
    ACCESS read-write
    STATUS mandatory
    DESCRIPTION
        "Which module's code/configuration is being
        transferred."
    ::= { tftpGrp 3 }

tftpAction OBJECT-TYPE
    SYNTAX INTEGER {
        other(1),
        downloadConfig(2),
        uploadConfig(3),
        downloadSw(4),
        uploadSw(5),
        downloadFw(6),
        uploadFw(7)
        }
    ACCESS read-write
    STATUS mandatory
    DESCRIPTION
        "Setting this object to one of the acceptable
        values initiates the requested action using the
        information given in tftpHost, tftpFile,
        tftpModule.
        
            downloadConfig(2): receive configuration from
                               host/file
            uploadConfig(3)  : send configuration to
                               host/file
            downloadSw(4)    : receive software image from
                               host/file
            uploadSw(5)      : send software image to
                               host/file
            downloadFw(6)    : receive firmware image from
                               host/file
            uploadFw(7)      : send firmware image to
                               host/file
        Setting this object to any other value results in
        an error."
    ::= { tftpGrp 4 }

tftpResult OBJECT-TYPE
    SYNTAX INTEGER {
        inProgress(1),
        success(2),
        noResponse(3),
        tooManyRetries(4),
        noBuffers(5),
        noProcesses(6),
        badChecksum(7),
        badLength(8),
        badFlash(9),
        serverError(10),
        userCanceled(11),
        wrongCode(12),
        fileNotFound(13),
        invalidTftpHost(14),
        invalidTftpModule(15),
        accessViolation(16),
        unknownStatus(17),
        invalidStorageDevice(18),
        insufficientSpaceOnStorageDevice(19),
        insufficientDramSize(20),
        incompatibleImage(21)
        }
    ACCESS read-only
    STATUS mandatory
    DESCRIPTION
        "Contains result of the last tftp action request."
    ::= { tftpGrp 5 }

brouterEnableRip OBJECT-TYPE
    SYNTAX INTEGER {
        enabled(1),
        disabled(2)
        }
    ACCESS read-write
    STATUS mandatory
    DESCRIPTION
        "Indicates whether the RIP protocol is enabled."
    DEFVAL { enabled }
    ::= { brouterGrp 1 }

brouterEnableSpantree OBJECT-TYPE
    SYNTAX INTEGER {
        enabled(1),
        disabled(2)
        }
    ACCESS read-write
    STATUS mandatory
    DESCRIPTION
        "Indicates if Spanning Tree protocol is enabled."
    DEFVAL { disabled }
    ::= { brouterGrp 2 }

brouterEnableGiantCheck OBJECT-TYPE
    SYNTAX INTEGER {
        enabled(1),
        disabled(2)
        }
    ACCESS read-write
    STATUS mandatory
    DESCRIPTION
        "Indicates whether special handling of giant
        packets is enabled."
    DEFVAL { disabled }
    ::= { brouterGrp 3 }

brouterEnableIpFragmentation OBJECT-TYPE
    SYNTAX INTEGER {
        enabled(1),
        disabled(2)
        }
    ACCESS read-write
    STATUS mandatory
    DESCRIPTION
        "Indicates whether IP fragmentation is enabled."
    DEFVAL { enabled }
    ::= { brouterGrp 4 }

brouterEnableUnreachables OBJECT-TYPE
    SYNTAX INTEGER {
        enabled(1),
        disabled(2)
        }
    ACCESS read-write
    STATUS mandatory
    DESCRIPTION
        "Indicates whether ICMP unreachable messages are
        sent by the system."
    DEFVAL { enabled }
    ::= { brouterGrp 5 }

brouterCamAgingTime OBJECT-TYPE
    SYNTAX INTEGER(0..1000000)
    ACCESS read-write
    STATUS deprecated
    DESCRIPTION
        "The aging time for the CAM table. This duplicate
        item is the same value as dot1dTpAgingTime."
    DEFVAL { 300 }
    ::= { brouterGrp 6 }

brouterCamMode OBJECT-TYPE
    SYNTAX INTEGER {
        filtering(1),
        forwarding(2)
        }
    ACCESS read-write
    STATUS mandatory
    DESCRIPTION
        "Mode in which the CAM module is operating."
    DEFVAL { filtering }
    ::= { brouterGrp 7 }

brouterIpxSnapToEther OBJECT-TYPE
    SYNTAX INTEGER {
        snap(1),
        ethernetII(2),
        iso8023(3),
        raw8023(4)
        }
    ACCESS read-write
    STATUS mandatory
    DESCRIPTION
        "The default translation for IPX packets when
        bridging from FDDI SNAP to Ethernet."
    DEFVAL { raw8023 }
    ::= { brouterGrp 8 }

brouterIpx8023RawToFddi OBJECT-TYPE
    SYNTAX INTEGER {
        snap(1),
        iso8022(5),
        fddiRaw(6)
        }
    ACCESS read-write
    STATUS mandatory
    DESCRIPTION
        "The default translation for IPX packets when
        bridging from Ethernet 802.3 Raw to FDDI."
    DEFVAL { snap }
    ::= { brouterGrp 9 }

brouterEthernetReceiveMax OBJECT-TYPE
    SYNTAX INTEGER(1..100)
    ACCESS read-write
    STATUS mandatory
    DESCRIPTION
        "Maximum number of Ethernet receive buffers
        processed at one time per port."
    DEFVAL { 64 }
    ::= { brouterGrp 10 }

brouterEthernetTransmitMax OBJECT-TYPE
    SYNTAX INTEGER(1..100)
    ACCESS read-write
    STATUS mandatory
    DESCRIPTION
        "Maximum number of Ethernet transmit buffers
        processed at one time per port."
    DEFVAL { 64 }
    ::= { brouterGrp 11 }

brouterFddiReceiveMax OBJECT-TYPE
    SYNTAX INTEGER(1..512)
    ACCESS read-write
    STATUS mandatory
    DESCRIPTION
        "Maximum number of FDDI receive buffers processed
        at one time per port."
    DEFVAL { 256 }
    ::= { brouterGrp 12 }

brouterFddiTransmitMax OBJECT-TYPE
    SYNTAX INTEGER(1..512)
    ACCESS read-write
    STATUS mandatory
    DESCRIPTION
        "Maximum number of FDDI transmit buffers processed
        at one time per port."
    DEFVAL { 256 }
    ::= { brouterGrp 13 }

brouterPortTable OBJECT-TYPE
    SYNTAX SEQUENCE OF BrouterPortEntry
    ACCESS not-accessible
    STATUS mandatory
    DESCRIPTION
        "A list of brouter port entries. The number of
        entries is determined by the number of modules in
        the chassis and the number of ports on each
        module."
    ::= { brouterGrp 14 }

brouterPortEntry OBJECT-TYPE
    SYNTAX BrouterPortEntry
    ACCESS not-accessible
    STATUS mandatory
    DESCRIPTION
        "Entry containing bridge/router information for a
        particular port on a module."
    INDEX { brouterPortModule, brouterPort }
    ::= { brouterPortTable 1 }

BrouterPortEntry ::= SEQUENCE {
    brouterPortModule INTEGER,
    brouterPort INTEGER,
    brouterPortIpVlan VlanIndex,
    brouterPortIpAddr IpAddress,
    brouterPortNetMask IpAddress,
    brouterPortBroadcast IpAddress,
    brouterPortBridgeVlan INTEGER,
    brouterPortIpHelpers OCTET STRING
    }

brouterPortModule OBJECT-TYPE
    SYNTAX INTEGER(1..16)
    ACCESS read-only
    STATUS mandatory
    DESCRIPTION
        "An index value that uniquely identifies the
        module index where this port is located."
    ::= { brouterPortEntry 1 }

brouterPort OBJECT-TYPE
    SYNTAX INTEGER(1..255)
    ACCESS read-only
    STATUS mandatory
    DESCRIPTION
        "An index value that uniquely identifies this port
        within a module (see portIndex)."
    ::= { brouterPortEntry 2 }

brouterPortIpVlan OBJECT-TYPE
    SYNTAX VlanIndex
--    Rsyntax INTEGER(0..4095)
    ACCESS read-write
    STATUS mandatory
    DESCRIPTION
        "The IP Virtual LAN to which this port belongs."
    ::= { brouterPortEntry 3 }

brouterPortIpAddr OBJECT-TYPE
    SYNTAX IpAddress
    ACCESS read-write
    STATUS mandatory
    DESCRIPTION
        "This port's IP address."
    ::= { brouterPortEntry 4 }

brouterPortNetMask OBJECT-TYPE
    SYNTAX IpAddress
    ACCESS read-write
    STATUS mandatory
    DESCRIPTION
        "This port's subnet mask."
    ::= { brouterPortEntry 5 }

brouterPortBroadcast OBJECT-TYPE
    SYNTAX IpAddress
    ACCESS read-write
    STATUS mandatory
    DESCRIPTION
        "This port's broadcast address."
    ::= { brouterPortEntry 6 }

brouterPortBridgeVlan OBJECT-TYPE
    SYNTAX INTEGER(0..1023)
    ACCESS read-write
    STATUS mandatory
    DESCRIPTION
        "The bridge Virtual LAN to which this port
        belongs."
    ::= { brouterPortEntry 7 }

brouterPortIpHelpers OBJECT-TYPE
    SYNTAX OCTET STRING(SIZE(0..128))
    ACCESS read-write
    STATUS mandatory
    DESCRIPTION
        "An indication of which other Virtual LANs UDP/IP
        broadcasts received on this port will be forwarded
        to. The normal situation is broadcasts NOT
        forwarded beyond the originating VLAN, but it can
        be useful in certain circumstances. This is an
        octet string value with bits set to indicate
        forwarded to VLANs. It can be interpreted as a sum
        of f(x) as x goes from 0 to 1023, where f(x) = 0
        for no forwarding to VLAN x and f(x) = exp(2, x)
        for VLAN x forwarded to. If all bits are 0 or the
        octet string is zero length, then UDP/IP
        broadcasts are not being forwarded to other
        VLANs."
    ::= { brouterPortEntry 8 }

brouterIpx8022ToEther OBJECT-TYPE
    SYNTAX INTEGER {
        snap(1),
        ethernetII(2),
        iso8023(3),
        raw8023(4)
        }
    ACCESS read-write
    STATUS mandatory
    DESCRIPTION
        "The default translation for IPX packets when
        bridging from FDDI 802.2 to Ethernet."
    DEFVAL { iso8023 }
    ::= { brouterGrp 15 }

brouterEnableTransitEncapsulation OBJECT-TYPE
    SYNTAX INTEGER {
        enabled(1),
        disabled(2)
        }
    ACCESS read-write
    STATUS mandatory
    DESCRIPTION
        "Indicates whether Ethernet packets are
        encapsulated on FDDI via transit encapsulation
        protocol. Normally this option would be disabled
        to allow translational bridging between Ethernet
        and FDDI to take place."
    DEFVAL { disabled }
    ::= { brouterGrp 16 }

brouterEnableFddiCheck OBJECT-TYPE
    SYNTAX INTEGER {
        enabled(1),
        disabled(2)
        }
    ACCESS read-write
    STATUS mandatory
    DESCRIPTION
        "Indicates whether MAC addresses learned one side
        of a translational bridge should not be allowed to
        be learned on the other side of the bridge. The
        presence certain misbehaving devices on the
        network may require this option to be enabled."
    DEFVAL { disabled }
    ::= { brouterGrp 17 }

brouterEnableAPaRT OBJECT-TYPE
    SYNTAX INTEGER {
        enabled(1),
        disabled(2)
        }
    ACCESS read-write
    STATUS mandatory
    DESCRIPTION
        "Indicates whether the Automatic Packet
        Recognition and Translation feature is enabled on
        translational bridge(s) in the box. If APaRT is
        disabled, the default translations as defined by
        the objects brouterIpx8022ToEther,
        brouterIpx8023RawToFddi, brouterIpxSnapToEther,
        etc, are used on all packets and no automatic
        learning of translation information is performed."
    DEFVAL { enabled }
    ::= { brouterGrp 18 }

filterMacTable OBJECT-TYPE
    SYNTAX SEQUENCE OF FilterMacEntry
    ACCESS not-accessible
    STATUS mandatory
    DESCRIPTION
        "A list of filter mac entries."
    ::= { filterGrp 1 }

filterMacEntry OBJECT-TYPE
    SYNTAX FilterMacEntry
    ACCESS not-accessible
    STATUS mandatory
    DESCRIPTION
        "Entry containing MAC address filter information."
    INDEX { filterMacModule, filterMacPort, filterMacAddress }
    ::= { filterMacTable 1 }

FilterMacEntry ::= SEQUENCE {
    filterMacModule INTEGER,
    filterMacPort INTEGER,
    filterMacAddress MacAddress,
    filterMacType INTEGER
    }

filterMacModule OBJECT-TYPE
    SYNTAX INTEGER(1..16)
    ACCESS read-only
    STATUS mandatory
    DESCRIPTION
        "An index value that uniquely identifies the
        module where this port is located
        (see portModuleIndex)."
    ::= { filterMacEntry 1 }

filterMacPort OBJECT-TYPE
    SYNTAX INTEGER(1..255)
    ACCESS read-only
    STATUS mandatory
    DESCRIPTION
        "An index value that uniquely identifies this port
        within a module (see portIndex)."
    ::= { filterMacEntry 2 }

filterMacAddress OBJECT-TYPE
    SYNTAX MacAddress
--    Rsyntax OCTET STRING(SIZE(6))
    ACCESS read-only
    STATUS mandatory
    DESCRIPTION
        "A MAC address. If the source or destination MAC
        address equals this value, a match occurs. The
        packet is dropped if a match occurs and deny(1)
        was specified. The packet is dropped if a match
        doesn't occur and at least one MAC address filter
        was specified with permit(3)."
    ::= { filterMacEntry 3 }

filterMacType OBJECT-TYPE
    SYNTAX INTEGER {
        deny(1),
        invalid(2),
        permit(3),
        permitSrc(4),
        permitDst(5),
        denySrc(6),
        denyDst(7),
        denySrcLearn(8)
        }
    ACCESS read-write
    STATUS mandatory
    DESCRIPTION
        "Setting this object to invalid(2) removes the
        corresponding entry from the filterMacTable.
        To add a new entry to the filterMacTable, set this
        object to deny(1) or any value from permit(3) to
        denySrcLearn(8) for a module, port, and MAC
        address not already in the table."
    ::= { filterMacEntry 4 }

filterVendorTable OBJECT-TYPE
    SYNTAX SEQUENCE OF FilterVendorEntry
    ACCESS not-accessible
    STATUS mandatory
    DESCRIPTION
        "A list of filter vendor ID entries."
    ::= { filterGrp 2 }

filterVendorEntry OBJECT-TYPE
    SYNTAX FilterVendorEntry
    ACCESS not-accessible
    STATUS mandatory
    DESCRIPTION
        "Entry containing vendor ID filter information."
    INDEX { filterVendorModule, filterVendorPort, filterVendorId }
    ::= { filterVendorTable 1 }

FilterVendorEntry ::= SEQUENCE {
    filterVendorModule INTEGER,
    filterVendorPort INTEGER,
    filterVendorId VendorIdType,
    filterVendorType INTEGER
    }

filterVendorModule OBJECT-TYPE
    SYNTAX INTEGER(1..16)
    ACCESS read-only
    STATUS mandatory
    DESCRIPTION
        "An index value that uniquely identifies the
        module where this port is located
        (see portModuleIndex)."
    ::= { filterVendorEntry 1 }

filterVendorPort OBJECT-TYPE
    SYNTAX INTEGER(1..255)
    ACCESS read-only
    STATUS mandatory
    DESCRIPTION
        "An index value that uniquely identifies this port
        within a module (see portIndex)."
    ::= { filterVendorEntry 2 }

filterVendorId OBJECT-TYPE
    SYNTAX VendorIdType
--    Rsyntax OCTET STRING(SIZE(3))
    ACCESS read-only
    STATUS mandatory
    DESCRIPTION
        "The vendor ID portion of a MAC address. If the
        source or destination MAC address has the same
        vendor ID, a match occurs. The packet is dropped
        if a match occurs and deny(1) was specified. The
        packet is dropped if a match doesn't occur and at
        least one Vendor ID filter was specified with
        permit(3)."
    ::= { filterVendorEntry 3 }

filterVendorType OBJECT-TYPE
    SYNTAX INTEGER {
        deny(1),
        invalid(2),
        permit(3)
        }
    ACCESS read-write
    STATUS mandatory
    DESCRIPTION
        "Setting this object to invalid(2) removes the
        corresponding entry from the filterVendorTable.
        To add a new entry to the filterVendorTable, set
        this object to deny(1) or permit(3) for a module,
        port, and vendor ID not already in the table."
    ::= { filterVendorEntry 4 }

filterProtocolTable OBJECT-TYPE
    SYNTAX SEQUENCE OF FilterProtocolEntry
    ACCESS not-accessible
    STATUS mandatory
    DESCRIPTION
        "A list of filter protocol entries."
    ::= { filterGrp 3 }

filterProtocolEntry OBJECT-TYPE
    SYNTAX FilterProtocolEntry
    ACCESS not-accessible
    STATUS mandatory
    DESCRIPTION
        "Entry containing PROTOCOL address filter
        information."
    INDEX { filterProtocolModule, filterProtocolPort, filterProtocolValue }
    ::= { filterProtocolTable 1 }

FilterProtocolEntry ::= SEQUENCE {
    filterProtocolModule INTEGER,
    filterProtocolPort INTEGER,
    filterProtocolValue INTEGER,
    filterProtocolType INTEGER
    }

filterProtocolModule OBJECT-TYPE
    SYNTAX INTEGER(1..16)
    ACCESS read-only
    STATUS mandatory
    DESCRIPTION
        "An index value that uniquely identifies the
        module where this port is located
        (see portModuleIndex)."
    ::= { filterProtocolEntry 1 }

filterProtocolPort OBJECT-TYPE
    SYNTAX INTEGER(1..255)
    ACCESS read-only
    STATUS mandatory
    DESCRIPTION
        "An index value that uniquely identifies this port
        within a module (see portIndex)."
    ::= { filterProtocolEntry 2 }

filterProtocolValue OBJECT-TYPE
    SYNTAX INTEGER(0..65535)
    ACCESS read-only
    STATUS mandatory
    DESCRIPTION
        "A 16-bit protocol value. If the packet's type
        field or the packet's DSAP/SSAP field is equal to
        this value, a match occurs. The packet is dropped
        if a match occurs and deny(1) was specified. The
        packet is dropped if a match doesn't occur and at
        least one protocol type filter was specified with
        permit(3)."
    ::= { filterProtocolEntry 3 }

filterProtocolType OBJECT-TYPE
    SYNTAX INTEGER {
        deny(1),
        invalid(2),
        permit(3)
        }
    ACCESS read-write
    STATUS mandatory
    DESCRIPTION
        "Setting this object to invalid(2) removes the
        corresponding entry from the filterProtocolTable.
        To add a new entry to the filterProtocolTable, set
        this object to deny(1) or permit(3) for a module,
        port, and protocol value not already in the
        table."
    ::= { filterProtocolEntry 4 }

filterTestTable OBJECT-TYPE
    SYNTAX SEQUENCE OF FilterTestEntry
    ACCESS not-accessible
    STATUS mandatory
    DESCRIPTION
        "A list of filter test entries."
    ::= { filterGrp 4 }

filterTestEntry OBJECT-TYPE
    SYNTAX FilterTestEntry
    ACCESS not-accessible
    STATUS mandatory
    DESCRIPTION
        "Entry containing test filter information."
    INDEX { filterTestModule, filterTestPort, filterTestIndex }
    ::= { filterTestTable 1 }

FilterTestEntry ::= SEQUENCE {
    filterTestModule INTEGER,
    filterTestPort INTEGER,
    filterTestIndex INTEGER,
    filterTestType INTEGER,
    filterTestOffset INTEGER,
    filterTestValue INTEGER,
    filterTestMask INTEGER
    }

filterTestModule OBJECT-TYPE
    SYNTAX INTEGER(1..16)
    ACCESS read-only
    STATUS mandatory
    DESCRIPTION
        "An index value that uniquely identifies the
        module where this port is located
        (see portModuleIndex)."
    ::= { filterTestEntry 1 }

filterTestPort OBJECT-TYPE
    SYNTAX INTEGER(1..255)
    ACCESS read-only
    STATUS mandatory
    DESCRIPTION
        "An index value that uniquely identifies this port
        within a module (see portIndex)."
    ::= { filterTestEntry 2 }

filterTestIndex OBJECT-TYPE
    SYNTAX INTEGER(1..8)
    ACCESS read-only
    STATUS mandatory
    DESCRIPTION
        "An index value that uniquely identifies a test
         for a particular module/port."
    ::= { filterTestEntry 3 }

filterTestType OBJECT-TYPE
    SYNTAX INTEGER {
        valid(1),
        invalid(2)
        }
    ACCESS read-write
    STATUS mandatory
    DESCRIPTION
        "Setting this object to invalid(2) removes the
        corresponding entry from the filterTestTable. To
        add a new entry to the filterTestTable, set this
        object to valid(1) for a module, port, and test
        index not already in the table."
    ::= { filterTestEntry 4 }

filterTestOffset OBJECT-TYPE
    SYNTAX INTEGER(0..4500)
    ACCESS read-write
    STATUS mandatory
    DESCRIPTION
        "A byte offset into packet. Must be a 32-bit word
        aligned offset, i.e. 0, 4, 8, etc."
    ::= { filterTestEntry 5 }

filterTestValue OBJECT-TYPE
    SYNTAX INTEGER(0..2147483647)
    ACCESS read-write
    STATUS mandatory
    DESCRIPTION
        "A 32-bit value to be compared against the packet
        location specified by filterTestOffset."
    ::= { filterTestEntry 6 }

filterTestMask OBJECT-TYPE
    SYNTAX INTEGER(0..2147483647)
    ACCESS read-write
    STATUS mandatory
    DESCRIPTION
        "A 32-bit value to be bitwise ANDed with the
        packet location specified by filterTestOffset
        before  being compared to filterTestValue."
    ::= { filterTestEntry 7 }

filterPortTable OBJECT-TYPE
    SYNTAX SEQUENCE OF FilterPortEntry
    ACCESS not-accessible
    STATUS mandatory
    DESCRIPTION
        "A list of filter port entries. The number of
        entries is determined by the number of modules in
        the chassis and the number of ports on each
        module."
    ::= { filterGrp 5 }

filterPortEntry OBJECT-TYPE
    SYNTAX FilterPortEntry
    ACCESS not-accessible
    STATUS mandatory
    DESCRIPTION
        "Entry containing filter information for a
        particular port on a module."
    INDEX { filterPortModule, filterPort }
    ::= { filterPortTable 1 }

FilterPortEntry ::= SEQUENCE {
    filterPortModule INTEGER,
    filterPort INTEGER,
    filterPortComplex DisplayString,
    filterPortBroadcastThrottle INTEGER,
    filterPortBroadcastThreshold INTEGER,
    filterPortBroadcastDiscards Counter,
    filterPortBroadcastThresholdFraction INTEGER,
    filterPortSuppressionOption OCTET STRING,
    filterPortSuppressionViolation INTEGER
    }

filterPortModule OBJECT-TYPE
    SYNTAX INTEGER(1..16)
    ACCESS read-only
    STATUS mandatory
    DESCRIPTION
        "An index value that uniquely identifies the
        module where this port is located
        (see portModuleIndex)."
    ::= { filterPortEntry 1 }

filterPort OBJECT-TYPE
    SYNTAX INTEGER(1..255)
    ACCESS read-only
    STATUS mandatory
    DESCRIPTION
        "An index value that uniquely identifies this port
        within a module (see portIndex)."
    ::= { filterPortEntry 2 }

filterPortComplex OBJECT-TYPE
    SYNTAX DisplayString(SIZE(0..50))
--    Rsyntax OCTET STRING(SIZE(0..50))
    ACCESS read-write
    STATUS mandatory
    DESCRIPTION
        "A complex expression made up of the numbers 1
        through 8 indicating test results from
        filterTestIndex and using logical operators '&'
        (and), '|' (or), '!' (not), and parenthesis. For
        example: ((1 & 2) | !3). If this complex filter
        matches a packet, it is dropped."
    ::= { filterPortEntry 3 }

filterPortBroadcastThrottle OBJECT-TYPE
    SYNTAX INTEGER(0..150000)
    ACCESS read-write
    STATUS mandatory
    DESCRIPTION
        "The maximum number of broadcast packets per
        second allowed on this port. If the number of
        incoming broadcast packets in a one second
        interval exceeds this amount, packets are
        dropped for the rest of the interval. If the
        capability exists, only broadcast packets should
        be dropped. Otherwise, all packets are dropped
        during the suppression interval.
        
        A value of 0 indicates broadcast packets should
        not be limited.
        
        The ability to suppress broadcast packets in this
        manner exists only on certain ports. If it does
        not exist on this port, attempts to write a value
        other than 0 are rejected.
        
        This object also applies to multicast (and/or)
        unicast suppression when
        filterPortSuppressionOption is enabled."
    DEFVAL { 0 }
    ::= { filterPortEntry 4 }

filterPortBroadcastThreshold OBJECT-TYPE
    SYNTAX INTEGER(0..100)
    ACCESS read-write
    STATUS mandatory
    DESCRIPTION
        "Indicates the integer part of the maximum
        percentage of available bandwidth allowed for
        incoming traffic of the specific traffic types on
        this port. The associated object
        filterPortBroadcastThresholdFraction indicates the
        fraction part of the maximum percentage of
        available bandwidth allowed for incoming traffic
        of the specific traffic types on this port. Either
        packets of the specific traffic types are dropped
        of the port is put into errdisable state depending
        on the value of filterPortSuppressionViolation on
        this port if the percentage of incoming traffic of
        the specific traffic types would exceed this
        limit. The traffic types that are enabled for
        this traffic suppression feature is indicated by
        filterPortBroadcastOption.
        
        The maximum percentage for the combination of this
        object value and the object value of
        filterPortBroadcastThresholdFraction is 100.00
        which indicates traffic of all traffic types
        should not be limited.
        
        The ability to suppress traffic in this manner
        exists only on certain ports. If it does not
        exist on this port, attempts to write a value of
        this object other than 100 are rejected.
        
        On platforms where filterPortSuppressionOption
        object is not supported, this object only applies
        to broadcast suppression."
    DEFVAL { 100 }
    ::= { filterPortEntry 5 }

filterPortBroadcastDiscards OBJECT-TYPE
    SYNTAX Counter
    ACCESS read-only
    STATUS mandatory
    DESCRIPTION
        "The number of packets discarded due to traffic
        suppression on this port."
    ::= { filterPortEntry 6 }

filterPortBroadcastThresholdFraction OBJECT-TYPE
    SYNTAX INTEGER(0..99)
--  Units
--    one-hundredths
    ACCESS read-write
    STATUS mandatory
    DESCRIPTION
        "Indicates the fraction part of the maximum
        percentage of available bandwidth allowed for
        incoming traffic of the specific traffic types on
        this port. The associated object
        filterPortBroadcastThreshold indicates the integer
        part of the maximum percentage of available
        bandwidth allowed for incoming traffic of the
        specific traffic types on this port. Either
        packets of the specific traffic types are dropped
        or the port is put into errdisable state
        depending on the value of
        filterPortSuppressionViolation on this port if the
        percentage of incoming traffic of the specific
        traffic type would exceed this limit. The
        traffic types that are enabled for this traffic
        suppression feature is indicated by
        filterPortBroadcastOption.
        
        The maximum percentage for the combination
        of this object value and the object value of
        filterPortBroadcastThreshold is 100.00 which
        indicates traffic of all traffic types should not
        be limited.
        
        The ability to suppress traffic in this manner
        exists only on certain ports. If it does not exist
        on this port, attempts to write a value of this
        object other than 100 are rejected.
        
        On platforms where filterPortSuppressionOption
        object is not supported, this object only applies
        to broadcast suppression."
    DEFVAL { 0 }
    ::= { filterPortEntry 7 }

filterPortSuppressionOption OBJECT-TYPE
    SYNTAX OCTET STRING(SIZE(1..2))
        -- BITS are:
        --   multicast(0)
        --   unicast(1)
        --   broadcast(2)
    ACCESS read-write
    STATUS mandatory
    DESCRIPTION
        "Indicates the traffic types that traffic
        suppression feature is enabled for.
        
        multicast(0) is set when multicast suppression is
        enabled. unicast(1) is set when unicast
        suppression is enabled. broadcast(2) is set when
        broadcast suppression is enabled."
    ::= { filterPortEntry 8 }

filterPortSuppressionViolation OBJECT-TYPE
    SYNTAX INTEGER {
        dropPackets(1),
        errdisable(2)
        }
    ACCESS read-write
    STATUS mandatory
    DESCRIPTION
        "Indicates the action that will be taken on this
        port when the percentage of either broadcast,
        multicast or unicast traffic exceeds the limit as
        indicated by filterPortBroadcastThreshold and
        filterPortBroadcastThresholdFraction.
        
        
        dropPackets - the excessive packets will be
                    - dropped on this port.
        
        errdisable - the port will be put into errdisable
                   - state.
        
        The object is only supported on platforms that
        support this suppression violation action
        feature."
    ::= { filterPortEntry 9 }

monitorSourceModule OBJECT-TYPE
    SYNTAX INTEGER(0..16)
    ACCESS read-write
    STATUS deprecated
    DESCRIPTION
        "An index value that uniquely identifies the
        module where the monitoring source port is
        located. A value of 0 indicates that the
        monitorSourcePort is really a source Virtual LAN
        number. To monitor multiple source ports, this
        object should be set to 0 and
        monitorAdminSourcePorts should be configured."
    ::= { monitorGrp 1 }

monitorSourcePort OBJECT-TYPE
    SYNTAX INTEGER(0..1023)
    ACCESS read-write
    STATUS deprecated
    DESCRIPTION
        "An index value that uniquely identifies the
        monitoring source port within a module or the
        monitoring source Virtual LAN. To monitor multiple
        source ports, this object should be set to 0 and
        monitorAdminSourcePorts should be configured"
    ::= { monitorGrp 2 }

monitorDestinationModule OBJECT-TYPE
    SYNTAX INTEGER(1..16)
    ACCESS read-write
    STATUS deprecated
    DESCRIPTION
        "An index value that uniquely identifies the
        module where the monitoring destination port is
        located."
    ::= { monitorGrp 3 }

monitorDestinationPort OBJECT-TYPE
    SYNTAX INTEGER(1..255)
    ACCESS read-write
    STATUS deprecated
    DESCRIPTION
        "An index value that uniquely identifies the
        monitoring destination port within a module."
    ::= { monitorGrp 4 }

monitorDirection OBJECT-TYPE
    SYNTAX INTEGER {
        transmit(1),
        receive(2),
        transmitAndReceive(3)
        }
    ACCESS read-write
    STATUS deprecated
    DESCRIPTION
        "The type of packets to be monitored at the source
        port."
    DEFVAL { transmitAndReceive }
    ::= { monitorGrp 5 }

monitorEnable OBJECT-TYPE
    SYNTAX INTEGER {
        enabled(1),
        disabled(2)
        }
    ACCESS read-write
    STATUS deprecated
    DESCRIPTION
        "Indicates whether port monitoring is in
        progress."
    DEFVAL { disabled }
    ::= { monitorGrp 6 }

monitorAdminSourcePorts OBJECT-TYPE
    SYNTAX OCTET STRING(SIZE(0..128))
    ACCESS read-write
    STATUS deprecated
    DESCRIPTION
        "Indicates the administrative status of which
        ports are monitored. All the monitored ports have
        to be non-trunking port and belong to the same
        Virtual LAN. The octet string contains one bit
        per port. Each bit within the octet string
        represents one port of the device. The ordering
        of ports represented within the octet string is
        in the same order as in the RFC 1493
        dot1dStpPortTable.
        
        The bit value interpretation is as follows:
                1 = being monitored
                0 = not being monitored"
    ::= { monitorGrp 7 }

monitorOperSourcePorts OBJECT-TYPE
    SYNTAX OCTET STRING(SIZE(0..128))
    ACCESS read-only
    STATUS deprecated
    DESCRIPTION
        "Indicates which ports are actually being
        monitored. All the monitored ports have to be
        non-trunking port and belong to the same Virtual
        LAN. The octet string contains one bit per port.
        Each bit within the octet string represents one
        port of the device. The ordering of ports
        represented within the octet string is in the same
        order as in the RFC 1493 dot1dStpPortTable.
        
        The bit value interpretation is as follows:
                1 = being monitored
                0 = not being monitored"
    ::= { monitorGrp 8 }

vlanTable OBJECT-TYPE
    SYNTAX SEQUENCE OF VlanEntry
    ACCESS not-accessible
    STATUS deprecated
    DESCRIPTION
        "A list of Virtual LAN entries. The number of
        entries is determined by the number of VLANs
        supported by the system."
    ::= { vlanGrp 2 }

vlanEntry OBJECT-TYPE
    SYNTAX VlanEntry
    ACCESS not-accessible
    STATUS deprecated
    DESCRIPTION
        "Entry containing information for a particular
        Virtual LAN."
    INDEX { vlanIndex }
    ::= { vlanTable 1 }

VlanEntry ::= SEQUENCE {
    vlanIndex VlanIndex,
    vlanSpantreeEnable INTEGER,
    vlanIfIndex INTEGER
    }

vlanIndex OBJECT-TYPE
    SYNTAX VlanIndex
--    Rsyntax INTEGER(0..4095)
    ACCESS read-only
    STATUS deprecated
    DESCRIPTION
        "An index value that uniquely identifies the
        Virtual LAN associated with this information."
    ::= { vlanEntry 1 }

vlanSpantreeEnable OBJECT-TYPE
    SYNTAX INTEGER {
        enabled(1),
        disabled(2),
        notApplicable(3)
        }
    ACCESS read-write
    STATUS deprecated
    DESCRIPTION
        "Indicates whether Spanning Tree protocol is
        enabled for this Virtual LAN.
        
        If the device only supports a single global
        Spanning Tree PVST+ Protocol enable/disable
        for all the existing VLANs, then the object
        value assigned to this VLAN will be applied
        to the object values of all the instances
        in this table which do not have the value
        of notApplicable(3).
        
        This object is deprecated and replaced by
        stpxPVSTVlanEnable in
        CISCO-STP-EXTENSIONS-MIB."
    DEFVAL { enabled }
    ::= { vlanEntry 2 }

vlanIfIndex OBJECT-TYPE
    SYNTAX INTEGER(1..2147483647)
    ACCESS read-only
    STATUS deprecated
    DESCRIPTION
        "The value of the ifIndex object defined in
        MIB-II, for the interface corresponding to this
        VLAN.
        
        This object is deprecated and replaced by
        vtpVlanIfIndex in CISCO-VTP-MIB."
    ::= { vlanEntry 3 }

vlanPortTable OBJECT-TYPE
    SYNTAX SEQUENCE OF VlanPortEntry
    ACCESS not-accessible
    STATUS mandatory
    DESCRIPTION
        "A list of Virtual LAN port entries. The number of
        entries is determined by the number of modules in
        the chassis and the number of ports on each
        module."
    ::= { vlanGrp 3 }

vlanPortEntry OBJECT-TYPE
    SYNTAX VlanPortEntry
    ACCESS not-accessible
    STATUS mandatory
    DESCRIPTION
        "Entry containing Virtual LAN information for a
        particular port on a module."
    INDEX { vlanPortModule, vlanPort }
    ::= { vlanPortTable 1 }

VlanPortEntry ::= SEQUENCE {
    vlanPortModule INTEGER,
    vlanPort INTEGER,
    vlanPortVlan VlanIndex,
    vlanPortIslVlansAllowed OCTET STRING,
    vlanPortSwitchLevel INTEGER,
    vlanPortIslAdminStatus INTEGER,
    vlanPortIslOperStatus INTEGER,
    vlanPortIslPriorityVlans OCTET STRING,
    vlanPortAdminStatus INTEGER,
    vlanPortOperStatus INTEGER,
    vlanPortAuxiliaryVlan INTEGER
    }

vlanPortModule OBJECT-TYPE
    SYNTAX INTEGER(1..16)
    ACCESS read-only
    STATUS mandatory
    DESCRIPTION
        "An index value that uniquely identifies the
        module where this port is located
        (see portModuleIndex)."
    ::= { vlanPortEntry 1 }

vlanPort OBJECT-TYPE
    SYNTAX INTEGER(1..255)
    ACCESS read-only
    STATUS mandatory
    DESCRIPTION
        "An index value that uniquely identifies this port
        within a module (see portIndex)."
    ::= { vlanPortEntry 2 }

vlanPortVlan OBJECT-TYPE
    SYNTAX VlanIndex
--    Rsyntax INTEGER(0..4095)
    ACCESS read-write
    STATUS mandatory
    DESCRIPTION
        "The Virtual LAN to which this port belongs."
    ::= { vlanPortEntry 3 }

vlanPortIslVlansAllowed OBJECT-TYPE
    SYNTAX OCTET STRING(SIZE(0..128))
    ACCESS read-write
    STATUS mandatory
    DESCRIPTION
        "An indication of which Virtual LANs are allowed
        on this Inter-Switch Link. This is an octet string
        value with bits set to indicate allowed VLANs. It
        can be interpreted as a sum of f(x) as x goes from
        0 to 1023, where f(x) = 0 for VLAN x not allowed
        and f(x) = exp(2, x) for VLAN x allowed."
    ::= { vlanPortEntry 5 }

vlanPortSwitchLevel OBJECT-TYPE
    SYNTAX INTEGER {
        normal(1),
        high(2),
        notApplicable(3)
        }
    ACCESS read-write
    STATUS mandatory
    DESCRIPTION
        "Indicates the priority level the port uses to
        access the switching media. If vlanPortSwitchLevel
        is not applicable to the port, notApplicable(3)
        will be returned by the device."
    DEFVAL { normal }
    ::= { vlanPortEntry 6 }

vlanPortIslAdminStatus OBJECT-TYPE
    SYNTAX INTEGER {
        on(1),
        off(2),
        desirable(3),
        auto(4),
        onNoNegotiate(5)
        }
    ACCESS read-write
    STATUS mandatory
    DESCRIPTION
        "Indicates the administrative status set on the
        trunk port while the operational status is the one
        that indicates whether the port is actually
        trunking or not. If the status is set to off(2),
        the port is permanently set to be a non-trunk. If
        the status is set to onNoNegotiate(5), the port is
        permanently set to be a trunk and no negotiation
        takes place with the far end to try to ensure
        consistent operation. If the status is set to
        on(1), the port initiates a request to become a
        trunk and will become a trunk regardless of the
        response from the far end. If the status is set to
        desirable(3), the port initiates a request to
        become a trunk and will become a trunk if the far
        end agrees. If the status is set to auto(4), the
        port does not initiate a request to become a trunk
        but will do so if it receives a request to become
        a trunk from the far end."
    ::= { vlanPortEntry 7 }

vlanPortIslOperStatus OBJECT-TYPE
    SYNTAX INTEGER {
        trunking(1),
        notTrunking(2)
        }
    ACCESS read-only
    STATUS mandatory
    DESCRIPTION
        "Indicates if the port is actually trunking or
        not. In the case of ISL capable ports, the status
        depends on the success or failure of the
        negotiation process initiated by the port to
        become a trunk or non trunk.
        In the case of 802.10 capable ports, it is
        directly related to the on/off administrative
        status."
    ::= { vlanPortEntry 8 }

vlanPortIslPriorityVlans OBJECT-TYPE
    SYNTAX OCTET STRING(SIZE(0..128))
    ACCESS read-write
    STATUS mandatory
    DESCRIPTION
        "An indication of which Virtual LANs have a better
        dot1dStpPortPriority value. This object can be
        used to perform load balancing on Inter-Switch
        Links via spanning tree. An Inter-Switch Link has
        two dot1dStpPortPriority values which are shared
        by all the Virtual LANs on the link. The Virtual
        LANs indicated by this object have priority
        over the other Virtual LANs on the link.
        
        This is an octet string value with bits set to
        indicate priority VLANs. It can be interpreted as
        a sum of f(x) as x goes from 0 to 1023, where
        f(x) = 0 for a VLAN x which does not have priority
        and f(x) = exp(2, x) for a VLAN x which has
        priority.
        
        Setting the dot1dStpPortPriority value for any of
        the Virtual LANs indicated by this object causes
        the dot1dStpPortPriority value for all the Virtual
        LANs indicated by this object to be set to the
        same value.
        
        Setting the dot1dStpPortPriority value for any
        other Virtual LAN causes the dot1dStpPortPriority
        value for all other Virtual LANs to be set to the
        same value."
    ::= { vlanPortEntry 9 }

vlanPortAdminStatus OBJECT-TYPE
    SYNTAX INTEGER {
        static(1),
        dynamic(2)
        }
    ACCESS read-write
    STATUS mandatory
    DESCRIPTION
        "Indicates whether the port will get assigned to a
        VLAN statically or dynamically. When it is set to
        dynamic, the needed information will be accessed
        from one of the Vlan Membership Policy Servers
        specified in the vmpsTable. Default value is
        static(1).
        Note that vlanPortAdminStatus cannot be set to
        dynamic(2) for a port which has
        portSecurityAdminStatus set to enabled(1) or for a
        port which currently has a vlanPortIslOperStatus
        of trunking(1)."
    DEFVAL { static }
    ::= { vlanPortEntry 10 }

vlanPortOperStatus OBJECT-TYPE
    SYNTAX INTEGER {
        inactive(1),
        active(2),
        shutdown(3),
        vlanActiveFault(4)
        }
    ACCESS read-only
    STATUS mandatory
    DESCRIPTION
        "An indication of the current VLAN status of the
        port.
        A status of inactive(1) indicates that a dynamic
        port does not yet have a VLAN assigned or that a
        static or dynamic port has been assigned a VLAN
        that is not currently active. A status of
        active(2) indicates that the currently assigned
        VLAN is active. A status of shutdown(3) indicates
        that the port has been shutdown as a result of a
        VMPS response on a dynamic port.
        A status of vlanActiveFault(4) only applies to
        tokenring ports and indicates that the port is
        operationally disabled because the TR-CRF VLAN of
        which the port is a member has active ports on
        another device and only ports on that remote
        device may participate in that TR-CRF VLAN."
    ::= { vlanPortEntry 11 }

vlanPortAuxiliaryVlan OBJECT-TYPE
    SYNTAX INTEGER(0|1..1000|1025..4094|4095|4096)
    ACCESS read-write
    STATUS deprecated
    DESCRIPTION
        "The Voice Virtual Vlan ID (VVID) to which this
        port belongs to.
        If the VVID is not supported on the port, this MIB
        object will not be configurable and will return
        4096.
        
        Setting this MIB object to 4096, the CDP packets
        transmitting through this port would not include
        Appliance VLAN-ID TLV.
        
        Setting this MIB object to 4095, the CDP packets
        transmitting through this port would contain
        Appliance VLAN-ID TLV with value of 4095 - VoIP
        and related packets are expected to be sent and
        received untagged without an 802.1p priority.
        
        Setting this MIB object to 0, the CDP packets
        transmitting through this port would contain
        Appliance VLAN-ID TLV with value of 0 - VoIP
        and related packets are expected to be sent and
        received with VLAN-id=0 and an 802.1p priority.
        
        Setting this MIB object to N (1..1000|1025..4094),
        the CDP packets transmitting through this port
        would contain Appliance VLAN-ID TLV with N - VoIP
        and related packets are expected to be sent and
        received with VLAN-id=N and an 802.1p priority.
        
        This object is deprecated and replaced by
        vmVoiceVlanId in CISCO-VLAN-MEMBERSHIP-MIB."
    ::= { vlanPortEntry 12 }

vmpsTable OBJECT-TYPE
    SYNTAX SEQUENCE OF VmpsEntry
    ACCESS not-accessible
    STATUS mandatory
    DESCRIPTION
        "This table lists a maximum of 3 IP addresses of
        Vlan Membership Policy Servers."
    ::= { vlanGrp 4 }

vmpsEntry OBJECT-TYPE
    SYNTAX VmpsEntry
    ACCESS not-accessible
    STATUS mandatory
    DESCRIPTION
        "A VMPS table entry."
    INDEX { vmpsAddr }
    ::= { vmpsTable 1 }

VmpsEntry ::= SEQUENCE {
    vmpsAddr IpAddress,
    vmpsType INTEGER
    }

vmpsAddr OBJECT-TYPE
    SYNTAX IpAddress
    ACCESS read-only
    STATUS mandatory
    DESCRIPTION
        "The IP address of a Vlan Membership Policy
        Server. To configure the internal VMPS, use the
        same IP address as specified in sysIpAddr."
    ::= { vmpsEntry 1 }

vmpsType OBJECT-TYPE
    SYNTAX INTEGER {
        invalid(1),
        primary(2),
        other(3)
        }
    ACCESS read-write
    STATUS mandatory
    DESCRIPTION
        "To add a new entry to the vmpsTable, set this
        object to primary(2) or other(3) for an IP address
        which is not already in the table. The primary
        entry will be used first, if it is reachable.
        Otherwise one of the other entries will be used.
        Setting one entry to primary(2) causes any
        previous primary entry to change to other(3).
        To remove an entry from the table, set this
        object to invalid(1)."
    ::= { vmpsEntry 2 }

vmpsAction OBJECT-TYPE
    SYNTAX INTEGER {
        other(1),
        inProgress(2),
        success(3),
        noResponse(4),
        noPrimaryVmps(5),
        noDynamicPort(6),
        noHostConnected(7),
        reconfirm(8)
        }
    ACCESS read-write
    STATUS mandatory
    DESCRIPTION
        "This object, when read, returns the result of the
        last action requested: other(1), inProgress(2),
        success(3), noResponse(3), noPrimaryVmps(5),
        noDynamicPort(6), or noHostConnected(7).
        
        Setting this object to reconfirm(8) causes the
        switch to contact the Vlan Membership Policy
        Server immediately to reconfirm the current VLAN
        assignments for all dynamic ports on the switch.
        Normally VLAN assignments for dynamic ports are
        reconfirmed once an hour."
    ::= { vlanGrp 5 }

vmpsAccessed OBJECT-TYPE
    SYNTAX IpAddress
    ACCESS read-only
    STATUS mandatory
    DESCRIPTION
        "The IP address of the last Vlan Membership Policy
        Server accessed. If there was no response from the
        last VMPS request, the value returned is 0."
    ::= { vlanGrp 6 }

vlanTrunkMappingMax OBJECT-TYPE
    SYNTAX Gauge(0..65535)
--  Units
--    entries
    ACCESS read-only
    STATUS mandatory
    DESCRIPTION
        "Maximum number of active configurable trunk VLAN
        mapping entries allowed. A value of zero indicates
        no limitation on the number of active configurable
        trunk VLAN mapping."
    ::= { vlanGrp 7 }

vlanTrunkMappingTable OBJECT-TYPE
    SYNTAX SEQUENCE OF VlanTrunkMappingEntry
    ACCESS not-accessible
    STATUS mandatory
    DESCRIPTION
        "This table contains zero or more rows of trunk
        VLAN to VLAN associations. The maximum number of
        active entries is determined by
        vlanTrunkMappingMax.
        
        VLAN above 1k can not be created if the value of
        corresponding instance of vlanTrunkMappingType is
        dot1qToisl(2)."
    ::= { vlanGrp 8 }

vlanTrunkMappingEntry OBJECT-TYPE
    SYNTAX VlanTrunkMappingEntry
    ACCESS not-accessible
    STATUS mandatory
    DESCRIPTION
        "Information about the VLAN mapping of a
        particular trunk VLAN to another VLAN."
    INDEX { vlanTrunkMappingFromVlan }
    ::= { vlanTrunkMappingTable 1 }

VlanTrunkMappingEntry ::= SEQUENCE {
    vlanTrunkMappingFromVlan VlanIndex,
    vlanTrunkMappingToVlan VlanIndex,
    vlanTrunkMappingType INTEGER,
    vlanTrunkMappingOper TruthValue,
    vlanTrunkMappingStatus RowStatus
    }

vlanTrunkMappingFromVlan OBJECT-TYPE
    SYNTAX VlanIndex
--    Rsyntax INTEGER(0..4095)
    ACCESS not-accessible
    STATUS mandatory
    DESCRIPTION
        "The VLAN with this VLAN ID will be mapped to the
        VLAN in the corresponding instance of
        vlanTrunkMappingToVlan in the device.
        
        Agent returns inconsistentValue if this VLAN
        exists in the device.
        
        Agent returns inconsistentValue if this VLAN is
        not a reserved VLAN and the value of corresponding
        instance of vlanTrunkMappingType is
        reservedToNonReserved(1).
        
        Agent returns wrongValue if this VLAN is not a
        valid 802.1Q VLAN and the value of corresponding
        instance of vlanTrunkMappingType is
        dot1qToisl(2)."
    ::= { vlanTrunkMappingEntry 1 }

vlanTrunkMappingToVlan OBJECT-TYPE
    SYNTAX VlanIndex
--    Rsyntax INTEGER(0..4095)
    ACCESS read-write
    STATUS mandatory
    DESCRIPTION
        "The VLAN which the corresponding instance of
        vlanTrunkMappingFromVlan will be mapped to.
        
        Agent returns inconsistentValue if this VLAN
        exists in the device.
        
        Agent returns inconsistentValue if this VLAN is a
        reserved VLAN and the value of corresponding
        instance of vlanTrunkMappingType is
        reservedToNonReserved(1).
        
        Agent returns inconsistentValue if this VLAN is
        not a valid ISL VLAN and the value of
        corresponding instance of vlanTrunkMappingType
        is dot1qToisl(2)."
    ::= { vlanTrunkMappingEntry 2 }

vlanTrunkMappingType OBJECT-TYPE
    SYNTAX INTEGER {
        reservedToNonReserved(1),
        dot1qToisl(2)
        }
    ACCESS read-write
    STATUS mandatory
    DESCRIPTION
        "The type of this trunk VLAN mapping.
        
        reservedToNonReserved(1)
            An user defined association which maps a
            reserved VLAN to a non-reserved VLAN.
        
        dot1qToisl(2)
            An user defined association which maps a VLAN
            in 802.1q trunk to a VLAN in ISL trunk.
        
        Implementations are allowed to restrict the
        available types for this object.
        
        For devices which support the range of VlanIndex
        between 1024 and 4095, the default value is
        reservedToNonReserved(1).  The default value is
        dot1qToisl(2) for devices which do not support the
        range of VlanIndex between 1024 and 4095."
    ::= { vlanTrunkMappingEntry 3 }

vlanTrunkMappingOper OBJECT-TYPE
    SYNTAX TruthValue
--    Rsyntax INTEGER {
--        true(1),
--        false(2)
--        }
    ACCESS read-only
    STATUS mandatory
    DESCRIPTION
        "Indicates whether this VLAN mapping is effective
        or not."
    ::= { vlanTrunkMappingEntry 4 }

vlanTrunkMappingStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of this trunk VLAN mapping.
        
        Once a row becomes active, value in any other
        column within such row cannot be modified except
        by setting vlanTrunkMappingStatus to
        notInService(2) for such row."
    ::= { vlanTrunkMappingEntry 5 }

portSecurityTable OBJECT-TYPE
    SYNTAX SEQUENCE OF PortSecurityEntry
    ACCESS not-accessible
    STATUS mandatory
    DESCRIPTION
        "A list of port security entries. The number of
        entries is determined by the number of ports in
        the system which support the Security feature."
    ::= { securityGrp 1 }

portSecurityEntry OBJECT-TYPE
    SYNTAX PortSecurityEntry
    ACCESS not-accessible
    STATUS mandatory
    DESCRIPTION
        "Entry containing security information for a
        particular port."
    INDEX { portSecurityModuleIndex, portSecurityPortIndex }
    ::= { portSecurityTable 1 }

PortSecurityEntry ::= SEQUENCE {
    portSecurityModuleIndex INTEGER,
    portSecurityPortIndex INTEGER,
    portSecurityAdminStatus INTEGER,
    portSecurityOperStatus INTEGER,
    portSecurityLastSrcAddr OCTET STRING,
    portSecuritySecureSrcAddr OCTET STRING,
    portSecurityMaxSrcAddr INTEGER,
    portSecurityAgingTime INTEGER,
    portSecurityShutdownTimeOut INTEGER,
    portSecurityViolationPolicy INTEGER
    }

portSecurityModuleIndex OBJECT-TYPE
    SYNTAX INTEGER(1..16)
    ACCESS read-only
    STATUS mandatory
    DESCRIPTION
        "An index value that uniquely identifies the
        module where this port is located
        (see portModuleIndex)."
    ::= { portSecurityEntry 1 }

portSecurityPortIndex OBJECT-TYPE
    SYNTAX INTEGER(1..255)
    ACCESS read-only
    STATUS mandatory
    DESCRIPTION
        "An index value that uniquely identifies this port
        within a module (see portIndex)."
    ::= { portSecurityEntry 2 }

portSecurityAdminStatus OBJECT-TYPE
    SYNTAX INTEGER {
        enabled(1),
        disabled(2)
        }
    ACCESS read-write
    STATUS mandatory
    DESCRIPTION
        "When security is enabled, source MAC addresses
        are monitored for all packets received on the
        port. If an address is detected that does not
        match the portSecuritySecureSrcAddr and any
        corresponding portSecurityExtSecureSrcAddr, of
        which portSecurityExtModuleIndex and
        portSecurityExtPortIndex in the
        portSecurityExtTable is the same as the
        portSecurityModuleIndex and portSecurityPortIndex,
        and the number of MAC address learned or
        configured for this port is equal to
        portSecurityMaxSrcAddr, the port will shutdown or
        drop packets. If the
        portSecurityViolationPolicy is set to shutdown(2),
        the port is shutdown and a linkDown trap is sent;
        otherwise the port drops the invalid packets."
    DEFVAL { disabled }
    ::= { portSecurityEntry 3 }

portSecurityOperStatus OBJECT-TYPE
    SYNTAX INTEGER {
        notShutdown(1),
        shutdown(2)
        }
    ACCESS read-only
    STATUS mandatory
    DESCRIPTION
        "An indication of whether the port has been shut
        down as a result of an insecure address being
        detected on a secure port."
    ::= { portSecurityEntry 4 }

portSecurityLastSrcAddr OBJECT-TYPE
    SYNTAX OCTET STRING(SIZE(6))
    ACCESS read-only
    STATUS mandatory
    DESCRIPTION
        "The last source MAC address in a receive packet
        seen on the port."
    ::= { portSecurityEntry 5 }

portSecuritySecureSrcAddr OBJECT-TYPE
    SYNTAX OCTET STRING(SIZE(6))
    ACCESS read-write
    STATUS mandatory
    DESCRIPTION
        "The address to be compared with source MAC
        addresses of received packets when the
        portSecurityAdminStatus is enabled(1). Setting
        this value to 0.0.0.0.0.0 puts the port in
        learning mode so that the next source MAC
        address received by the port becomes the
        portSecuritySecureSrcAddr."
    ::= { portSecurityEntry 6 }

portSecurityMaxSrcAddr OBJECT-TYPE
    SYNTAX INTEGER(1..1025)
    ACCESS read-write
    STATUS mandatory
    DESCRIPTION
        "The maximum number (N) of MAC address to be
        secured on the port. The first N MAC addresses
        learned or configured are made secured. If the
        user wants to make the port secured for more than
        one MAC address, the portSecurityExtTable is used
        in addition to portSecuritySecureSrcAddr. If
        changing the maximum number N of Mac address to M,
        which is smaller than N, some MAC addresses are
        removed. Setting this value to 1,
        the portSecurityExtTable will not be used for this
        port and the corresponding entries for this port
        will also be removed from portSecurityExtTable."
    DEFVAL { 1 }
    ::= { portSecurityEntry 7 }

portSecurityAgingTime OBJECT-TYPE
    SYNTAX INTEGER(0|10..1440)
--  Units
--    minutes
    ACCESS read-write
    STATUS mandatory
    DESCRIPTION
        "The interval in which the port is secured. After
        the expiration of the time, the corresponding
        portSecuritySecureSrcAddr or
        portSecurityExtSecureSrcAddr will be removed from
        the secure address list. If the value of this
        object is 0, the aging mechanism is disabled."
    DEFVAL { 0 }
    ::= { portSecurityEntry 8 }

portSecurityShutdownTimeOut OBJECT-TYPE
    SYNTAX INTEGER(0|10..1440)
--  Units
--    minutes
    ACCESS read-write
    STATUS mandatory
    DESCRIPTION
        "The interval in which the port is shutdown due to
        the violation of security. After the expiration
        of the time all the security configuration of this
        port is re-installed and the port is enabled. If
        the value of this object is 0, the port is shut
        down permanently."
    DEFVAL { 0 }
    ::= { portSecurityEntry 9 }

portSecurityViolationPolicy OBJECT-TYPE
    SYNTAX INTEGER {
        restrict(1),
        shutdown(2)
        }
    ACCESS read-write
    STATUS mandatory
    DESCRIPTION
        "If the value of this object is
          restrict(1)  - the port drops all packets with
                         insecured addresses.
          shutdown(2)  - the port is forced to shut down
                         if there is a violation of
                         security."
    DEFVAL { shutdown }
    ::= { portSecurityEntry 10 }

portSecurityExtTable OBJECT-TYPE
    SYNTAX SEQUENCE OF PortSecurityExtEntry
    ACCESS not-accessible
    STATUS mandatory
    DESCRIPTION
        "A list of port security entries. The number of
        entries is determined by the number of ports in
        the system which support the Security feature and
        the number of MAC addresses learned/configured to
        be secured per port."
    ::= { securityGrp 2 }

portSecurityExtEntry OBJECT-TYPE
    SYNTAX PortSecurityExtEntry
    ACCESS not-accessible
    STATUS mandatory
    DESCRIPTION
        "Entry containing security information for a
        particular port and a particular MAC address. The
        entry can be configured by the user and can be
        added by the agent when the device learns a new
        secured MAC address."
    INDEX { portSecurityExtModuleIndex, portSecurityExtPortIndex, portSecurityExtSecureSrcAddr }
    ::= { portSecurityExtTable 1 }

PortSecurityExtEntry ::= SEQUENCE {
    portSecurityExtModuleIndex INTEGER,
    portSecurityExtPortIndex INTEGER,
    portSecurityExtSecureSrcAddr OCTET STRING,
    portSecurityExtControlStatus INTEGER
    }

portSecurityExtModuleIndex OBJECT-TYPE
    SYNTAX INTEGER(1..16)
    ACCESS read-only
    STATUS mandatory
    DESCRIPTION
        "An index value that uniquely identifies the
        module where this port is located
        (see portModuleIndex)."
    ::= { portSecurityExtEntry 1 }

portSecurityExtPortIndex OBJECT-TYPE
    SYNTAX INTEGER(1..255)
    ACCESS read-only
    STATUS mandatory
    DESCRIPTION
        "An index value that uniquely identifies this port
        within a module (see portIndex)."
    ::= { portSecurityExtEntry 2 }

portSecurityExtSecureSrcAddr OBJECT-TYPE
    SYNTAX OCTET STRING(SIZE(6))
    ACCESS read-only
    STATUS mandatory
    DESCRIPTION
        "An index value that uniquely identifies the  MAC
        address, which is to be secured."
    ::= { portSecurityExtEntry 3 }

portSecurityExtControlStatus OBJECT-TYPE
    SYNTAX INTEGER {
        valid(1),
        invalid(2)
        }
    ACCESS read-write
    STATUS mandatory
    DESCRIPTION
        "This object used to add or remove a secured
        MAC address of the corresponding port in
        the row. If setting this object to valid(1), the
        portSecurityExtSecureSrcAddr is made to be secured
        for the port. If setting this object to
        invalid(2), the portSecurityExtSecureSrcAddr is
        no longer to be secured for the current port."
    ::= { portSecurityExtEntry 4 }

tokenRingPortTable OBJECT-TYPE
    SYNTAX SEQUENCE OF TokenRingPortEntry
    ACCESS not-accessible
    STATUS mandatory
    DESCRIPTION
        "Table containing token ring configuration
        information."
    ::= { tokenRingGrp 1 }

tokenRingPortEntry OBJECT-TYPE
    SYNTAX TokenRingPortEntry
    ACCESS not-accessible
    STATUS mandatory
    DESCRIPTION
        "Entry containing token ring configuration
        information for a particular port."
    INDEX { tokenRingModuleIndex, tokenRingPortIndex }
    ::= { tokenRingPortTable 1 }

TokenRingPortEntry ::= SEQUENCE {
    tokenRingModuleIndex INTEGER,
    tokenRingPortIndex INTEGER,
    tokenRingPortSetACbits INTEGER,
    tokenRingPortMode INTEGER,
    tokenRingPortEarlyTokenRel INTEGER,
    tokenRingPortPriorityThresh INTEGER,
    tokenRingPortPriorityMinXmit INTEGER,
    tokenRingPortCfgLossThresh INTEGER,
    tokenRingPortCfgLossInterval INTEGER
    }

tokenRingModuleIndex OBJECT-TYPE
    SYNTAX INTEGER(1..16)
    ACCESS read-only
    STATUS mandatory
    DESCRIPTION
        "An index value that uniquely identifies the
        module where this port is located
        (see portModuleIndex)."
    ::= { tokenRingPortEntry 1 }

tokenRingPortIndex OBJECT-TYPE
    SYNTAX INTEGER(1..255)
    ACCESS read-only
    STATUS mandatory
    DESCRIPTION
        "An index value that uniquely identifies this port
        within a module (see portIndex)."
    ::= { tokenRingPortEntry 2 }

tokenRingPortSetACbits OBJECT-TYPE
    SYNTAX INTEGER {
        enabled(1),
        disabled(2)
        }
    ACCESS read-write
    STATUS mandatory
    DESCRIPTION
        "Specifies if the AC bits shall be set
        unconditionally when a port forwards certain LLC
        frames."
    DEFVAL { disabled }
    ::= { tokenRingPortEntry 3 }

tokenRingPortMode OBJECT-TYPE
    SYNTAX INTEGER {
        auto(1),
        fdxCport(2),
        fdxStation(3),
        hdxCport(4),
        hdxStation(5),
        riro(7)
        }
    ACCESS read-write
    STATUS mandatory
    DESCRIPTION
        "Specifies the port's mode of operation.
        
        auto:       Automatically detect the port mode
                    upon insertion.
        
        fdxCport:   Transmit Immediate (full-duplex)
                    Concentrator Port
        
        fdxStation: Transmit Immediate (full-duplex)
                    Station emulation
        
        hdxCport:   Token Passing Protocol (half-duplex)
                    Concentrator Port
        
        hdxStation: Token Passing Protocol (half-duplex)
                    Station emulation
        
        riro:       RingIn/RingOut mode. (wsx5031 only)"
    DEFVAL { auto }
    ::= { tokenRingPortEntry 4 }

tokenRingPortEarlyTokenRel OBJECT-TYPE
    SYNTAX INTEGER {
        enabled(1),
        disabled(2)
        }
    ACCESS read-write
    STATUS mandatory
    DESCRIPTION
        "This object provides the ability to enable or
        disable early token release for a particular port.
        
        Early token release only applies to ports
        operating at 16 Mbps. If ifSpeed reflects 4 Mbps
        for a particular port, then the corresponding
        instance of this object will have a value of
        disabled(2) regardless of attempts to set the
        object to enabled(1).
        
        Whenever a port is opened with a ring speed of
        16 Mbps, by default, early token release will be
        enabled."
    ::= { tokenRingPortEntry 9 }

tokenRingPortPriorityThresh OBJECT-TYPE
    SYNTAX INTEGER(0..7)
    ACCESS read-write
    STATUS mandatory
    DESCRIPTION
        "The highest token ring frame priority that shall
        go to the low-priority transmit queue."
    DEFVAL { 3 }
    ::= { tokenRingPortEntry 10 }

tokenRingPortPriorityMinXmit OBJECT-TYPE
    SYNTAX INTEGER(0..6)
    ACCESS read-write
    STATUS mandatory
    DESCRIPTION
        "The minimum token priority that will be used for
        transmit."
    DEFVAL { 4 }
    ::= { tokenRingPortEntry 11 }

tokenRingPortCfgLossThresh OBJECT-TYPE
    SYNTAX INTEGER(1..100)
    ACCESS read-write
    STATUS mandatory
    DESCRIPTION
        "Number of configuration loss events during the
        sample interval which, if exceeded, should cause
        the port to be disabled. If the port is disabled
        by this function the port must be administratively
        re-enabled."
    DEFVAL { 8 }
    ::= { tokenRingPortEntry 12 }

tokenRingPortCfgLossInterval OBJECT-TYPE
    SYNTAX INTEGER(1..9999)
    ACCESS read-write
    STATUS mandatory
    DESCRIPTION
        "The sampling interval, in minutes, for which the
        port monitors to see if the configuration loss
        threshold has been exceeded."
    DEFVAL { 10 }
    ::= { tokenRingPortEntry 13 }

tokenRingDripDistCrfMode OBJECT-TYPE
    SYNTAX INTEGER {
        enabled(1),
        disabled(2)
        }
    ACCESS read-write
    STATUS mandatory
    DESCRIPTION
        "This object reflects whether TR-CRFs can be
        distributed across ISL topologies. Setting
        this object to enabled(1) allows TR-CRFs to be
        distributed. Setting this object to disabled(2)
        prevents TR-CRFs from being distributed across
        ISL topologies. When this object is set to
        disabled(2), the system will disable ports
        involved in the distributed TR-CRF."
    DEFVAL { disabled }
    ::= { tokenRingGrp 2 }

tokenRingDripAreReductionMode OBJECT-TYPE
    SYNTAX INTEGER {
        enabled(1),
        disabled(2)
        }
    ACCESS read-write
    STATUS mandatory
    DESCRIPTION
        "This object reflects whether or not All
        Routes Explorer (ARE) reduction capabilities are
        enabled or disabled on this system. Setting
        this object to enabled(1) will permit DRiP to
        participate in the configuration of Token Ring
        ports ARE reduction capabilities on the system.
        Setting this object to disabled(2) will prevent
        DRiP from participating in the configuration
        of Token Ring port ARE reduction capabilities."
    DEFVAL { enabled }
    ::= { tokenRingGrp 3 }

tokenRingDripLocalNodeID OBJECT-TYPE
    SYNTAX OCTET STRING(SIZE(6))
    ACCESS read-only
    STATUS mandatory
    DESCRIPTION
        "The unique system identifier that will be sent
        in all advertisements generated by this system.
        It uniquely identifies this system from other
        DRiP capable systems."
    ::= { tokenRingGrp 4 }

tokenRingDripLastRevision OBJECT-TYPE
    SYNTAX INTEGER(0..9999999)
    ACCESS read-only
    STATUS mandatory
    DESCRIPTION
        "The revision number transmitted in the most
        recent advertisement. That advertisement may
        or may not have contained changed data."
    ::= { tokenRingGrp 5 }

tokenRingDripLastChangedRevision OBJECT-TYPE
    SYNTAX INTEGER(0..9999999)
    ACCESS read-only
    STATUS mandatory
    DESCRIPTION
        "The revision number transmitted in the most
        recent advertisement containing changed data."
    ::= { tokenRingGrp 6 }

tokenRingDripAdvertsReceived OBJECT-TYPE
    SYNTAX Counter
    ACCESS read-only
    STATUS mandatory
    DESCRIPTION
        "The number of DRiP advertisements received
        by this system."
    ::= { tokenRingGrp 7 }

tokenRingDripAdvertsTransmitted OBJECT-TYPE
    SYNTAX Counter
    ACCESS read-only
    STATUS mandatory
    DESCRIPTION
        "The number of DRiP advertisements transmitted
        by this system."
    ::= { tokenRingGrp 8 }

tokenRingDripAdvertsProcessed OBJECT-TYPE
    SYNTAX Counter
    ACCESS read-only
    STATUS mandatory
    DESCRIPTION
        "The number of DRiP advertisements processed
        by this system."
    ::= { tokenRingGrp 9 }

tokenRingDripInputQueueDrops OBJECT-TYPE
    SYNTAX Counter
    ACCESS read-only
    STATUS mandatory
    DESCRIPTION
        "The number of DRiP advertisements dropped
        from this system's input queue."
    ::= { tokenRingGrp 10 }

tokenRingDripOutputQueueDrops OBJECT-TYPE
    SYNTAX Counter
    ACCESS read-only
    STATUS mandatory
    DESCRIPTION
        "The number of DRiP advertisements dropped
        from this system's output queue."
    ::= { tokenRingGrp 11 }

tokenRingDripLocalVlanStatusTable OBJECT-TYPE
    SYNTAX SEQUENCE OF TokenRingDripLocalVlanStatusEntry
    ACCESS not-accessible
    STATUS mandatory
    DESCRIPTION
        "A table containing DRiP VLAN status information
        local to this system. The existence of an
        entry indicates that at least one local port
        is assigned to the associated TR-CRF VLAN."
    ::= { tokenRingGrp 12 }

tokenRingDripLocalVlanStatusEntry OBJECT-TYPE
    SYNTAX TokenRingDripLocalVlanStatusEntry
    ACCESS not-accessible
    STATUS mandatory
    DESCRIPTION
        "Entry containing DRiP related information for
        a particular TR-CRF VLAN."
    INDEX { tokenRingDripVlan }
    ::= { tokenRingDripLocalVlanStatusTable 1 }

TokenRingDripLocalVlanStatusEntry ::= SEQUENCE {
    tokenRingDripVlan VlanIndex,
    tokenRingDripLocalPortStatus INTEGER,
    tokenRingDripRemotePortStatus INTEGER,
    tokenRingDripRemotePortConfigured INTEGER,
    tokenRingDripDistributedCrf INTEGER,
    tokenRingDripBackupCrf INTEGER,
    tokenRingDripOwnerNodeID OCTET STRING
    }

tokenRingDripVlan OBJECT-TYPE
    SYNTAX VlanIndex
--    Rsyntax INTEGER(0..4095)
    ACCESS read-only
    STATUS mandatory
    DESCRIPTION
        "A TR-CRF VLAN ID."
    ::= { tokenRingDripLocalVlanStatusEntry 1 }

tokenRingDripLocalPortStatus OBJECT-TYPE
    SYNTAX INTEGER {
        active(1),
        inactive(2)
        }
    ACCESS read-only
    STATUS mandatory
    DESCRIPTION
        "This object reflects DRiP's status regarding
        the overall set of local ports assigned to
        the TR-CRF VLAN associated with this entry.
        A value of active(1) indicates that at least
        one local port is inserted/connected (i.e.,
        active on the Token Ring). A value of inactive(2)
        indicates that none of the local ports are
        inserted/connected. All local ports are either
        disabled or are simply not connected."
    ::= { tokenRingDripLocalVlanStatusEntry 2 }

tokenRingDripRemotePortStatus OBJECT-TYPE
    SYNTAX INTEGER {
        active(1),
        inactive(2)
        }
    ACCESS read-only
    STATUS mandatory
    DESCRIPTION
        "This object reflects DRiP's status regarding
        any ports on remote systems. A value of
        active(1) indicates that at least one remote
        port is inserted/connected (i.e., active on
        the Token Ring). A value of inactive(2) indicates
        that none of the remote ports are
        inserted/connected. All remote ports are either
        disabled or are simply not connected."
    ::= { tokenRingDripLocalVlanStatusEntry 3 }

tokenRingDripRemotePortConfigured OBJECT-TYPE
    SYNTAX INTEGER {
        true(1),
        false(2)
        }
    ACCESS read-only
    STATUS mandatory
    DESCRIPTION
        "This object reflects whether or not DRiP has
        detected remote ports assigned to the TR-CRF
        VLAN associated with this entry. A value of
        true(1) indicates there is at least one port
        on a remote system assigned to this TR-CRF VLAN.
        A value of false(2) indicates no remote ports
        are assigned to this TR-CRF VLAN."
    ::= { tokenRingDripLocalVlanStatusEntry 4 }

tokenRingDripDistributedCrf OBJECT-TYPE
    SYNTAX INTEGER {
        true(1),
        false(2)
        }
    ACCESS read-only
    STATUS mandatory
    DESCRIPTION
        "This object reflects whether DRiP considers the
        TR-CRF VLAN associated with this entry to be
        distributed across systems. A value of true(1)
        indicates the TR-CRF is distributed. A value
        of false(2) indicates the TR-CRF is not
        distributed."
    ::= { tokenRingDripLocalVlanStatusEntry 5 }

tokenRingDripBackupCrf OBJECT-TYPE
    SYNTAX INTEGER {
        true(1),
        false(2)
        }
    ACCESS read-only
    STATUS mandatory
    DESCRIPTION
        "This object reflects whether or not the TR-CRF
        VLAN associated with this entry is configured
        as a backup TR-CRF. A value of true(1) indicates
        the TR-CRF is a configured as a backup. A value
        of false(2) indicates the TR-CRF is not configured
        as a backup."
    ::= { tokenRingDripLocalVlanStatusEntry 6 }

tokenRingDripOwnerNodeID OBJECT-TYPE
    SYNTAX OCTET STRING(SIZE(6))
    ACCESS read-only
    STATUS mandatory
    DESCRIPTION
        "The unique identifier  of the system that has
        advertised that it has local ports assigned to the
        TR-CRF VLAN associated with this entry."
    ::= { tokenRingDripLocalVlanStatusEntry 7 }

tokenRingPortSoftErrTable OBJECT-TYPE
    SYNTAX SEQUENCE OF TokenRingPortSoftErrEntry
    ACCESS not-accessible
    STATUS mandatory
    DESCRIPTION
        "Table containing token ring soft error monitoring
         configuration information."
    ::= { tokenRingGrp 14 }

tokenRingPortSoftErrEntry OBJECT-TYPE
    SYNTAX TokenRingPortSoftErrEntry
    ACCESS not-accessible
    STATUS mandatory
    DESCRIPTION
        "Entry containing token ring soft error monitoring
         configuration information for a particular port."
    INDEX { tokenRingModuleIndex, tokenRingPortIndex }
-- Augments tokenRingPortEntry
    ::= { tokenRingPortSoftErrTable 1 }

TokenRingPortSoftErrEntry ::= SEQUENCE {
    tokenRingPortSoftErrThresh INTEGER,
    tokenRingPortSoftErrReportInterval INTEGER,
    tokenRingPortSoftErrResetCounters INTEGER,
    tokenRingPortSoftErrLastCounterReset TimeTicks,
    tokenRingPortSoftErrEnable INTEGER
    }

tokenRingPortSoftErrThresh OBJECT-TYPE
    SYNTAX INTEGER(1..255)
    ACCESS read-write
    STATUS mandatory
    DESCRIPTION
        "The number of soft errors reported from a station
         connected to this port which, if exceeded, should
        cause a soft error exceeded trap to be issued.
        The error counters being monitored and compared to
        this threshold value are all of the error counters
        in the ringStationTable (see RFC 1513)."
    DEFVAL { 100 }
    ::= { tokenRingPortSoftErrEntry 1 }

tokenRingPortSoftErrReportInterval OBJECT-TYPE
    SYNTAX INTEGER(0..65535)
    ACCESS read-write
    STATUS mandatory
    DESCRIPTION
        "The sampling period, in seconds, in which each
         station connected to this port will be monitored
         for excessive soft error reports. If a station
         reports more than tokenRingPortSoftErrThreshold
         errors within the sampling period a trap will be
         issued to the management station(s). Setting a
         value of 0 will cause no traps to be sent for
         this port."
    DEFVAL { 60 }
    ::= { tokenRingPortSoftErrEntry 2 }

tokenRingPortSoftErrResetCounters OBJECT-TYPE
    SYNTAX INTEGER {
        noop(1),
        reset(2)
        }
    ACCESS read-write
    STATUS mandatory
    DESCRIPTION
        "When this object is set to reset(2), all Soft
         Error Monitoring related counters on this port
         will be set to 0."
    ::= { tokenRingPortSoftErrEntry 3 }

tokenRingPortSoftErrLastCounterReset OBJECT-TYPE
    SYNTAX TimeTicks
    ACCESS read-only
    STATUS mandatory
    DESCRIPTION
        "The time (in hundredths of a second) since Soft
         Error Monitoring counters for this port were last
         cleared."
    ::= { tokenRingPortSoftErrEntry 4 }

tokenRingPortSoftErrEnable OBJECT-TYPE
    SYNTAX INTEGER {
        enabled(1),
        disabled(2)
        }
    ACCESS read-write
    STATUS mandatory
    DESCRIPTION
        "Indicates whether the Token Ring Soft Error
         Monitoring feature is enabled on this port or not.
         The detailed soft error statistics are provided
         by Token Ring RMON SNMP objects. Thus, if RMON
         (sysEnableRmon) is disabled(2) then the soft error
         statistics will only be available from the CLI."
    DEFVAL { disabled }
    ::= { tokenRingPortSoftErrEntry 5 }

mcastRouterTable OBJECT-TYPE
    SYNTAX SEQUENCE OF McastRouterEntry
    ACCESS not-accessible
    STATUS mandatory
    DESCRIPTION
        "A list of multicast router port entries. The
        number of entries is determined by the number of
        ports in the system."
    ::= { multicastGrp 1 }

mcastRouterEntry OBJECT-TYPE
    SYNTAX McastRouterEntry
    ACCESS not-accessible
    STATUS mandatory
    DESCRIPTION
        "Entry containing multicast router information for
        a particular port."
    INDEX { mcastRouterModuleIndex, mcastRouterPortIndex }
    ::= { mcastRouterTable 1 }

McastRouterEntry ::= SEQUENCE {
    mcastRouterModuleIndex INTEGER,
    mcastRouterPortIndex INTEGER,
    mcastRouterAdminStatus INTEGER,
    mcastRouterOperStatus INTEGER
    }

mcastRouterModuleIndex OBJECT-TYPE
    SYNTAX INTEGER(1..16)
    ACCESS read-only
    STATUS mandatory
    DESCRIPTION
        "An index value that uniquely identifies the
        module where this port is located
        (see portModuleIndex)."
    ::= { mcastRouterEntry 1 }

mcastRouterPortIndex OBJECT-TYPE
    SYNTAX INTEGER(1..255)
    ACCESS read-only
    STATUS mandatory
    DESCRIPTION
        "An index value that uniquely identifies this port
        within a module (see portIndex)."
    ::= { mcastRouterEntry 2 }

mcastRouterAdminStatus OBJECT-TYPE
    SYNTAX INTEGER {
        routerPresent(1),
        dynamic(3)
        }
    ACCESS read-write
    STATUS mandatory
    DESCRIPTION
        "And indication of whether the presence of an IP
        multicast router on this port is to be determined
        statically or dynamically. The value
        routerPresent(1) indicates that the presence of a
        router is statically configured to be present.
        The value dynamic(3) indicates the presence is to
        be learned dynamically."
    DEFVAL { dynamic }
    ::= { mcastRouterEntry 3 }

mcastRouterOperStatus OBJECT-TYPE
    SYNTAX INTEGER {
        routerPresent(1),
        noRouter(2)
        }
    ACCESS read-only
    STATUS mandatory
    DESCRIPTION
        "An indication of whether an IP multicast router
        is present on this port."
    ::= { mcastRouterEntry 4 }

mcastEnableCgmp OBJECT-TYPE
    SYNTAX INTEGER {
        enabled(1),
        disabled(2)
        }
    ACCESS read-write
    STATUS mandatory
    DESCRIPTION
        "Indicates whether Cisco Group Management Protocol
        is enabled on the device or not. When CGMP is
        enabled in conjunction with Cisco routers running
        CGMP, only the required ports will participate in
        IP multicast groups."
    DEFVAL { disabled }
    ::= { multicastGrp 2 }

mcastEnableIgmp OBJECT-TYPE
    SYNTAX INTEGER {
        enabled(1),
        disabled(2)
        }
    ACCESS read-write
    STATUS mandatory
    DESCRIPTION
        "Indicates whether Internet Group Management
        Protocol is enabled on the device or not. When
        IGMP is enabled in conjunction with Cisco routers
        running CGMP, only the required ports will
        participate in IP multicast groups."
    DEFVAL { disabled }
    ::= { multicastGrp 3 }

mcastEnableRgmp OBJECT-TYPE
    SYNTAX INTEGER {
        enabled(1),
        disabled(2)
        }
    ACCESS read-write
    STATUS mandatory
    DESCRIPTION
        "Indicates whether Router Group Management
        Protocol is enabled on the device or not. When
        RGMP is enabled in conjunction with Cisco routers
        running RGMP, multicast data traffic is forwarded
        only to those multicast routers that are
        interested to receive that data traffic. IGMP
        snooping feature must be enabled on the system
        to make RGMP feature operational."
    DEFVAL { disabled }
    ::= { multicastGrp 4 }

dnsEnable OBJECT-TYPE
    SYNTAX INTEGER {
        enabled(1),
        disabled(2)
        }
    ACCESS read-write
    STATUS mandatory
    DESCRIPTION
        "Indicates if the DNS feature is enabled or
        disabled."
    DEFVAL { disabled }
    ::= { dnsGrp 1 }

dnsServerTable OBJECT-TYPE
    SYNTAX SEQUENCE OF DnsServerEntry
    ACCESS not-accessible
    STATUS mandatory
    DESCRIPTION
        "This table lists a maximum of 3 DNS servers."
    ::= { dnsGrp 2 }

dnsServerEntry OBJECT-TYPE
    SYNTAX DnsServerEntry
    ACCESS not-accessible
    STATUS mandatory
    DESCRIPTION
        "A DNS server table entry."
    INDEX { dnsServerAddr }
    ::= { dnsServerTable 1 }

DnsServerEntry ::= SEQUENCE {
    dnsServerAddr IpAddress,
    dnsServerType INTEGER
    }

dnsServerAddr OBJECT-TYPE
    SYNTAX IpAddress
    ACCESS read-only
    STATUS mandatory
    DESCRIPTION
        "The IP address of a DNS server."
    ::= { dnsServerEntry 1 }

dnsServerType OBJECT-TYPE
    SYNTAX INTEGER {
        invalid(1),
        primary(2),
        other(3)
        }
    ACCESS read-write
    STATUS mandatory
    DESCRIPTION
        "To add a new entry to the dnsServerTable, set
         this object to primary(2) or other(3) for an IP
         address which is not already in the table. The
         primary entry will be used first, if it is
         reachable. Otherwise, one of the other entries
         will be used. Setting one entry to primary(2)
         causes any previous primary entry to change to
         other(3). To remove an entry from the table, set
         this object to invalid(1)."
    ::= { dnsServerEntry 2 }

dnsDomainName OBJECT-TYPE
    SYNTAX DisplayString(SIZE(0..127))
--    Rsyntax OCTET STRING(SIZE(0..127))
    ACCESS read-write
    STATUS mandatory
    DESCRIPTION
        "DNS domain name."
    REFERENCE
        "RFC1035, section 2.3.1 Preferred name syntax."
    ::= { dnsGrp 3 }

syslogServerTable OBJECT-TYPE
    SYNTAX SEQUENCE OF SyslogServerEntry
    ACCESS not-accessible
    STATUS mandatory
    DESCRIPTION
        "This table lists a maximum of 3 system log
        servers."
    ::= { syslogGrp 1 }

syslogServerEntry OBJECT-TYPE
    SYNTAX SyslogServerEntry
    ACCESS not-accessible
    STATUS mandatory
    DESCRIPTION
        "A system log server table entry."
    INDEX { syslogServerAddr }
    ::= { syslogServerTable 1 }

SyslogServerEntry ::= SEQUENCE {
    syslogServerAddr IpAddress,
    syslogServerType INTEGER
    }

syslogServerAddr OBJECT-TYPE
    SYNTAX IpAddress
    ACCESS read-only
    STATUS mandatory
    DESCRIPTION
        "The IP address of a system log Server."
    ::= { syslogServerEntry 1 }

syslogServerType OBJECT-TYPE
    SYNTAX INTEGER {
        valid(1),
        invalid(2)
        }
    ACCESS read-write
    STATUS mandatory
    DESCRIPTION
        "To add/remove a new entry to the
        syslogServerTable, setting to invalid(2) removes
        the corresponding entry from the
        syslogServerTable. To add a new entry into
        syslogServerTable, set this object to valid(1)
        for an IP address which is not already in the
        table."
    ::= { syslogServerEntry 2 }

syslogConsoleEnable OBJECT-TYPE
    SYNTAX INTEGER {
        enabled(1),
        disabled(2)
        }
    ACCESS read-write
    STATUS mandatory
    DESCRIPTION
        "Indicate whether the system log messages should
         be sent to console."
    DEFVAL { disabled }
    ::= { syslogGrp 2 }

syslogHostEnable OBJECT-TYPE
    SYNTAX INTEGER {
        enabled(1),
        disabled(2)
        }
    ACCESS read-write
    STATUS mandatory
    DESCRIPTION
        "Indicate whether the system log messages should
        be sent to syslog servers."
    DEFVAL { disabled }
    ::= { syslogGrp 3 }

syslogMessageControlTable OBJECT-TYPE
    SYNTAX SEQUENCE OF SyslogMessageControlEntry
    ACCESS not-accessible
    STATUS mandatory
    DESCRIPTION
        "This table contains the information about what
        system log messages should be sent to syslog host,
        console, login session, and/or logged into the
        internal buffer."
    ::= { syslogGrp 4 }

syslogMessageControlEntry OBJECT-TYPE
    SYNTAX SyslogMessageControlEntry
    ACCESS not-accessible
    STATUS mandatory
    DESCRIPTION
        "A system log message control table entry."
    INDEX { syslogMessageFacility }
    ::= { syslogMessageControlTable 1 }

SyslogMessageControlEntry ::= SEQUENCE {
    syslogMessageFacility INTEGER,
    syslogMessageSeverity INTEGER
    }

syslogMessageFacility OBJECT-TYPE
    SYNTAX INTEGER {
        cdp(1),
        mcast(2),
        dtp(3),
        dvlan(4),
        earl(5),
        fddi(6),
        ip(7),
        pruning(8),
        snmp(9),
        spantree(10),
        system(11),
        tac(12),
        tcp(13),
        telnet(14),
        tftp(15),
        vtp(16),
        vmps(17),
        kernel(18),
        filesys(19),
        drip(20),
        pagp(21),
        mgmt(22),
        mls(23),
        protfilt(24),
        security(25),
        radius(26),
        udld(27),
        gvrp(28),
        cops(29),
        qos(30),
        acl(31),
        rsvp(32),
        ld(33),
        privatevlan(34),
        ethc(35),
        gl2pt(36),
        callhome(37),
        dhcpsnooping(38),
        diags(40),
        eou(42),
        backup(43),
        eoam(44),
        webauth(45),
        dom(46),
        mvrp(47)
        }
    ACCESS read-only
    STATUS mandatory
    DESCRIPTION
        "System log message facility."
    ::= { syslogMessageControlEntry 1 }

syslogMessageSeverity OBJECT-TYPE
    SYNTAX INTEGER {
        emergencies(1),
        alerts(2),
        critical(3),
        errors(4),
        warnings(5),
        notification(6),
        informational(7),
        debugging(8)
        }
    ACCESS read-write
    STATUS mandatory
    DESCRIPTION
        "System log message severity."
    ::= { syslogMessageControlEntry 2 }

syslogTimeStampOption OBJECT-TYPE
    SYNTAX INTEGER {
        enabled(1),
        disabled(2)
        }
    ACCESS read-write
    STATUS mandatory
    DESCRIPTION
        "Indicates whether syslog Time Stamp Option is
        enabled or not. If it is set to enabled(1), the
        Time Stamp will be in the beginning of each
        syslog message."
    ::= { syslogGrp 5 }

syslogTelnetEnable OBJECT-TYPE
    SYNTAX INTEGER {
        enabled(1),
        disabled(2)
        }
    ACCESS read-write
    STATUS mandatory
    DESCRIPTION
        "Indicate whether the system log messages should
         be sent to telnet sessions."
    DEFVAL { enabled }
    ::= { syslogGrp 6 }

ntpBcastClient OBJECT-TYPE
    SYNTAX INTEGER {
        enabled(1),
        disabled(2)
        }
    ACCESS read-write
    STATUS mandatory
    DESCRIPTION
        "Entry which tells if Cat5000 should act as a
        Broadcast client or not."
    DEFVAL { disabled }
    ::= { ntpGrp 1 }

ntpBcastDelay OBJECT-TYPE
    SYNTAX INTEGER(1..999999)
    ACCESS read-write
    STATUS mandatory
    DESCRIPTION
        "Estimated Round trip time (in micro seconds) for
        NTP broadcasts. The range is from 1 to 999999."
    DEFVAL { 3000 }
    ::= { ntpGrp 2 }

ntpClient OBJECT-TYPE
    SYNTAX INTEGER {
        enabled(1),
        disabled(2)
        }
    ACCESS read-write
    STATUS mandatory
    DESCRIPTION
        "Entry which tells if the device can act as a NTP
        client (in a client-server configuration type)."
    DEFVAL { disabled }
    ::= { ntpGrp 3 }

ntpServerTable OBJECT-TYPE
    SYNTAX SEQUENCE OF NtpServerEntry
    ACCESS not-accessible
    STATUS mandatory
    DESCRIPTION
        "A list of NTP Server entries. This table lists a
        maximum of 10 Entries."
    ::= { ntpGrp 4 }

ntpServerEntry OBJECT-TYPE
    SYNTAX NtpServerEntry
    ACCESS not-accessible
    STATUS mandatory
    DESCRIPTION
        "Entry containing NTP information for a particular
        entry."
    INDEX { ntpServerAddress }
    ::= { ntpServerTable 1 }

NtpServerEntry ::= SEQUENCE {
    ntpServerAddress IpAddress,
    ntpServerType INTEGER,
    ntpServerPublicKey Gauge
    }

ntpServerAddress OBJECT-TYPE
    SYNTAX IpAddress
    ACCESS read-only
    STATUS mandatory
    DESCRIPTION
        "Entry containing NTP Server's IP address."
    ::= { ntpServerEntry 1 }

ntpServerType OBJECT-TYPE
    SYNTAX INTEGER {
        valid(1),
        invalid(2)
        }
    ACCESS read-write
    STATUS mandatory
    DESCRIPTION
        "To add or remove an entry to ntpServerTable.
        Setting to 1 adds the entry and setting to 2
        clears the entry."
    ::= { ntpServerEntry 2 }

ntpServerPublicKey OBJECT-TYPE
    SYNTAX Gauge
    ACCESS read-write
    STATUS mandatory
    DESCRIPTION
        "The key to be used when communicating with this
        server.
        A key with a value of zero indicates an invalid
        ntpServerPublicKey. When the authentication
        feature is enabled the system will not sync with
        this server when ntpAuthenticationPublicKey
        doesn't match with NTP Packet's public key.
          or
        If the ntpAuthenticationTrustedMode is trusted but
        encrypted message of ntpAuthenticationSecretKey
        with NTP packet's data doesn't match with NTP
        packet's crypto checksum in the message
        authentication mode (MAC).
          or
        If the ntpAuthenticationTrustedMode is untrusted.
        
        In client mode NMP will not send request NTP
        Packet to the server when ntpServerPublicKey
        doesn't match with any of the
        ntpAuthenticationPublicKey in
        ntpAuthenticationTable.
          or
        If the ntpAuthenticationTrustedMode is untrusted."
    ::= { ntpServerEntry 3 }

ntpSummertimeStatus OBJECT-TYPE
    SYNTAX INTEGER {
        enabled(1),
        disabled(2)
        }
    ACCESS read-write
    STATUS mandatory
    DESCRIPTION
        "Enabling or Disabling will set the clock ahead or
        behind 1 hour respectively.(daylight savings time
        in USA). This command gets active only in Summer
        time."
    DEFVAL { disabled }
    ::= { ntpGrp 5 }

ntpSummerTimezoneName OBJECT-TYPE
    SYNTAX DisplayString(SIZE(0..20))
--    Rsyntax OCTET STRING(SIZE(0..20))
    ACCESS read-write
    STATUS mandatory
    DESCRIPTION
        "Summertime time zone name for display purposes."
    ::= { ntpGrp 6 }

ntpTimezoneName OBJECT-TYPE
    SYNTAX DisplayString(SIZE(0..20))
--    Rsyntax OCTET STRING(SIZE(0..20))
    ACCESS read-write
    STATUS mandatory
    DESCRIPTION
        "Time zone name for display purposes."
    ::= { ntpGrp 7 }

ntpTimezoneOffsetHour OBJECT-TYPE
    SYNTAX INTEGER(-12..12)
    ACCESS read-write
    STATUS mandatory
    DESCRIPTION
        "Time offset (Hour) from Greenwich Mean Time."
    ::= { ntpGrp 8 }

ntpTimezoneOffsetMinute OBJECT-TYPE
    SYNTAX INTEGER(0..59)
    ACCESS read-write
    STATUS mandatory
    DESCRIPTION
        "Time offset (Minutes) from Greenwich Mean Time."
    ::= { ntpGrp 9 }

ntpAuthenticationEnable OBJECT-TYPE
    SYNTAX INTEGER {
        enabled(1),
        disabled(2)
        }
    ACCESS read-write
    STATUS mandatory
    DESCRIPTION
        "Specifies if authentication feature is enabled or
        disabled in the system."
    DEFVAL { disabled }
    ::= { ntpGrp 10 }

ntpAuthenticationTable OBJECT-TYPE
    SYNTAX SEQUENCE OF NtpAuthenticationEntry
    ACCESS not-accessible
    STATUS mandatory
    DESCRIPTION
        "A list of NTP Authentication Key entries.
        This table lists a maximum of 10 Entries"
    ::= { ntpGrp 11 }

ntpAuthenticationEntry OBJECT-TYPE
    SYNTAX NtpAuthenticationEntry
    ACCESS not-accessible
    STATUS mandatory
    DESCRIPTION
        "An entry in the ntpAuthenticationTable,
        containing values of an NTP authentication key
        pair."
    INDEX { ntpAuthenticationPublicKey }
    ::= { ntpAuthenticationTable 1 }

NtpAuthenticationEntry ::= SEQUENCE {
    ntpAuthenticationPublicKey Gauge,
    ntpAuthenticationSecretKey DisplayString,
    ntpAuthenticationTrustedMode INTEGER,
    ntpAuthenticationType INTEGER
    }

ntpAuthenticationPublicKey OBJECT-TYPE
    SYNTAX Gauge
    ACCESS read-only
    STATUS mandatory
    DESCRIPTION
        "A unique value to identify the authentication
        key. When the authentication feature is enabled
        and the ntpAuthenticationPublicKey matches with
        the NTP packet's public key then this entry is
        used."
    ::= { ntpAuthenticationEntry 1 }

ntpAuthenticationSecretKey OBJECT-TYPE
    SYNTAX DisplayString(SIZE(1..32))
--    Rsyntax OCTET STRING(SIZE(1..32))
    ACCESS read-write
    STATUS mandatory
    DESCRIPTION
        "An arbitrary string known as the secret key used
        for encrypting of the NTP packet. This key is
        useful when the ntpAuthenticationTrustedMode is
        set to trusted(1).
        This key has to be specified when this
        ntpAuthenticationEntry is created. When reading
        this object, it will return empty string."
    ::= { ntpAuthenticationEntry 2 }

ntpAuthenticationTrustedMode OBJECT-TYPE
    SYNTAX INTEGER {
        trusted(1),
        untrusted(2)
        }
    ACCESS read-write
    STATUS mandatory
    DESCRIPTION
        "A flag indicates whether the
        ntpAuthenticationSecretKey is trusted or
        untrusted. Setting a ntpAuthenticationSecretKey
        to trusted(1) allows authentication on NTP
        packets containing this key, and setting a
        ntpAuthenticationSecretKey to untrusted(2) drops
        all NTP packets containing this key."
    ::= { ntpAuthenticationEntry 3 }

ntpAuthenticationType OBJECT-TYPE
    SYNTAX INTEGER {
        valid(1),
        invalid(2)
        }
    ACCESS read-write
    STATUS mandatory
    DESCRIPTION
        "To add or remove an entry to
        ntpAuthenticationTable. Setting to 1 adds the
        entry and setting to 2 clears the entry."
    ::= { ntpAuthenticationEntry 4 }

tacacsLoginAuthentication OBJECT-TYPE
    SYNTAX INTEGER {
        enabled(1),
        disabled(2),
        enabledForTelnetOnly(3),
        enabledForConsoleOnly(4)
        }
    ACCESS read-write
    STATUS deprecated
    DESCRIPTION
        "Indicates whether the login authentication using
        the TACACS+ feature is enabled or disabled for
        console sessions and/or telnet sessions.
        
        Setting this object to enabled(1), the login
        authentication using the TACACS+ feature is
        enabled for both telnet and console sessions.
        
        Setting this object to disabled(2), the login
        authentication using the TACACS+ feature is
        disabled for both telnet and console sessions.
        
        Setting this object to enabledForTelnetOnly(3),
        the login authentication using the TACACS+
        feature is enabled only for telnet sessions, but
        disabled for console sessions.
        
        Setting this object to enabledForConsoleOnly(4),
        the login authentication using the TACACS+
        feature is enabled only for console sessions,
        but disabled for telnet sessions.
        
        This object is deprecated and replaced by
        cacPriorityTable in CISCO-AAA-CLIENT-MIB."
    DEFVAL { disabled }
    ::= { tacacsGrp 1 }

tacacsEnableAuthentication OBJECT-TYPE
    SYNTAX INTEGER {
        enabled(1),
        disabled(2),
        enabledForTelnetOnly(3),
        enabledForConsoleOnly(4)
        }
    ACCESS read-write
    STATUS deprecated
    DESCRIPTION
        "Indicates whether the enable authentication using
        the TACACS+ feature is enabled or disabled for
        console sessions and/or telnet sessions based on
        the value.
        
        Setting this object to enabled(1), the enable
        authentication using the TACACS+ feature is
        enabled for both telnet and console sessions.
        
        Setting this object to disabled(2), the enable
        authentication using the TACACS+ feature is
        disabled for both telnet and console sessions.
        
        Setting this object to enabledForTelnetOnly(3),
        the enable authentication using the TACACS+
        feature is enabled only for telnet sessions, but
        disabled for console sessions.
        
        Setting this object to enabledForConsoleOnly(4),
        the enable authentication using the TACACS+
        feature is enabled only for console sessions,
        but disabled for telnet sessions.
        
        This object is deprecated and replaced by
        cacPriorityTable in CISCO-AAA-CLIENT-MIB."
    DEFVAL { disabled }
    ::= { tacacsGrp 2 }

tacacsLocalLoginAuthentication OBJECT-TYPE
    SYNTAX INTEGER {
        enabled(1),
        disabled(2),
        enabledForTelnetOnly(3),
        enabledForConsoleOnly(4)
        }
    ACCESS read-write
    STATUS deprecated
    DESCRIPTION
        "Indicates whether the login authentication using
        local password is enabled or disabled for Console
        session and/or Telnet session based on the value.
        
        Setting this object to enabled(1),the login
        authentication using local password is enabled for
        both telnet and console sessions.
        
        Setting this object to disabled(2), the login
        authentication using local password is disabled
        for both telnet and console sessions.
        
        Setting this object to enabledForTelnetOnly(3),
        the login authentication using local password is
        enabled only for telnet sessions, but disabled for
        console session.
        
        Setting this object to enabledForConsoleOnly(4),
        the login authentication using local password is
        enabled only for console session, but disabled for
        telnet sessions.
        
        This object is deprecated and replaced by
        cacPriorityTable in CISCO-AAA-CLIENT-MIB."
    DEFVAL { enabled }
    ::= { tacacsGrp 3 }

tacacsLocalEnableAuthentication OBJECT-TYPE
    SYNTAX INTEGER {
        enabled(1),
        disabled(2),
        enabledForTelnetOnly(3),
        enabledForConsoleOnly(4)
        }
    ACCESS read-write
    STATUS deprecated
    DESCRIPTION
        "Indicates whether the enable authentication using
        local password is enabled or disabled for Console
        session and/or Telnet sessions.
        
        Setting this object to enabled(1),the enable
        authentication using local password is enabled for
        both telnet and console sessions.
        
        Setting this object to disabled(2), the enable
        authentication using local password is disabled
        for both telnet and console sessions.
        
        Setting this object to enabledForTelnetOnly(3),
        the enable authentication using local password is
        enabled only for telnet sessions, but disabled for
        console sessions.
        
        Setting this object to enabledForConsoleOnly(4),
        the enable authentication using local password is
        enabled only for console sessions, but disabled
        for telnet sessions.
        
        This object is deprecated and replaced by
        cacPriorityTable in CISCO-AAA-CLIENT-MIB."
    DEFVAL { enabled }
    ::= { tacacsGrp 4 }

tacacsNumLoginAttempts OBJECT-TYPE
    SYNTAX INTEGER(1..10)
    ACCESS read-write
    STATUS deprecated
    DESCRIPTION
        "The number of login attempts allowed.
        
        This object is deprecated and replaced by
        cacMaxLoginAttempt in CISCO-AAA-CLIENT-MIB."
    DEFVAL { 3 }
    ::= { tacacsGrp 5 }

tacacsDirectedRequest OBJECT-TYPE
    SYNTAX INTEGER {
        enabled(1),
        disabled(2)
        }
    ACCESS read-write
    STATUS mandatory
    DESCRIPTION
        "Indicates whether the directed-request feature of
        TACACS+ is enabled or disabled."
    DEFVAL { disabled }
    ::= { tacacsGrp 6 }

tacacsTimeout OBJECT-TYPE
    SYNTAX INTEGER(1..255)
    ACCESS read-write
    STATUS deprecated
    DESCRIPTION
        "The duration in seconds to wait for a response
        from the TACACS+ server host.
        
        This object is deprecated and replaced by
        cacLockoutPeriodExt in CISCO-AAA-CLIENT-MIB."
    DEFVAL { 5 }
    ::= { tacacsGrp 7 }

tacacsAuthKey OBJECT-TYPE
    SYNTAX DisplayString(SIZE(0..100))
--    Rsyntax OCTET STRING(SIZE(0..100))
    ACCESS read-write
    STATUS mandatory
    DESCRIPTION
        "The key used in encrypting the packets passed
        between the TACACS+ server and the client. This
        key must match the one configured on the server.
        
        Note that this item is only accessible when using
        the community string defined in sysCommunityRwa."
    ::= { tacacsGrp 8 }

tacacsServerTable OBJECT-TYPE
    SYNTAX SEQUENCE OF TacacsServerEntry
    ACCESS not-accessible
    STATUS mandatory
    DESCRIPTION
        "This table lists a maximum of 3 TACACS+ servers."
    ::= { tacacsGrp 9 }

tacacsServerEntry OBJECT-TYPE
    SYNTAX TacacsServerEntry
    ACCESS not-accessible
    STATUS mandatory
    DESCRIPTION
        "A TACACS+ server table entry."
    INDEX { tacacsServerAddr }
    ::= { tacacsServerTable 1 }

TacacsServerEntry ::= SEQUENCE {
    tacacsServerAddr IpAddress,
    tacacsServerType INTEGER
    }

tacacsServerAddr OBJECT-TYPE
    SYNTAX IpAddress
    ACCESS read-only
    STATUS mandatory
    DESCRIPTION
        "The IP address of a TACACS+ Server."
    ::= { tacacsServerEntry 1 }

tacacsServerType OBJECT-TYPE
    SYNTAX INTEGER {
        invalid(1),
        primary(2),
        other(3)
        }
    ACCESS read-write
    STATUS mandatory
    DESCRIPTION
        "To add a new entry to the tacacsServerTable, set
        this object to primary(2) or other(3) for an IP
        address which is not already in the table. The
        primary entry will be used first, if it is
        reachable. Otherwise, one of the other entries
        will be used. Setting one entry to primary(2)
        causes any previous primary entry to change to
        other(3). To remove an entry from the table, set
        this object to invalid(1)."
    ::= { tacacsServerEntry 2 }

ipPermitEnable OBJECT-TYPE
    SYNTAX INTEGER {
        enabled(1),
        disabled(2),
        enabledForTelnetOnly(3),
        enabledForSnmpOnly(4)
        }
    ACCESS read-write
    STATUS deprecated
    DESCRIPTION
        "This is deprecated and replaced by
        ipPermitAccessTypeEnable.
        
        Indicate whether the IP permit feature is enabled
        or disabled for Telnet and/or SNMP.
        
        Setting this object to enabled(1), the IP permit
        feature is enabled for both telnet and SNMP.
        
        Setting this object to disabled(2), the IP permit
        feature is disabled for both telnet and SNMP.
        
        Setting this object to enabledForTelnetOnly(3),
        the IP permit feature is enabled for Telnet, but
        disabled for the rest.
        
        Setting this object to enabledForSnmpOnly(4), the
        IP permit feature is enabled for SNMP, but
        disabled for the rest."
    DEFVAL { disabled }
    ::= { ipPermitListGrp 1 }

ipPermitListTable OBJECT-TYPE
    SYNTAX SEQUENCE OF IpPermitListEntry
    ACCESS not-accessible
    STATUS mandatory
    DESCRIPTION
        "This table lists a maximum of 100 IP Addresses
        with net masks of IP permit hosts. If
        ipPermitEnable is set to enabled(1), the system
        will only accept inbound accesses which come from
        the configured hosts with their permit access
        types in this table."
    ::= { ipPermitListGrp 2 }

ipPermitListEntry OBJECT-TYPE
    SYNTAX IpPermitListEntry
    ACCESS not-accessible
    STATUS mandatory
    DESCRIPTION
        "A IP permit list table entry."
    INDEX { ipPermitAddress, ipPermitMask }
    ::= { ipPermitListTable 1 }

IpPermitListEntry ::= SEQUENCE {
    ipPermitAddress IpAddress,
    ipPermitMask IpAddress,
    ipPermitType INTEGER,
    ipPermitAccessType OCTET STRING,
    ipPermitTelnetConnectLimit Gauge,
    ipPermitSshConnectLimit Gauge
    }

ipPermitAddress OBJECT-TYPE
    SYNTAX IpAddress
    ACCESS read-only
    STATUS mandatory
    DESCRIPTION
        "The IP address of a IP permit host."
    ::= { ipPermitListEntry 1 }

ipPermitMask OBJECT-TYPE
    SYNTAX IpAddress
    ACCESS read-only
    STATUS mandatory
    DESCRIPTION
        "The IP net mask of a IP permit host."
    ::= { ipPermitListEntry 2 }

ipPermitType OBJECT-TYPE
    SYNTAX INTEGER {
        valid(1),
        invalid(2)
        }
    ACCESS read-write
    STATUS mandatory
    DESCRIPTION
        "Setting this object to invalid(2), removes the
        corresponding entry from the ipPermitListTable. To
        add a new entry into ipPermitListTable, set this
        object to valid(1), for an IP address and IP net
        mask which are not already in the table."
    ::= { ipPermitListEntry 3 }

ipPermitAccessType OBJECT-TYPE
    SYNTAX OCTET STRING(SIZE(1..2))
        -- BITS are:
        --   telnet(0)
        --   snmp(1)
        --   ssh(2)
        --   http(3)
    ACCESS read-write
    STATUS mandatory
    DESCRIPTION
        "The IP access type of a IP permit host.
        At least one access type has to be set."
    DEFVAL { 'f0'h }
    ::= { ipPermitListEntry 4 }

ipPermitTelnetConnectLimit OBJECT-TYPE
    SYNTAX Gauge
    ACCESS read-write
    STATUS mandatory
    DESCRIPTION
        "Indicates the telnet connection limit that 
        will be applied when accepting new telnet 
        connections for a specific host. A value of 
        zero means no limit will be applied for telnet 
        connections.
        
        Setting this object to a non-zero value will
        turn on the 'telnet' bit in the corresponding 
        ipPermitAccessType. Turnning off the 'telnet' 
        bit in the corresponding ipPermitAccessType will
        reset this ipPermitTelnetConnectLimit value to
        zero."
    DEFVAL { 0 }
    ::= { ipPermitListEntry 5 }

ipPermitSshConnectLimit OBJECT-TYPE
    SYNTAX Gauge
    ACCESS read-write
    STATUS mandatory
    DESCRIPTION
        "Indicates the ssh connection limit that will 
        be applied when accepting new ssh connections 
        for a specific host. A value of zero means no 
        limit will be applied for ssh connections.
        
        Setting this object to a non-zero value will
        turn on the 'ssh' bit in the corresponding 
        ipPermitAccessType. Turnning off the 'ssh' bit 
        in the corresponding ipPermitAccessType will
        reset this ipPermitSshConnectLimit value to
        zero."
    DEFVAL { 0 }
    ::= { ipPermitListEntry 6 }

ipPermitDeniedListTable OBJECT-TYPE
    SYNTAX SEQUENCE OF IpPermitDeniedListEntry
    ACCESS not-accessible
    STATUS mandatory
    DESCRIPTION
        "This table lists up to 10 the most recently
        denied IP addresses with the access type."
    ::= { ipPermitListGrp 3 }

ipPermitDeniedListEntry OBJECT-TYPE
    SYNTAX IpPermitDeniedListEntry
    ACCESS not-accessible
    STATUS mandatory
    DESCRIPTION
        "A IP permit denied list table entry."
    INDEX { ipPermitDeniedAddress }
    ::= { ipPermitDeniedListTable 1 }

IpPermitDeniedListEntry ::= SEQUENCE {
    ipPermitDeniedAddress IpAddress,
    ipPermitDeniedAccess INTEGER,
    ipPermitDeniedTime TimeTicks
    }

ipPermitDeniedAddress OBJECT-TYPE
    SYNTAX IpAddress
    ACCESS read-only
    STATUS mandatory
    DESCRIPTION
        "The IP address of a IP permit denied access."
    ::= { ipPermitDeniedListEntry 1 }

ipPermitDeniedAccess OBJECT-TYPE
    SYNTAX INTEGER {
        telnet(1),
        snmp(2),
        ssh(3),
        http(4)
        }
    ACCESS read-only
    STATUS mandatory
    DESCRIPTION
        "The denied access type."
    ::= { ipPermitDeniedListEntry 2 }

ipPermitDeniedTime OBJECT-TYPE
    SYNTAX TimeTicks
    ACCESS read-only
    STATUS mandatory
    DESCRIPTION
        "The time (in hundredths of a second) since the IP
        permit denied access happens."
    ::= { ipPermitDeniedListEntry 3 }

ipPermitAccessTypeEnable OBJECT-TYPE
    SYNTAX OCTET STRING(SIZE(1..2))
        -- BITS are:
        --   telnet(0)
        --   snmp(1)
        --   ssh(2)
        --   http(3)
    ACCESS read-write
    STATUS mandatory
    DESCRIPTION
        "This is to replace ipPermitEnable.
        Indicates whether the IP permit feature is
        enabled or disabled for Telnet, SNMP, ssh and
        http. If a bit is set the coresponding feature is
        enabled. If a bit is not set the coresponding
        feature is disabled."
    DEFVAL { '00'h }
    ::= { ipPermitListGrp 4 }

portChannelTable OBJECT-TYPE
    SYNTAX SEQUENCE OF PortChannelEntry
    ACCESS not-accessible
    STATUS deprecated
    DESCRIPTION
        "A list of port channel entries. The number of
        entries is determined by the number of ports in
        the system which support the Ethernet Channelling
        feature.
        
        This table is deprecated and replaced by
        pagpEtherChannelTable in CISCO-PAGP-MIB and
        dot3adAggTable in IEEE8023-LAG-MIB."
    ::= { portChannelGrp 1 }

portChannelEntry OBJECT-TYPE
    SYNTAX PortChannelEntry
    ACCESS not-accessible
    STATUS deprecated
    DESCRIPTION
        "Entry containing information for a particular
        port on a module."
    INDEX { portChannelModuleIndex, portChannelPortIndex }
    ::= { portChannelTable 1 }

PortChannelEntry ::= SEQUENCE {
    portChannelModuleIndex INTEGER,
    portChannelPortIndex INTEGER,
    portChannelPorts OCTET STRING,
    portChannelAdminStatus INTEGER,
    portChannelOperStatus INTEGER,
    portChannelNeighbourDeviceId OCTET STRING,
    portChannelNeighbourPortId INTEGER,
    portChannelProtInPackets Counter,
    portChannelProtOutPackets Counter,
    portChannelIfIndex INTEGER
    }

portChannelModuleIndex OBJECT-TYPE
    SYNTAX INTEGER(1..16)
    ACCESS read-only
    STATUS deprecated
    DESCRIPTION
        "An index value that uniquely identifies the
        module where this port is located."
    ::= { portChannelEntry 1 }

portChannelPortIndex OBJECT-TYPE
    SYNTAX INTEGER(1..255)
    ACCESS read-only
    STATUS deprecated
    DESCRIPTION
        "An index value that uniquely identifies this port
        within a module (see portIndex)."
    ::= { portChannelEntry 2 }

portChannelPorts OBJECT-TYPE
    SYNTAX OCTET STRING(SIZE(0..8))
    ACCESS read-write
    STATUS deprecated
    DESCRIPTION
        "The set of ports on a module channelling
        together. Each Octet within the value of this
        object specifies a set of eight ports, with the
        first octet specifying ports 1 through 8, the
        second octet specifying ports 9 through 16, etc.
        Within each octet, the most significant bit
        represents the lowest numbered port, and the
        least significant bit rep resents the highest
        numbered port. Thus, each port is represented by
        a single bit within the value of this object. If
        that bit has a value of `1' then that port is
        included in the set of channel ports. The default
        value of this object is a string which only has a
        value of `1' on its own port."
    ::= { portChannelEntry 3 }

portChannelAdminStatus OBJECT-TYPE
    SYNTAX INTEGER {
        on(1),
        off(2),
        desirable(3),
        auto(4),
        desirableSilent(5),
        autoSilent(6)
        }
    ACCESS read-write
    STATUS deprecated
    DESCRIPTION
        "Indicates the administrative status set on the
        channel ports. If the status is set to on(1), the
        channelling is enabled. If the status is set to
        off(2), the channelling is disabled. If the status
        is set to desirable(3), the port initiates a pagp
        negotiation request to become a channel and will
        become a channel if the far end agrees. If the
        status is set to auto(4), the port does not
        initiate a request to become a channel but will do
        so if it receives a request to become a channel
        from the far end. If the status is set to
        desirableSilent(5), the port initiates a pagp
        negotiation request to become a channel and will
        become a channel if the far end agrees. If the
        port doesn't receive any packets from far end,
        then  after some timeout period the port forms a
        channel by itself. If the status is set to
        autoSilent(6), the port does not initiate a
        request to become a channel, but will do so if it
        receives a request to become a channel from the
        far end. If the port doesn't receive any request,
        then after some timeout period the port forms a
        channel by itself."
    DEFVAL { auto }
    ::= { portChannelEntry 4 }

portChannelOperStatus OBJECT-TYPE
    SYNTAX INTEGER {
        channelling(1),
        notChannelling(2)
        }
    ACCESS read-only
    STATUS deprecated
    DESCRIPTION
        "Indicates whether the ports current channelling
        operational status is channel or not."
    ::= { portChannelEntry 5 }

portChannelNeighbourDeviceId OBJECT-TYPE
    SYNTAX OCTET STRING(SIZE(6))
    ACCESS read-only
    STATUS deprecated
    DESCRIPTION
        "Indicates the neighbors device id."
    ::= { portChannelEntry 6 }

portChannelNeighbourPortId OBJECT-TYPE
    SYNTAX INTEGER(1..2147483647)
    ACCESS read-only
    STATUS deprecated
    DESCRIPTION
        "Indicates the neighbor ports' Id."
    ::= { portChannelEntry 7 }

portChannelProtInPackets OBJECT-TYPE
    SYNTAX Counter
    ACCESS read-only
    STATUS deprecated
    DESCRIPTION
        "Indicates the number of protocol packets received
        on the ports."
    ::= { portChannelEntry 8 }

portChannelProtOutPackets OBJECT-TYPE
    SYNTAX Counter
    ACCESS read-only
    STATUS deprecated
    DESCRIPTION
        "Indicates the number of protocol packets
        transmitted on the ports."
    ::= { portChannelEntry 9 }

portChannelIfIndex OBJECT-TYPE
    SYNTAX INTEGER(1..2147483647)
    ACCESS read-only
    STATUS deprecated
    DESCRIPTION
        "The value of the instance of the ifIndex object
        defined in MIB-II, for the interface corresponding
        to the channel which the port belongs to. This
        object will have a non zero value if its
        portChannelOperStatus is channelling and the link
        of this port is up."
    ::= { portChannelEntry 10 }

portCpbTable OBJECT-TYPE
    SYNTAX SEQUENCE OF PortCpbEntry
    ACCESS not-accessible
    STATUS mandatory
    DESCRIPTION
        "A list of port capability entries. The number of
        entries is determined by the number of modules in
        the chassis and the number of ports on each
        module."
    ::= { portCpbGrp 1 }

portCpbEntry OBJECT-TYPE
    SYNTAX PortCpbEntry
    ACCESS not-accessible
    STATUS mandatory
    DESCRIPTION
        "Entry containing port capability information for
        a particular port on a module."
    INDEX { portCpbModuleIndex, portCpbPortIndex }
    ::= { portCpbTable 1 }

PortCpbEntry ::= SEQUENCE {
    portCpbModuleIndex INTEGER,
    portCpbPortIndex INTEGER,
    portCpbSpeed OCTET STRING,
    portCpbDuplex OCTET STRING,
    portCpbTrunkEncapsulationType OCTET STRING,
    portCpbTrunkMode OCTET STRING,
    portCpbChannel DisplayString,
    portCpbBroadcastSuppression OCTET STRING,
    portCpbFlowControl OCTET STRING,
    portCpbSecurity INTEGER,
    portCpbVlanMembership OCTET STRING,
    portCpbPortfast INTEGER,
    portCpbUdld INTEGER,
    portCpbInlinePower OCTET STRING,
    portCpbAuxiliaryVlan OCTET STRING,
    portCpbSpan OCTET STRING,
    portCpbCosRewrite INTEGER,
    portCpbTosRewrite OCTET STRING,
    portCpbCopsGrouping OCTET STRING,
    portCpbDot1x INTEGER,
    portCpbIgmpFilter INTEGER
    }

portCpbModuleIndex OBJECT-TYPE
    SYNTAX INTEGER(1..16)
    ACCESS read-only
    STATUS mandatory
    DESCRIPTION
        "An index value that uniquely identifies the
        module where this port is located (see
        portModuleIndex)."
    ::= { portCpbEntry 1 }

portCpbPortIndex OBJECT-TYPE
    SYNTAX INTEGER(1..255)
    ACCESS read-only
    STATUS mandatory
    DESCRIPTION
        "An index value that uniquely identifies this port
        within a module (see portIndex)."
    ::= { portCpbEntry 2 }

portCpbSpeed OBJECT-TYPE
    SYNTAX OCTET STRING(SIZE(1..2))
        -- BITS are:
        --   auto(0)
        --   mbps4(1)
        --   mbps10(2)
        --   mbps16(3)
        --   mbps45(4)
        --   mbps100(5)
        --   mbps155(6)
        --   mbps400(7)
        --   mbps622(8)
        --   mbps1000(9)
        --   mbps1dot544(10)
        --   mbps2(11)
        --   mbps2dot048(12)
        --   kps64(13)
        --   mbps10000(14)
    ACCESS read-only
    STATUS mandatory
    DESCRIPTION
        "Indicates the port speed capability of a port."
    ::= { portCpbEntry 3 }

portCpbDuplex OBJECT-TYPE
    SYNTAX OCTET STRING(SIZE(1..2))
        -- BITS are:
        --   half(0)
        --   full(1)
        --   auto(2)
        --   hdx(3)
        --   fdx(4)
    ACCESS read-only
    STATUS mandatory
    DESCRIPTION
        "Indicates the duplex capability of a port.
        The fdx(4) is specially for tokenring full-duplex
        and hdx(3) is specially for tokenring
        half-duplex."
    ::= { portCpbEntry 4 }

portCpbTrunkEncapsulationType OBJECT-TYPE
    SYNTAX OCTET STRING(SIZE(1..2))
        -- BITS are:
        --   lane(0)
        --   dot10(1)
        --   dot1Q(2)
        --   isl(3)
        --   negotiate(4)
    ACCESS read-only
    STATUS mandatory
    DESCRIPTION
        "Indicates the VLAN encapsulation capability of a
        port, The dot10(1) is for 801.10 and dot1q(2) is
        for 801.1Q."
    ::= { portCpbEntry 5 }

portCpbTrunkMode OBJECT-TYPE
    SYNTAX OCTET STRING(SIZE(1..2))
        -- BITS are:
        --   on(0)
        --   off(1)
        --   desirable(2)
        --   auto(3)
        --   onNoNegotiate(4)
    ACCESS read-only
    STATUS mandatory
    DESCRIPTION
        "Indicates the trunk capability of a port."
    ::= { portCpbEntry 6 }

portCpbChannel OBJECT-TYPE
    SYNTAX DisplayString(SIZE(0..128))
--    Rsyntax OCTET STRING(SIZE(0..128))
    ACCESS read-only
    STATUS mandatory
    DESCRIPTION
        "Indicates the channelling capability of a port."
    ::= { portCpbEntry 7 }

portCpbBroadcastSuppression OBJECT-TYPE
    SYNTAX OCTET STRING(SIZE(1..2))
        -- BITS are:
        --   pps(0)
        --   percentage(1)
    ACCESS read-only
    STATUS mandatory
    DESCRIPTION
        "Indicates the broadcast suppression capability of
        a port. The pps(0) is for ports capable of
        specifying suppression in packets per second and
        percentage(1) is for ports capable of specifying
        suppression in terms of percentage of bandwidth."
    ::= { portCpbEntry 8 }

portCpbFlowControl OBJECT-TYPE
    SYNTAX OCTET STRING(SIZE(1..2))
        -- BITS are:
        --   receiveOff(0)
        --   receiveOn(1)
        --   receiveDesired(2)
        --   sendOff(3)
        --   sendOn(4)
        --   sendDesired(5)
    ACCESS read-only
    STATUS mandatory
    DESCRIPTION
        "Indicates the flow control capability of a port."
    ::= { portCpbEntry 9 }

portCpbSecurity OBJECT-TYPE
    SYNTAX INTEGER {
        yes(1),
        no(2)
        }
    ACCESS read-only
    STATUS mandatory
    DESCRIPTION
        "Indicates whether a port supports security."
    ::= { portCpbEntry 10 }

portCpbVlanMembership OBJECT-TYPE
    SYNTAX OCTET STRING(SIZE(1..2))
        -- BITS are:
        --   static(0)
        --   dynamic(1)
    ACCESS read-only
    STATUS mandatory
    DESCRIPTION
        "Indicates the vlan membership capability of a
        port."
    ::= { portCpbEntry 11 }

portCpbPortfast OBJECT-TYPE
    SYNTAX INTEGER {
        yes(1),
        no(2)
        }
    ACCESS read-only
    STATUS mandatory
    DESCRIPTION
        "Indicates whether a port supports portfast."
    ::= { portCpbEntry 12 }

portCpbUdld OBJECT-TYPE
    SYNTAX INTEGER {
        yes(1),
        no(2)
        }
    ACCESS read-only
    STATUS mandatory
    DESCRIPTION
        "Indicates whether the port is capable of UDLD
        (UniDirectional Link Detection) or not."
    ::= { portCpbEntry 13 }

portCpbInlinePower OBJECT-TYPE
    SYNTAX OCTET STRING(SIZE(1..2))
        -- BITS are:
        --   auto(0)
        --   on(1)
        --   off(2)
        --   static(3)
    ACCESS read-only
    STATUS mandatory
    DESCRIPTION
        "Indicate the inline power capability of a port.
        'auto' denotes the ability that the switch
        automatically determines whether or not power
        should be provided. 'on' denotes the ability to
        manually turn on inline power.
        'off' denotes the ability to manually turn off
        inline power. 'static' denotes the ability to
        preallocate power for a port."
    ::= { portCpbEntry 14 }

portCpbAuxiliaryVlan OBJECT-TYPE
    SYNTAX OCTET STRING(SIZE(1..2))
        -- BITS are:
        --   vlanNo(0)
        --   untagged(1)
        --   dot1p(2)
        --   none(3)
    ACCESS read-only
    STATUS mandatory
    DESCRIPTION
        "Indicate the voice vlan capability of a port."
    ::= { portCpbEntry 15 }

portCpbSpan OBJECT-TYPE
    SYNTAX OCTET STRING(SIZE(1..2))
        -- BITS are:
        --   source(0)
        --   destination(1)
        --   reflector(2)
    ACCESS read-only
    STATUS mandatory
    DESCRIPTION
        "Indicates port span capabilities.
        source(0) denotes the capability of being SPAN
        source destination(1) denotes the capability of
        being SPAN destination, reflector(2) denotes the
        capability of being SPAN reflector."
    ::= { portCpbEntry 16 }

portCpbCosRewrite OBJECT-TYPE
    SYNTAX INTEGER {
        yes(1),
        no(2)
        }
    ACCESS read-only
    STATUS mandatory
    DESCRIPTION
        "Indicates whether a port supports CoS rewrite."
    ::= { portCpbEntry 17 }

portCpbTosRewrite OBJECT-TYPE
    SYNTAX OCTET STRING(SIZE(1..2))
        -- BITS are:
        --   dscp(0)
        --   ipPrecedence(1)
    ACCESS read-only
    STATUS mandatory
    DESCRIPTION
        "Indicates the ToS rewrite capability of a port.
        dscp(0) denotes the port capability to classify
        packets according to the DSCP.
        ipPrecedence(1) denotes the port capability to
        classify packets according to the IP Precedence."
    ::= { portCpbEntry 18 }

portCpbCopsGrouping OBJECT-TYPE
    SYNTAX OCTET STRING(SIZE(0..8))
    ACCESS read-only
    STATUS mandatory
    DESCRIPTION
        "The set of ports on a module that are configured
        together as far as the Differentiated Services
        Cops feature is concerned. Each Octet within the
        value of this object specifies a set of eight
        ports, with the first octet specifying ports 1
        through 8, the second octet specifying ports 9
        through 16, etc. Within each octet, the most
        significant bit represents the lowest numbered
        port, and the least significant bit represents
        the highest numbered port. Thus, each port is
        represented by a single bit within the value of
        this object. If that bit has a value of `1' then
        that port is included in the set of Cops
        grouping."
    ::= { portCpbEntry 19 }

portCpbDot1x OBJECT-TYPE
    SYNTAX INTEGER {
        yes(1),
        no(2)
        }
    ACCESS read-only
    STATUS mandatory
    DESCRIPTION
        "Indicates whether a port supports 802.1x."
    ::= { portCpbEntry 20 }

portCpbIgmpFilter OBJECT-TYPE
    SYNTAX INTEGER {
        yes(1),
        no(2)
        }
    ACCESS read-only
    STATUS mandatory
    DESCRIPTION
        "Indicates whether a port supports IGMP filter."
    ::= { portCpbEntry 21 }

portTopNControlTable OBJECT-TYPE
    SYNTAX SEQUENCE OF PortTopNControlEntry
    ACCESS not-accessible
    STATUS mandatory
    DESCRIPTION
        "A list of top N port control entries."
    ::= { portTopNGrp 1 }

portTopNControlEntry OBJECT-TYPE
    SYNTAX PortTopNControlEntry
    ACCESS not-accessible
    STATUS mandatory
    DESCRIPTION
        "A set of parameters that control the creation of
        a report of the top N ports according to several
        metrics.
        For example, an instance of the portTopNDuration
        object might be named portTopNDuration.3"
    INDEX { portTopNControlIndex }
    ::= { portTopNControlTable 1 }

PortTopNControlEntry ::= SEQUENCE {
    portTopNControlIndex INTEGER,
    portTopNRateBase INTEGER,
    portTopNType INTEGER,
    portTopNMode INTEGER,
    portTopNReportStatus INTEGER,
    portTopNDuration INTEGER,
    portTopNTimeRemaining INTEGER,
    portTopNStartTime TimeTicks,
    portTopNRequestedSize INTEGER,
    portTopNGrantedSize INTEGER,
    portTopNOwner OwnerString,
    portTopNStatus RowStatus
    }

portTopNControlIndex OBJECT-TYPE
    SYNTAX INTEGER(1..5)
    ACCESS read-only
    STATUS mandatory
    DESCRIPTION
        "An index that uniquely identifies an entry
        in the portTopNControl table. Each such
        entry defines one top N report."
    ::= { portTopNControlEntry 1 }

portTopNRateBase OBJECT-TYPE
    SYNTAX INTEGER {
        portTopNUtilization(1),
        portTopNIOOctets(2),
        portTopNIOPkts(3),
        portTopNIOBroadcastPkts(4),
        portTopNIOMulticastPkts(5),
        portTopNInErrors(6),
        portTopNBufferOverflow(7)
        }
    ACCESS read-write
    STATUS mandatory
    DESCRIPTION
        "The variable for all ports in this system
        based on which portTopNTable/report is ordered.
        
        This object may not be modified if the associated
        portTopNStatus object is equal to active(1)."
    DEFVAL { portTopNUtilization }
    ::= { portTopNControlEntry 2 }

portTopNType OBJECT-TYPE
    SYNTAX INTEGER {
        portTopNAllPorts(1),
        portTopNEthernet(2),
        portTopNFastEthernet(3),
        portTopNGigaEthernet(4),
        portTopNTokenRing(5),
        portTopNFDDI(6),
        portTopNAllEthernetPorts(7),
        portTopN10GigaEthernet(8)
        }
    ACCESS read-write
    STATUS mandatory
    DESCRIPTION
        "The sampling port type.
        
        This object may not be modified if the associated
        portTopNStatus object is equal to active(1)."
    DEFVAL { portTopNAllPorts }
    ::= { portTopNControlEntry 3 }

portTopNMode OBJECT-TYPE
    SYNTAX INTEGER {
        portTopNForeground(1),
        portTopNBackground(2)
        }
    ACCESS read-write
    STATUS mandatory
    DESCRIPTION
        "The running mode of this portTopN control entry.
        portTopNForeground (1) means when
        portTopNTimeRemaining reaches to 0, the report
        will show on the CLI at once and it won't be kept
        in the portTopNTable. portTopNBackground (2) means
        the report will not show on the CLI it will be
        kept in the portTopNTable.
        
        This object may not be modified if the associated
        portTopNStatus object is equal to active(1)."
    DEFVAL { portTopNBackground }
    ::= { portTopNControlEntry 4 }

portTopNReportStatus OBJECT-TYPE
    SYNTAX INTEGER {
        progressing(1),
        ready(2)
        }
    ACCESS read-only
    STATUS mandatory
    DESCRIPTION
        "The report status of this portTopN control entry.
        Progressing (1) means that the report of this
        portTopN control entry is still in progress. The
        management station can poll this mib object to
        check the report data is available or not.
        Ready (2) means the report is available."
    ::= { portTopNControlEntry 5 }

portTopNDuration OBJECT-TYPE
    SYNTAX INTEGER(0|10..999)
    ACCESS read-write
    STATUS mandatory
    DESCRIPTION
        "The sampling interval in seconds during which
        statistics are collected for this report.
        
        When this is set a value and the corresponding
        portTopNControlEntry is valid, the
        portTopNTimeRemaining object shall be set to the
        same value.
        portTopNTimeRemaining starts at the same value as
        portTopNDuration and counts down as the collection
        goes on.
        
        If this object is set to be zero, it will do the
        collection immediately. And the collecting report
        value should be the absolute counter value."
    DEFVAL { 30 }
    ::= { portTopNControlEntry 6 }

portTopNTimeRemaining OBJECT-TYPE
    SYNTAX INTEGER(1..65535)
    ACCESS read-only
    STATUS mandatory
    DESCRIPTION
        "The number of seconds left in the report
        currently being collected. When portTopNDuration
        object is modified by the management station, a
        new collection is started, possibly aborting a
        currently running report. The new value is used as
        the requested duration of this report, which is
        loaded from the associated portTopNDuration
        object.
        
        When this object is a non-zero value, any
        associated portTopNEntries shall be made
        inaccessible by the monitor.
        
        While the value of this object is non-zero and the
        corresponding portTopNControlENtry is valid, it
        decrements by one per second until it reaches
        zero. During this time, all associated
        portTopNEntries shall remain inaccessible. At
        the time that this object decrements to zero, the
        report is made accessible in the portTopNTable.
        Thus, the portTopN table is to be created only at
        the end of the collection interval."
    ::= { portTopNControlEntry 7 }

portTopNStartTime OBJECT-TYPE
    SYNTAX TimeTicks
    ACCESS read-only
    STATUS mandatory
    DESCRIPTION
        "The value of sysUpTime when this top N report was
        last started. In other words, this is the time
        that the associated portTopNTimeRemaining object
        was modified to start the requested report."
    ::= { portTopNControlEntry 8 }

portTopNRequestedSize OBJECT-TYPE
    SYNTAX INTEGER(1..65535)
    ACCESS read-write
    STATUS mandatory
    DESCRIPTION
        "The maximum number of ports requested for the top
        N entry.
        
        When this object is created or modified, the value
        of portTopNGrantedSize is set as closely to this
        object as is possible for the particular
        implementation and available resources.
        Valid value for this object is 1 to maximum number
        of physical ports. The default value is 20 ports."
    DEFVAL { 20 }
    ::= { portTopNControlEntry 9 }

portTopNGrantedSize OBJECT-TYPE
    SYNTAX INTEGER(1..65535)
    ACCESS read-only
    STATUS mandatory
    DESCRIPTION
        "The maximum number of ports in the top N table.
        When the associated portTopNRequestedSize object
        is created or modified, the value of this object
        should be set as closely to the requested value as
        is possible for the particular implementation and
        available resources. The value must not be lowered
        except as a result of a set to the associated
        portTopNRequestedSize object.
        Ports with the highest value of portTopNRateBase
        shall be placed in this table in decreasing order
        of this rate until there is no more room or until
        there are no more ports."
    ::= { portTopNControlEntry 10 }

portTopNOwner OBJECT-TYPE
    SYNTAX OwnerString
--    Rsyntax OCTET STRING(SIZE(0..255))
    ACCESS read-write
    STATUS mandatory
    DESCRIPTION
        "The entity that configured this entry and is
        therefore using the resources assigned to it."
    ::= { portTopNControlEntry 11 }

portTopNStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of this portTopNControl entry.
        The Management station sends the user set values
        with a portTopNStatus value of createAndGo(4).
        When the agent receives it the collection of the
        report starts.
        When the portTopNReportStatus is ready(2) the user
        can get the reports (portTopNTable).
        For the current implementation createAndWait(5)
        will not be supported.
        There can be only 5 rows in the control table."
    ::= { portTopNControlEntry 12 }

portTopNTable OBJECT-TYPE
    SYNTAX SEQUENCE OF PortTopNEntry
    ACCESS not-accessible
    STATUS mandatory
    DESCRIPTION
        "A list of top N port entries."
    ::= { portTopNGrp 2 }

portTopNEntry OBJECT-TYPE
    SYNTAX PortTopNEntry
    ACCESS not-accessible
    STATUS mandatory
    DESCRIPTION
        "A set of statistics for a port that is part of a
        top N report. For example, an instance of the
        portTopNRateBase object might be named
        portTopNUtilization.3.10"
    INDEX { portTopNControlIndex, portTopNIndex }
    ::= { portTopNTable 1 }

PortTopNEntry ::= SEQUENCE {
    portTopNIndex INTEGER,
    portTopNModuleNumber INTEGER,
    portTopNPortNumber INTEGER,
    portTopNUtilization INTEGER,
    portTopNIOOctets Counter,
    portTopNIOPkts Counter,
    portTopNIOBroadcast Counter,
    portTopNIOMulticast Counter,
    portTopNInErrors Counter,
    portTopNBufferOverFlow Counter
    }

portTopNIndex OBJECT-TYPE
    SYNTAX INTEGER(1..65535)
    ACCESS read-only
    STATUS mandatory
    DESCRIPTION
        "An index that uniquely identifies an entry in
        the portTopN table among those in the same report.
        This index is between 1 and N, where N is the
        portTopNGrantedSize of ports with the highest
        portTopNRateBase. Increasing values of
        portTopNIndex shall be assigned to entries with
        decreasing values of portTopNRateBase until index
        N is assigned to the entry with the lowest value
        of portTopNRateBase or there are no more
        portTopNEntries."
    ::= { portTopNEntry 1 }

portTopNModuleNumber OBJECT-TYPE
    SYNTAX INTEGER(1..20)
    ACCESS read-only
    STATUS mandatory
    DESCRIPTION
        "The module number of the port counter data
        entry."
    ::= { portTopNEntry 2 }

portTopNPortNumber OBJECT-TYPE
    SYNTAX INTEGER(1..255)
    ACCESS read-only
    STATUS mandatory
    DESCRIPTION
        "The port number of the port counter data entry."
    ::= { portTopNEntry 3 }

portTopNUtilization OBJECT-TYPE
    SYNTAX INTEGER(1..65535)
    ACCESS read-only
    STATUS mandatory
    DESCRIPTION
        "The utilization of the port in the system.
        The utilization is computed in the following
        methods:
        
        Ethernet Utilization: (If Full Duplex, multiply by 2)
        
        10 Mbps         I/O-pkts * (9.6 + 6.4) + (0.8 * I/O-Bytes)
        Ethernet Util = -----------------------------------------
                Interval * 10,000
        
                where 9.6 is interframe gap of Ethernet
                6.4 is preamble of Ethernet
                10,000 is 10Mbps
        
        100 Mbps        I/O-pkts * (96 + 64) + (8 * I/O-Bytes)
        Ethernet Util = --------------------------------------
                Interval * 1,000,000
        
        1000 Mbps       I/O-pkts * (96 + 64) + (8 * I/O-Bytes)
        Ethernet Util = --------------------------------------
                Interval * 10,000,000
        
        All other       I/O-pkts * (9.6 + 6.4) + (0.8 * I/O-Bytes)
        Ethernet Util = ------------------------------------------
                Interval * N * 1,000
                (where N is N Mbps)
        
        Token Ring Utilization:
        (Assuming that Octets is from AC byte through FCS)
        
        
        4 Mbps                  Pkts * 32 + (8 * Octets)
        Token Ring Util = 100 * ------------------------
                        Interval * 4,000,000
                   where 32 is bits in SD, ED, FS and IFG
        
        16 Mbps                 Pkts * 64 + (8 * Octets)
        Token Ring Util = 100 * ------------------------
                        Interval * 16,000,000
                  where 64 is bits in SD, ED, FS and IFG
        
        FDDI Utilization:
        
           I/O-Pkts * (64 + 8 + 32 + 16) + (8 * I/O-Bytes)
        FDDI Util = ----------------------------------------------
           Interval * 100,000,000
        
           where 64 is Preamble of FDDI,
           8 is the Start Delimiter (SD) of FDDI,
           32 is the CRC, and
           16 is the End of Frame Sequence (EFS) of FDDI."
    ::= { portTopNEntry 4 }

portTopNIOOctets OBJECT-TYPE
    SYNTAX --?? syntax is not convertable to SMIv1
           Counter
    ACCESS read-only
    STATUS mandatory
    DESCRIPTION
        "The Input and Output octets of the port in the
        system."
    ::= { portTopNEntry 5 }

portTopNIOPkts OBJECT-TYPE
    SYNTAX --?? syntax is not convertable to SMIv1
           Counter
    ACCESS read-only
    STATUS mandatory
    DESCRIPTION
        "The Input and Output packets of the port in the
        system."
    ::= { portTopNEntry 6 }

portTopNIOBroadcast OBJECT-TYPE
    SYNTAX --?? syntax is not convertable to SMIv1
           Counter
    ACCESS read-only
    STATUS mandatory
    DESCRIPTION
        "The Input and Output broadcast packets of the
        port in the system."
    ::= { portTopNEntry 7 }

portTopNIOMulticast OBJECT-TYPE
    SYNTAX --?? syntax is not convertable to SMIv1
           Counter
    ACCESS read-only
    STATUS mandatory
    DESCRIPTION
        "The Input and Output multicast packets of the
         port in the system."
    ::= { portTopNEntry 8 }

portTopNInErrors OBJECT-TYPE
    SYNTAX Counter
    ACCESS read-only
    STATUS mandatory
    DESCRIPTION
        "The Input error packets of the port in the
        system."
    ::= { portTopNEntry 9 }

portTopNBufferOverFlow OBJECT-TYPE
    SYNTAX Counter
    ACCESS read-only
    STATUS mandatory
    DESCRIPTION
        "The number of buffer overflow of the port in
        the system."
    ::= { portTopNEntry 10 }

mdgGatewayTable OBJECT-TYPE
    SYNTAX SEQUENCE OF MdgGatewayEntry
    ACCESS not-accessible
    STATUS mandatory
    DESCRIPTION
        "This table lists a maximum of 3 MDG gateways."
    ::= { mdgGrp 1 }

mdgGatewayEntry OBJECT-TYPE
    SYNTAX MdgGatewayEntry
    ACCESS not-accessible
    STATUS mandatory
    DESCRIPTION
        "A MDG gateway table entry."
    INDEX { mdgGatewayAddr }
    ::= { mdgGatewayTable 1 }

MdgGatewayEntry ::= SEQUENCE {
    mdgGatewayAddr IpAddress,
    mdgGatewayType INTEGER
    }

mdgGatewayAddr OBJECT-TYPE
    SYNTAX IpAddress
    ACCESS read-only
    STATUS mandatory
    DESCRIPTION
        "The IP address of a default gateway."
    ::= { mdgGatewayEntry 1 }

mdgGatewayType OBJECT-TYPE
    SYNTAX INTEGER {
        invalid(1),
        primary(2),
        other(3)
        }
    ACCESS read-write
    STATUS mandatory
    DESCRIPTION
        "To add a new entry to the mdgGatewayTable, set
        this object to primary(2) or other(3) for an IP
        address which is not already in the table. The
        primary entry will be used first, if it is
        reachable. Otherwise, one of the other entries
        will be used. Setting one entry to primary(2)
        causes any previous primary entry to change to
        other(3). To remove an entry from the table, set
        this object to invalid(1). Changing an existing
        entry from primary(2) to other(3) is not allowed.
        If the value of this object is updated, the
        corresponding entry of the ipRouteTable (mibII)
        will be updated and vice versa."
    ::= { mdgGatewayEntry 2 }

radiusLoginAuthentication OBJECT-TYPE
    SYNTAX INTEGER {
        enabled(1),
        disabled(2),
        enabledForTelnetOnly(3),
        enabledForConsoleOnly(4)
        }
    ACCESS read-write
    STATUS deprecated
    DESCRIPTION
        "Indicates whether the login authentication using
        RADIUS feature is enabled or disabled for console
        and/or telnet sessions.
        
        Setting this object to enabled(1), the login
        authentication using RADIUS feature is enabled for
        both console and telnet sessions.
        
        Setting this object to disabled(2), the login
        authentication using RADIUS feature is disabled
        for both console and telnet sessions.
        
        Setting this object to enabledForTelnetOnly(3),the
        login authentication using RADIUS feature is
        enabled only for telnet sessions, but disabled
        for console session.
        
        Setting this object to enabledForConsoleOnly(4),
        the login authentication using RADIUS feature is
        enabled only for console sessions, but disabled
        for telnet sessions.
        
        This object is deprecated and replaced by
        cacPriorityTable in CISCO-AAA-CLIENT-MIB."
    DEFVAL { disabled }
    ::= { radiusGrp 1 }

radiusEnableAuthentication OBJECT-TYPE
    SYNTAX INTEGER {
        enabled(1),
        disabled(2),
        enabledForTelnetOnly(3),
        enabledForConsoleOnly(4)
        }
    ACCESS read-write
    STATUS deprecated
    DESCRIPTION
        "Indicates whether the enable authentication using
        the RADIUS feature is enabled or disabled for
        Console and telnet sessions.
        
        Setting this object to enabled(1), the enable
        authentication using RADIUS feature is enabled for
        both console and telnet sessions.
        
        Setting this object to disabled(2), the enable
        authentication using RADIUS feature is disabled
        for both console and telnet sessions.
        
        Setting this object to enabledForTelnetOnly(3),
        the enable authentication using RADIUS feature is
        enabled only for telnet sessions, but disabled for
        console sessions.
        
        Setting this object to enabledForConsoleOnly(4),
        the enable authentication using RADIUS feature is
        enabled only for console sessions, but disabled
        for telnet sessions.
        
        This object is deprecated and replaced by
        cacPriorityTable in CISCO-AAA-CLIENT-MIB."
    DEFVAL { disabled }
    ::= { radiusGrp 2 }

radiusDeadtime OBJECT-TYPE
    SYNTAX INTEGER(0..1440)
    ACCESS read-write
    STATUS mandatory
    DESCRIPTION
        "Indicates the length of time in minutes that
        the system will mark the server dead when a RADIUS
        server does not respond to an authentication
        request. During the interval of the dead time, any
        authentication request that comes up would not be
        sent to that RADIUS server that was marked as
        dead. The default value of 0 means that the
        RADIUS servers will not be marked dead if they
        do not respond."
    DEFVAL { 0 }
    ::= { radiusGrp 3 }

radiusAuthKey OBJECT-TYPE
    SYNTAX DisplayString(SIZE(0..64))
--    Rsyntax OCTET STRING(SIZE(0..64))
    ACCESS read-write
    STATUS mandatory
    DESCRIPTION
        "The key used in encrypting the packets passed
        between the RADIUS server and the client. This key
        must match the one configured on the server.
        
        Note that this item is only accessible when using
        the community string defined in sysCommunityRwa."
    ::= { radiusGrp 4 }

radiusTimeout OBJECT-TYPE
    SYNTAX INTEGER(1..1000)
    ACCESS read-write
    STATUS mandatory
    DESCRIPTION
        "This is the time in seconds between
        retransmissions to the RADIUS server."
    DEFVAL { 5 }
    ::= { radiusGrp 5 }

radiusRetransmits OBJECT-TYPE
    SYNTAX INTEGER(1..100)
    ACCESS read-write
    STATUS mandatory
    DESCRIPTION
        "Indicates number of times the RADIUS server
        should be tried before giving up on the server."
    DEFVAL { 2 }
    ::= { radiusGrp 6 }

radiusServerTable OBJECT-TYPE
    SYNTAX SEQUENCE OF RadiusServerEntry
    ACCESS not-accessible
    STATUS deprecated
    DESCRIPTION
        "This table lists a maximum of 3 RADIUS servers.
        
        This object is deprecated and replaced by
        crRadiusServerTable in CISCO-RADIUS-MIB."
    ::= { radiusGrp 7 }

radiusServerEntry OBJECT-TYPE
    SYNTAX RadiusServerEntry
    ACCESS not-accessible
    STATUS deprecated
    DESCRIPTION
        "A RADIUS server table entry."
    INDEX { radiusServerAddr }
    ::= { radiusServerTable 1 }

RadiusServerEntry ::= SEQUENCE {
    radiusServerAddr IpAddress,
    radiusServerAuthPort INTEGER,
    radiusServerType INTEGER
    }

radiusServerAddr OBJECT-TYPE
    SYNTAX IpAddress
    ACCESS read-only
    STATUS deprecated
    DESCRIPTION
        "The IP address of a RADIUS Server."
    ::= { radiusServerEntry 1 }

radiusServerAuthPort OBJECT-TYPE
    SYNTAX INTEGER(0..65535)
    ACCESS read-write
    STATUS deprecated
    DESCRIPTION
        "This is the destination UDP port number to which
        RADIUS messages should be sent. The RADIUS server
        will not be used for authentication if this port
        number is 0."
    REFERENCE
        "RFC2138, Implementation Note."
    DEFVAL { 1812 }
    ::= { radiusServerEntry 2 }

radiusServerType OBJECT-TYPE
    SYNTAX INTEGER {
        invalid(1),
        primary(2),
        other(3)
        }
    ACCESS read-write
    STATUS deprecated
    DESCRIPTION
        "To add a new entry to the radiusServerTable, set
        this object to primary(2) or other(3) for an IP
        address which is not already in the table. The
        primary entry will be used first, if it is
        reachable. Otherwise, one of the other entries
        will be used. Setting one entry to primary(2)
        causes any previous primary entry to change to
        other(3). To remove an entry from the table,
        set this object to invalid(1)."
    ::= { radiusServerEntry 3 }

traceRouteMaxQueries OBJECT-TYPE
    SYNTAX INTEGER(1..20)
    ACCESS read-only
    STATUS mandatory
    DESCRIPTION
        "Maximum number of query entries allowed to be
        outstanding at any time, in the
        traceRouteQueryTable.
        The typical value for this object is 5."
    ::= { traceRouteGrp 1 }

traceRouteQueryTable OBJECT-TYPE
    SYNTAX SEQUENCE OF TraceRouteQueryEntry
    ACCESS not-accessible
    STATUS mandatory
    DESCRIPTION
        "A control table used to query the information
        about each gateway along the path to a host by
        specifying retrieval criteria for the host. The
        resulting data for each instance of a query in
        this table is returned in the traceRouteDataTable.
        The maximum number of entries (rows) in this table
        cannot exceed the value returned by
        traceRouteMaxQueries."
    ::= { traceRouteGrp 2 }

traceRouteQueryEntry OBJECT-TYPE
    SYNTAX TraceRouteQueryEntry
    ACCESS not-accessible
    STATUS mandatory
    DESCRIPTION
        "A conceptual row of the traceRouteQueryTable used
        to setup retrieval criteria to search for gateways
        belongs to the path to a particular host
        identified by its IP address. The actual search
        is started by setting the value of
        traceRouteQueryStatus to valid(1)."
    INDEX { traceRouteQueryIndex }
    ::= { traceRouteQueryTable 1 }

TraceRouteQueryEntry ::= SEQUENCE {
    traceRouteQueryIndex INTEGER,
    traceRouteHost DisplayString,
    traceRouteQueryDNSEnable INTEGER,
    traceRouteQueryWaitingTime INTEGER,
    traceRouteQueryInitTTL INTEGER,
    traceRouteQueryMaxTTL INTEGER,
    traceRouteQueryUDPPort INTEGER,
    traceRouteQueryPacketCount INTEGER,
    traceRouteQueryPacketSize INTEGER,
    traceRouteQueryTOS INTEGER,
    traceRouteQueryResult INTEGER,
    traceRouteQueryTime TimeTicks,
    traceRouteQueryOwner DisplayString,
    traceRouteQueryStatus INTEGER
    }

traceRouteQueryIndex OBJECT-TYPE
    SYNTAX INTEGER(1..65535)
    ACCESS read-only
    STATUS mandatory
    DESCRIPTION
        "Object which specifies an unique entry in the
        traceRouteQueryTable."
    ::= { traceRouteQueryEntry 1 }

traceRouteHost OBJECT-TYPE
    SYNTAX DisplayString(SIZE(0..255))
--    Rsyntax OCTET STRING(SIZE(0..255))
    ACCESS read-write
    STATUS mandatory
    DESCRIPTION
        "Network(IP) address in dotted decimal format or
        the DNS hostname of the host which is tracerouted."
    ::= { traceRouteQueryEntry 2 }

traceRouteQueryDNSEnable OBJECT-TYPE
    SYNTAX INTEGER {
        enabled(1),
        disabled(2)
        }
    ACCESS read-write
    STATUS mandatory
    DESCRIPTION
        "If this value of this object is true, the
        traceroute operation will do a DNS lookup for each
        hop on the path, so the corresponding instance of
        the traceRouteDataTable will contain the host name
        and the ip address; otherwise, that instance only
        contains the ip address."
    DEFVAL { enabled }
    ::= { traceRouteQueryEntry 3 }

traceRouteQueryWaitingTime OBJECT-TYPE
    SYNTAX INTEGER(1..300)
--  Units
--    seconds
    ACCESS read-write
    STATUS mandatory
    DESCRIPTION
        "The trace route waiting time in seconds for an
        ICMP response message."
    DEFVAL { 5 }
    ::= { traceRouteQueryEntry 4 }

traceRouteQueryInitTTL OBJECT-TYPE
    SYNTAX INTEGER(1..255)
    ACCESS read-write
    STATUS mandatory
    DESCRIPTION
        "If this value of this object is set, it allows
        users skip processing for gateways that are less
        than traceRouteQueryInitTTL away by sending
        datagram with the value of this object instead of
        the default value of one."
    DEFVAL { 1 }
    ::= { traceRouteQueryEntry 5 }

traceRouteQueryMaxTTL OBJECT-TYPE
    SYNTAX INTEGER(1..255)
    ACCESS read-write
    STATUS mandatory
    DESCRIPTION
        "The maximum TTL value used in outgoing packets."
    DEFVAL { 30 }
    ::= { traceRouteQueryEntry 6 }

traceRouteQueryUDPPort OBJECT-TYPE
    SYNTAX INTEGER(1..65535)
    ACCESS read-write
    STATUS mandatory
    DESCRIPTION
        "The base UDP destination port is used in the
        traceroute datagrams. This value of this object is
        often larger than 30,000 to make it improbable
        that this port is used (this causes the
        destination host's UDP module to generate an ICMP
        port unreachable so the traceroute operation
        knows when the operation is accomplished).
        The traceroute operation will increment this value
        of this object each time it sends a datagram. This
        object should be used in the unlikely event that
        the destination port is listening to a port in the
        default traceroute port range."
    DEFVAL { 33434 }
    ::= { traceRouteQueryEntry 7 }

traceRouteQueryPacketCount OBJECT-TYPE
    SYNTAX INTEGER(1..1000)
    ACCESS read-write
    STATUS mandatory
    DESCRIPTION
        "Specifies the number of traceroute packets to
        send to the target host in this sequence."
    DEFVAL { 3 }
    ::= { traceRouteQueryEntry 8 }

traceRouteQueryPacketSize OBJECT-TYPE
    SYNTAX INTEGER(0..1420)
    ACCESS read-write
    STATUS mandatory
    DESCRIPTION
        "Specifies the size of traceroute packets to send
        to the target host in this sequence. "
    DEFVAL { 0 }
    ::= { traceRouteQueryEntry 9 }

traceRouteQueryTOS OBJECT-TYPE
    SYNTAX INTEGER(0..255)
    ACCESS read-write
    STATUS mandatory
    DESCRIPTION
        "The type of service to be set in the IP header of
        the outgoing packets.This value can set to see if
        different types-of-service result in different
        paths. Not all values of TOS are legal or
        meaningful (see the IP spec for definitions.
        Useful values are probably 16 (low delay) and 8
        (high throughput)."
    DEFVAL { 0 }
    ::= { traceRouteQueryEntry 10 }

traceRouteQueryResult OBJECT-TYPE
    SYNTAX INTEGER(-1..2147483647)
    ACCESS read-only
    STATUS mandatory
    DESCRIPTION
        "The result status of the query. Possible values
        are:
        
        -1 -Either the query has not been initiated or the
        agent is busy processing this query instance. Time
        to completion of the query processing depends on
        the complexity of the query and the number of
        matches that satisfy this query.
        
        0..2147483647 - The search has ended and this is
        the number of rows in the traceRouteDataTable,
        resulting from this query."
    ::= { traceRouteQueryEntry 21 }

traceRouteQueryTime OBJECT-TYPE
    SYNTAX TimeTicks
    ACCESS read-only
    STATUS mandatory
    DESCRIPTION
        "The value of sysUpTime at the time when the query
        is configured."
    ::= { traceRouteQueryEntry 22 }

traceRouteQueryOwner OBJECT-TYPE
    SYNTAX DisplayString(SIZE(0..50))
--    Rsyntax OCTET STRING(SIZE(0..50))
    ACCESS read-write
    STATUS mandatory
    DESCRIPTION
        "The manager entity that configured this entry and
        is therefore using the resources assigned to it."
    ::= { traceRouteQueryEntry 23 }

traceRouteQueryStatus OBJECT-TYPE
    SYNTAX INTEGER {
        valid(1),
        invalid(2)
        }
    ACCESS read-write
    STATUS mandatory
    DESCRIPTION
        "The status object used to manage rows in this
        table.
        When set this object to valid(1), the query is
        initiated. Once initiated, all the read-write
        objects of this table can't be modified. To remove
        an entry from the  table, set this object to
        invalid(2)."
    ::= { traceRouteQueryEntry 24 }

traceRouteDataTable OBJECT-TYPE
    SYNTAX SEQUENCE OF TraceRouteDataEntry
    ACCESS not-accessible
    STATUS mandatory
    DESCRIPTION
        "A table containing information about the gateway
        belongs to the path to the host corresponding to
        all the completed queries setup in the
        traceRouteQueryTable."
    ::= { traceRouteGrp 3 }

traceRouteDataEntry OBJECT-TYPE
    SYNTAX TraceRouteDataEntry
    ACCESS not-accessible
    STATUS mandatory
    DESCRIPTION
        "A conceptual row of the traceRouteDataTable used
        to return information about all the gateway
        belongs to the host of which search criteria is
        corresponding instance of the
        traceRouteQueryTable."
    INDEX { traceRouteQueryIndex, traceRouteDataIndex }
    ::= { traceRouteDataTable 1 }

TraceRouteDataEntry ::= SEQUENCE {
    traceRouteDataIndex INTEGER,
    traceRouteDataGatewayName DisplayString,
    traceRouteDataGatewayIp IpAddress,
    traceRouteDataRtt INTEGER,
    traceRouteDataHopCount INTEGER,
    traceRouteDataErrors INTEGER
    }

traceRouteDataIndex OBJECT-TYPE
    SYNTAX INTEGER(1..65535)
    ACCESS read-only
    STATUS mandatory
    DESCRIPTION
        "Object which specifies an unique entry in the
        traceRouteDataTable."
    ::= { traceRouteDataEntry 1 }

traceRouteDataGatewayName OBJECT-TYPE
    SYNTAX DisplayString(SIZE(0..255))
--    Rsyntax OCTET STRING(SIZE(0..255))
    ACCESS read-only
    STATUS mandatory
    DESCRIPTION
        "The DNS name of the gateway if available."
    ::= { traceRouteDataEntry 2 }

traceRouteDataGatewayIp OBJECT-TYPE
    SYNTAX IpAddress
    ACCESS read-only
    STATUS mandatory
    DESCRIPTION
        "The ip address of the gateway. If the traceroute
        packet was sent and timed-out, the ip address is
        set to 0.0.0.0."
    ::= { traceRouteDataEntry 3 }

traceRouteDataRtt OBJECT-TYPE
    SYNTAX INTEGER(1..65535)
--  Units
--    milliseconds
    ACCESS read-only
    STATUS mandatory
    DESCRIPTION
        "The  round trip time of the current packet that
        have been sent in this sequence."
    ::= { traceRouteDataEntry 4 }

traceRouteDataHopCount OBJECT-TYPE
    SYNTAX INTEGER(1..65535)
    ACCESS read-only
    STATUS mandatory
    DESCRIPTION
        "The number of hop starting from the place where
        the traceroute operation is initialized to the
        gateway which has the traceRouteDataGatewayIp."
    ::= { traceRouteDataEntry 5 }

traceRouteDataErrors OBJECT-TYPE
    SYNTAX INTEGER {
        icmpUnreachNet(1),
        icmpUnreachHost(2),
        icmpUnreachProtocol(3),
        icmpUnreachPort(4),
        icmpUnreachNeedFrag(5),
        icmpUnreachSrcFail(6),
        icmpUnreachNoNet(7),
        icmpUnreachNoHost(8),
        icmpUnreachHostIsolated(9),
        icmpUnreachNetProhib(10),
        icmpUnreachProhib(11),
        icmpUnreachNetTos(12),
        icmpUnreachHostTos(13),
        icmpUnreachAdmin(14),
        icmpUnreachHostPrec(15),
        icmpUnreachPrecedence(16),
        icmpUnknown(17),
        icmpTimeOut(18),
        icmpTTLExpired(19)
        }
    ACCESS read-only
    STATUS mandatory
    DESCRIPTION
        "The error of the traceroute operation."
    ::= { traceRouteDataEntry 6 }

fileCopyProtocol OBJECT-TYPE
    SYNTAX INTEGER {
        tftp(1),
        rcp(2)
        }
    ACCESS read-write
    STATUS mandatory
    DESCRIPTION
        "The protocol to be used for any remote copy.
        If the config file transfer is to occur locally on
        the SNMP agent, the method of transfer is left up
        to the implementation, and is not restricted to
        the protocols above.
        
        The value of this object can not be changed when
        the fileCopyResult object has the value of
        inProgress(1)."
    DEFVAL { tftp }
    ::= { fileCopyGrp 1 }

fileCopyRemoteServer OBJECT-TYPE
    SYNTAX DisplayString(SIZE(0..64))
--    Rsyntax OCTET STRING(SIZE(0..64))
    ACCESS read-write
    STATUS mandatory
    DESCRIPTION
        "The IP address  or the host name of the tftp/rcp
        remote server from (or to) which to copy the file.
        If the copy operation  is local on the SNMP agent,
        this object is not applicable.
        
        The value of this object can not be changed when
        the fileCopyResult object has the value of
        inProgress(1)."
    ::= { fileCopyGrp 2 }

fileCopySrcFileName OBJECT-TYPE
    SYNTAX DisplayString(SIZE(0..64))
--    Rsyntax OCTET STRING(SIZE(0..64))
    ACCESS read-write
    STATUS mandatory
    DESCRIPTION
        "The source file name (including the path, if
        applicable) of the file. The accepted value of
        this object is 'cfg1' or 'cfg2' when the requested
        action is one of the following:
        
        copyConfigFromFlashToRuntime(8), and
        copyConfigFileFromFlashToHost(11).
        
        The value of this object can not be changed when
        the fileCopyResult object has the value of
        inProgress(1)."
    ::= { fileCopyGrp 3 }

fileCopyDstFileName OBJECT-TYPE
    SYNTAX DisplayString(SIZE(0..64))
--    Rsyntax OCTET STRING(SIZE(0..64))
    ACCESS read-write
    STATUS mandatory
    DESCRIPTION
        "The destination file name (including the path, if
        applicable) of the file. The accepted value of
        this object is 'cfg1' or 'cfg2' when the requested
        action is one of the following:
        
        copyConfigFromRuntimeToFlash(9),
        copyConfigFileFromHostToFlash(10).
        
        The value of this object can not be changed when
        the fileCopyResult object has the value of
        inProgress(1)."
    ::= { fileCopyGrp 4 }

fileCopyModuleNumber OBJECT-TYPE
    SYNTAX INTEGER(0..16)
    ACCESS read-write
    STATUS mandatory
    DESCRIPTION
        "The module number specified in the copy
        operation.
        
        If the value of this object is 0 and the
        fileCopyAction object has the value of
        copyImageFromHostToFlash(4), the switch will do
        multiple download to the modules with matching
        image type. It is left to the SNMP agent to allow
        the individual modules to be reset with the
        downloaded images or not.
        
        The value of this object can not be changed when
        the fileCopyResult object has the value of
        inProgress(1)."
    ::= { fileCopyGrp 5 }

fileCopyUserName OBJECT-TYPE
    SYNTAX DisplayString(SIZE(1..40))
--    Rsyntax OCTET STRING(SIZE(1..40))
    ACCESS read-write
    STATUS mandatory
    DESCRIPTION
        "Remote user name for copy via rcp protocol. This
        object must be specified when the
        fileCopyProtocol is rcp."
    ::= { fileCopyGrp 6 }

fileCopyAction OBJECT-TYPE
    SYNTAX INTEGER {
        other(1),
        copyConfigFromHostToRuntime(2),
        copyConfigFromRuntimeToHost(3),
        copyImageFromHostToFlash(4),
        copyImageFromFlashToHost(5),
        copyConfigFromFlashToRuntime(8),
        copyConfigFromRuntimeToFlash(9),
        copyConfigFileFromHostToFlash(10),
        copyConfigFileFromFlashToHost(11),
        copyTechReportFromRuntimeToHost(12)
        }
    ACCESS read-write
    STATUS mandatory
    DESCRIPTION
        "Setting this object to one of the acceptable
        values will initiate the requested action using
        the information provided by fileCopyProtocol,
        fileCopyRemoteServer, fileCopySrcFileName,
        fileCopyDstFileName,fileCopyModuleNumber and
        fileCopyUserName.
        
        copyConfigFromHostToRuntime(2):
           Copy the configuration file from host to
           runtime configuration over the network through
           tftp/rcp. This action will use
           fileCopyProtocol, fileCopyRemoteServer,
           fileCopySrcFileName, fileCopyModuleNumber,
           and fileCopyUserName (if applicable).
        
        copyConfigFromRuntimeToHost(3):
           Copy the runtime configuration to host over the
           network through tftp/rcp. This action will use
           fileCopyProtocol, fileCopyRemoteServer,
           fileCopyModuleNumber, fileCopyDstFileName,
           fileCopyUserName (if applicable), and
           fileCopyRuntimeConfigPart.
        
        copyImageFromHostToFlash(4):
           Copy the image from host to the flash over the
           network through tftp/rcp. It is up to the
           SNMP agent to reset and run the downloaded
           image after copying. This action will use
           fileCopyProtocol, fileCopyRemoteServer,
           fileCopySrcFileName, fileCopyModuleNumber,
           and fileCopyUserName (if applicable).
        
        copyImageFromFlashToHost(5):
           Copy the image from flash to host over the
           switch through tftp/rcp. This action will use
           fileCopyProtocol, fileCopyRemoteServer,
           fileCopyDstFileName, fileCopyModuleNumber,
           and fileCopyUserName (if applicable).
        
        copyConfigFromFlashToRuntime(8):
           Copy the configuration file to the runtime
           configuration locally. This action can perform
           only on the SUPG supervisor model and will
           use fileCopySrcFileName ('cfg1' or 'cfg2').
        
        copyConfigFromRuntimeToFlash(9):
           Copy  the runtime configuration to a
           configuration file on the flash locally. This
           action can perform only on the SUPG supervisor
           model and will use fileCopyDstFileName ('cfg1'
           or 'cfg2'), and fileCopyRuntimeConfigPart.
        
        copyConfigFileFromHostToFlash(10):
           Copy the configuration file from host to the
           runtime configuration over the network through
           tftp/rcp. This action can perform only on the
           SUPG  supervisor model and will use
           fileCopyProtocol, fileCopyRemoteServer,
           fileCopySrcFileName, fileCopyDstFileName,
           fileCopyModuleNumber and fileCopyUserName
           (if applicable).
        
        copyConfigFileFromFlashToHost(11):
           Copy the configuration file on the flash to
           host over the network through tftp/rcp.
           This action can perform only on the
           SUPG supervisor model and will use
           fileCopyProtocol, fileCopyRemoteServer,
           fileCopySrcFileName, fileCopyDstFileName,
           fileCopyModuleNumber and fileCopyUserName
           (if applicable).
        
        copyTechReportFromRuntimeToHost(12):
           Copy the technical report of the system to
           host over the network through tftp only. This
           action will use fileCopyProtocol,
           fileCopyRemoteServer, fileCopyModuleNumber,
           and fileCopyDstFileName.
        
        Setting this object to any other value results in
        an error.
        
        The value of this object can not be changed when
        the fileCopyResult object has the value of
        inProgress(1)."
    ::= { fileCopyGrp 7 }

fileCopyResult OBJECT-TYPE
    SYNTAX INTEGER {
        inProgress(1),
        success(2),
        noResponse(3),
        tooManyRetries(4),
        noBuffers(5),
        noProcesses(6),
        badChecksum(7),
        badLength(8),
        badFlash(9),
        serverError(10),
        userCanceled(11),
        wrongCode(12),
        fileNotFound(13),
        invalidHost(14),
        invalidModule(15),
        accessViolation(16),
        unknownStatus(17),
        invalidStorageDevice(18),
        insufficientSpaceOnStorageDevice(19),
        insufficientDramSize(20),
        incompatibleImage(21),
        rcpError(22)
        }
    ACCESS read-only
    STATUS mandatory
    DESCRIPTION
        "Contains the result of the last copy action
        request.
        If the value of fileCopyResult is rcpError(22),
        then the detailed rcp error messages are contained
        in fileCopyResultRcpErrorMessage."
    ::= { fileCopyGrp 8 }

fileCopyResultRcpErrorMessage OBJECT-TYPE
    SYNTAX DisplayString(SIZE(0..255))
--    Rsyntax OCTET STRING(SIZE(0..255))
    ACCESS read-only
    STATUS mandatory
    DESCRIPTION
        "Contains the detailed rcp error messages if the
        value of fileCopyResult is rcpError(22) for the
        last copy action request; otherwise, this MIB
        object contains the empty string."
    ::= { fileCopyGrp 9 }

fileCopyRuntimeConfigPart OBJECT-TYPE
    SYNTAX INTEGER {
        all(1),
        nonDefault(2)
        }
    ACCESS read-write
    STATUS mandatory
    DESCRIPTION
        "Indicates the part of runtime configuration to be
        copied. This object will only take effect when the
        object value of fileCopyAction is one of the
        following:
        
        copyConfigFromRuntimeToHost(3),
        copyConfigFromRuntimeToFlash(9).
        
        all -- copy all the runtime configuration.
        
        nonDefault --copy only the part of the runtime
                     configuration which is different from
                     the default configuration."
    DEFVAL { all }
    ::= { fileCopyGrp 10 }

voicePortIfConfigTable OBJECT-TYPE
    SYNTAX SEQUENCE OF VoicePortIfConfigEntry
    ACCESS not-accessible
    STATUS mandatory
    DESCRIPTION
        "A list of port entries. The number of entries is
        determined by the number of modules in the chassis
        and the number of ports with the voice port
        interface configuration capability in the system."
    ::= { voiceGrp 1 }

voicePortIfConfigEntry OBJECT-TYPE
    SYNTAX VoicePortIfConfigEntry
    ACCESS not-accessible
    STATUS mandatory
    DESCRIPTION
        "Entry containing voice interface configuration
        for a particular port."
    INDEX { voicePortIfConfigModuleIndex, voicePortIfConfigPortIndex }
    ::= { voicePortIfConfigTable 1 }

VoicePortIfConfigEntry ::= SEQUENCE {
    voicePortIfConfigModuleIndex INTEGER,
    voicePortIfConfigPortIndex INTEGER,
    voicePortIfDHCPEnabled TruthValue,
    voicePortIfIpAddress IpAddress,
    voicePortIfIpNetMask IpAddress,
    voicePortIfTftpServerAddress IpAddress,
    voicePortIfGatewayAddress IpAddress,
    voicePortIfDnsServerAddress IpAddress,
    voicePortIfDnsDomain DisplayString,
    voicePortIfOperDnsDomain DisplayString
    }

voicePortIfConfigModuleIndex OBJECT-TYPE
    SYNTAX INTEGER(1..16)
    ACCESS not-accessible
    STATUS mandatory
    DESCRIPTION
        "An index value that uniquely identifies the
        module where this port is located."
    ::= { voicePortIfConfigEntry 1 }

voicePortIfConfigPortIndex OBJECT-TYPE
    SYNTAX INTEGER(1..255)
    ACCESS not-accessible
    STATUS mandatory
    DESCRIPTION
        "An index value that uniquely identifies this port
        within a module. The value is determined by the
        location of the port on the module."
    ::= { voicePortIfConfigEntry 2 }

voicePortIfDHCPEnabled OBJECT-TYPE
    SYNTAX TruthValue
--    Rsyntax INTEGER {
--        true(1),
--        false(2)
--        }
    ACCESS read-write
    STATUS mandatory
    DESCRIPTION
        "Indicate whether DHCP service is enabled."
    DEFVAL { true }
    ::= { voicePortIfConfigEntry 3 }

voicePortIfIpAddress OBJECT-TYPE
    SYNTAX IpAddress
    ACCESS read-write
    STATUS mandatory
    DESCRIPTION
        "This port's IP address. This object
        is configurable only if voicePortIfDHCPEnabled
        is false. When the value of voicePortIfDHCPEnabled
        is false, this object should be configured."
    ::= { voicePortIfConfigEntry 4 }

voicePortIfIpNetMask OBJECT-TYPE
    SYNTAX IpAddress
    ACCESS read-write
    STATUS mandatory
    DESCRIPTION
        "This port's subnet mask. This object
        is configurable only if voicePortIfDHCPEnabled
        is false. When the value of voicePortIfDHCPEnabled
        is false, this object should be configured."
    ::= { voicePortIfConfigEntry 5 }

voicePortIfTftpServerAddress OBJECT-TYPE
    SYNTAX IpAddress
    ACCESS read-write
    STATUS mandatory
    DESCRIPTION
        "This port's TFTP Server address. This object
        is configurable only if voicePortIfDHCPEnabled
        is false. When the value of voicePortIfDHCPEnabled
        is false, this object should be configured."
    ::= { voicePortIfConfigEntry 6 }

voicePortIfGatewayAddress OBJECT-TYPE
    SYNTAX IpAddress
    ACCESS read-write
    STATUS mandatory
    DESCRIPTION
        "This port's router address. This object
        is configurable only if voicePortIfDHCPEnabled
        is false."
    ::= { voicePortIfConfigEntry 7 }

voicePortIfDnsServerAddress OBJECT-TYPE
    SYNTAX IpAddress
    ACCESS read-write
    STATUS mandatory
    DESCRIPTION
        "This port's DNS Server address. This object
        is configurable only if voicePortIfDHCPEnabled
        is false."
    ::= { voicePortIfConfigEntry 8 }

voicePortIfDnsDomain OBJECT-TYPE
    SYNTAX DisplayString(SIZE(0..255))
--    Rsyntax OCTET STRING(SIZE(0..255))
    ACCESS read-write
    STATUS mandatory
    DESCRIPTION
        "This port's DNS domain name. This object
        is configurable only if voicePortIfDHCPEnabled
        is false."
    ::= { voicePortIfConfigEntry 9 }

voicePortIfOperDnsDomain OBJECT-TYPE
    SYNTAX DisplayString(SIZE(0..255))
--    Rsyntax OCTET STRING(SIZE(0..255))
    ACCESS read-only
    STATUS mandatory
    DESCRIPTION
        "This port's operational DNS domain name. If
        voicePortIfDHCPEnabled is true, this object
        indicates the domain name taken from the
        DHCP server. If voicePortIfDHCPEnabled is false,
        this object indicates the domain name configured
        by users for this voice port or the domain name
        taken from DNS configuration for the system
        otherwise."
    ::= { voicePortIfConfigEntry 10 }

voicePortCallManagerTable OBJECT-TYPE
    SYNTAX SEQUENCE OF VoicePortCallManagerEntry
    ACCESS not-accessible
    STATUS mandatory
    DESCRIPTION
        "A list of call manager entries. The number of
        entries is determined by the number of modules in
        the chassis and the number of ports with the
        voice port interface configuration capability
        in the system."
    ::= { voiceGrp 2 }

voicePortCallManagerEntry OBJECT-TYPE
    SYNTAX VoicePortCallManagerEntry
    ACCESS not-accessible
    STATUS mandatory
    DESCRIPTION
        "Entry containing voice interface configuration
        for a particular port."
    INDEX { voicePortModuleIndex, voicePortIndex, voicePortCallManagerIndex }
    ::= { voicePortCallManagerTable 1 }

VoicePortCallManagerEntry ::= SEQUENCE {
    voicePortModuleIndex INTEGER,
    voicePortIndex INTEGER,
    voicePortCallManagerIndex INTEGER,
    voicePortCallManagerIpAddr IpAddress
    }

voicePortModuleIndex OBJECT-TYPE
    SYNTAX INTEGER(1..16)
    ACCESS not-accessible
    STATUS mandatory
    DESCRIPTION
        "An index value that uniquely identifies the
        module where this port is located."
    ::= { voicePortCallManagerEntry 1 }

voicePortIndex OBJECT-TYPE
    SYNTAX INTEGER(1..255)
    ACCESS not-accessible
    STATUS mandatory
    DESCRIPTION
        "An index value that uniquely identifies this port
        within a module."
    ::= { voicePortCallManagerEntry 2 }

voicePortCallManagerIndex OBJECT-TYPE
    SYNTAX INTEGER(1..5)
    ACCESS not-accessible
    STATUS mandatory
    DESCRIPTION
        "An index value that uniquely identifies this
        CallManager within a module/port. A port can
        register up to 5 CallManager."
    ::= { voicePortCallManagerEntry 3 }

voicePortCallManagerIpAddr OBJECT-TYPE
    SYNTAX IpAddress
    ACCESS read-only
    STATUS mandatory
    DESCRIPTION
        "The Call Manager IP Address of this port. A port
        can register up to 5 call managers."
    ::= { voicePortCallManagerEntry 4 }

voicePortOperDnsServerTable OBJECT-TYPE
    SYNTAX SEQUENCE OF VoicePortOperDnsServerEntry
    ACCESS not-accessible
    STATUS mandatory
    DESCRIPTION
        "A list of operational DNS entries used by the
        voice ports."
    ::= { voiceGrp 3 }

voicePortOperDnsServerEntry OBJECT-TYPE
    SYNTAX VoicePortOperDnsServerEntry
    ACCESS not-accessible
    STATUS mandatory
    DESCRIPTION
        "Entry containing infomation on DNS servers may be
        used for a particular voice port.
        
        If DHCP is enabled on a port, the DNS server IP
        address will come from the DHCP server. If DHCP
        is disabled, the DNS server IP address can be
        configured by users through the mib object
        voicePortIfDnsServerAddress for a port, otherwise
        it will be taken from DNS configuration in the
        system."
    INDEX { voicePortDnsModuleIndex, voicePortDnsPortIndex, voicePortOperDnsServerIndex }
    ::= { voicePortOperDnsServerTable 1 }

VoicePortOperDnsServerEntry ::= SEQUENCE {
    voicePortDnsModuleIndex INTEGER,
    voicePortDnsPortIndex INTEGER,
    voicePortOperDnsServerIndex Gauge,
    voicePortOperDnsServerIpAddr IpAddress,
    voicePortOperDnsServerSource INTEGER
    }

voicePortDnsModuleIndex OBJECT-TYPE
    SYNTAX INTEGER(1..16)
    ACCESS not-accessible
    STATUS mandatory
    DESCRIPTION
        "An index value that uniquely identifies the
        module where this port is located."
    ::= { voicePortOperDnsServerEntry 1 }

voicePortDnsPortIndex OBJECT-TYPE
    SYNTAX INTEGER(1..255)
    ACCESS not-accessible
    STATUS mandatory
    DESCRIPTION
        "An index value that uniquely identifies this port
         within a module."
    ::= { voicePortOperDnsServerEntry 2 }

voicePortOperDnsServerIndex OBJECT-TYPE
    SYNTAX Gauge
    ACCESS not-accessible
    STATUS mandatory
    DESCRIPTION
        "An index value that uniquely identifies this DNS
         server within a module/port. This value indicates
         the priority order among these DNS servers."
    ::= { voicePortOperDnsServerEntry 3 }

voicePortOperDnsServerIpAddr OBJECT-TYPE
    SYNTAX IpAddress
    ACCESS read-only
    STATUS mandatory
    DESCRIPTION
        "The operational DNS Server IP Address of this
        port. "
    ::= { voicePortOperDnsServerEntry 4 }

voicePortOperDnsServerSource OBJECT-TYPE
    SYNTAX INTEGER {
        fromDhcp(1),
        fromPortConfig(2),
        fromSystemConfig(3)
        }
    ACCESS read-only
    STATUS mandatory
    DESCRIPTION
        "The source of the Dns Server IP Address of this
        port.
        
        fromDhcp(1) indicates that the DNS server IP
        address comes from the DHCP server.
        
        fromPortConfig(2) indicates that the DNS server IP
        address comes from the object
        voicePorfIfDnsServerAdress.
        
        fromSystemConfig(3) indicates that the DNS server
        IP address comes from DNS configuration for the
        system."
    ::= { voicePortOperDnsServerEntry 5 }

portJumboFrameTable OBJECT-TYPE
    SYNTAX SEQUENCE OF PortJumboFrameEntry
    ACCESS not-accessible
    STATUS mandatory
    DESCRIPTION
        "A list of port jumbo frame entries. The number of
        entries is determined by the number of ports in
        the system which support the Jumbo frame feature."
    ::= { portJumboFrameGrp 1 }

portJumboFrameEntry OBJECT-TYPE
    SYNTAX PortJumboFrameEntry
    ACCESS not-accessible
    STATUS mandatory
    DESCRIPTION
        "Entry containing the jumbo frame configuration
        for a particular port."
    INDEX { portJumboFrameModuleIndex, portJumboFramePortIndex }
    ::= { portJumboFrameTable 1 }

PortJumboFrameEntry ::= SEQUENCE {
    portJumboFrameModuleIndex INTEGER,
    portJumboFramePortIndex INTEGER,
    portJumboFrameEnable INTEGER
    }

portJumboFrameModuleIndex OBJECT-TYPE
    SYNTAX INTEGER(1..16)
    ACCESS read-only
    STATUS mandatory
    DESCRIPTION
        "An index value that uniquely identifies the
        module where this port is located."
    ::= { portJumboFrameEntry 1 }

portJumboFramePortIndex OBJECT-TYPE
    SYNTAX INTEGER(1..255)
    ACCESS read-only
    STATUS mandatory
    DESCRIPTION
        "An index value that uniquely identifies this port
        within a module. The value is determined by the
        location of the port on the module. Valid entries
        are 1 to the value of moduleNumPorts for this
        module."
    ::= { portJumboFrameEntry 2 }

portJumboFrameEnable OBJECT-TYPE
    SYNTAX INTEGER {
        enabled(1),
        disabled(2)
        }
    ACCESS read-write
    STATUS mandatory
    DESCRIPTION
        "Indicates the jumbo frame status of the port. If
        enabled, the port supports frame size greater than
        the standard ethernet frame size of 1518 bytes."
    ::= { portJumboFrameEntry 3 }

switchAccelerationModuleTable OBJECT-TYPE
    SYNTAX SEQUENCE OF SwitchAccelerationModuleEntry
    ACCESS not-accessible
    STATUS mandatory
    DESCRIPTION
        "This table contains a list of the modules for
        which the switch acceleration capability can be
        configured."
    ::= { switchAccelerationGrp 1 }

switchAccelerationModuleEntry OBJECT-TYPE
    SYNTAX SwitchAccelerationModuleEntry
    ACCESS not-accessible
    STATUS mandatory
    DESCRIPTION
        "A module for which switch acceleration can be
        configured."
    INDEX { switchAccelerationModuleIndex }
    ::= { switchAccelerationModuleTable 1 }

SwitchAccelerationModuleEntry ::= SEQUENCE {
    switchAccelerationModuleIndex INTEGER,
    switchAccelerationModuleEnable TruthValue
    }

switchAccelerationModuleIndex OBJECT-TYPE
    SYNTAX INTEGER(1..16)
    ACCESS read-only
    STATUS mandatory
    DESCRIPTION
        "The value of moduleIndex for the module where
        switch acceleration feature can be configured."
    ::= { switchAccelerationModuleEntry 1 }

switchAccelerationModuleEnable OBJECT-TYPE
    SYNTAX TruthValue
--    Rsyntax INTEGER {
--        true(1),
--        false(2)
--        }
    ACCESS read-write
    STATUS mandatory
    DESCRIPTION
        "Indicates whether switch acceleration is enabled
        on  this module or not.
        
        When this feature is enabled, the system will
        increase the switching bandwidth, but the
        ifAdminStatus of any port on this module can not
        be set to 'up'.
        
        If the ifAdminStatus of any port on this module is
        'up', this feature can not be enabled until
        ifAdminStatus of all ports on the module is set
        to 'down'."
    DEFVAL { false }
    ::= { switchAccelerationModuleEntry 2 }

configMode OBJECT-TYPE
    SYNTAX INTEGER {
        binary(1),
        text(2)
        }
    ACCESS read-write
    STATUS mandatory
    DESCRIPTION
        "Configuration mode to store the configuration
        information."
    DEFVAL { binary }
    ::= { configGrp 1 }

configTextFileLocation OBJECT-TYPE
    SYNTAX DisplayString(SIZE(0..255))
--    Rsyntax OCTET STRING(SIZE(0..255))
    ACCESS read-write
    STATUS mandatory
    DESCRIPTION
        "The location of the text configuration file
        which can be either NVRAM or a file in the
        FLASH file system. If the location is NVRAM,
        this object is a zero length octet string.
        Otherwise, the FLASH file should be specified
        in <device>:<filename> format. This object
        is only instantiated when configMode has
        the value of of text(2). "
    DEFVAL { ''H }
    ::= { configGrp 2 }

configWriteMem OBJECT-TYPE
    SYNTAX TruthValue
--    Rsyntax INTEGER {
--        true(1),
--        false(2)
--        }
    ACCESS read-write
    STATUS mandatory
    DESCRIPTION
        "When this object is set to true(1), the current
        configuration is saved in text format in the
        location specified by configTextFileLocation.
        This object is only instantiated when configMode
        has the value of text(2). When read,
        this object always returns false(2). "
    ::= { configGrp 3 }

configWriteMemStatus OBJECT-TYPE
    SYNTAX INTEGER {
        inProgress(1),
        succeeded(2),
        resourceUnavailable(3),
        badFileName(4),
        someOtherError(5)
        }
    ACCESS read-write
    STATUS mandatory
    DESCRIPTION
        "The status of the current or the most recently
        completed 'write memory' operation. The possible
        values are:
        
          inProgress - 'write' operation in progress;
        
          succeeded - the 'write' was successful (this
          value is also used when no write has been
          invoked since the last time the local system
          restarted);
        
          resourceUnavailable, -the 'write' failed because
          insufficeient resource was available.
        
          badFileName - the 'write' failed because the
          specified destination file was not found.
          This might be due to invalid FLASH device
          name or invalid file name.
        
          someOtherError - the 'write' failed for some
          other reason.
        
        This object is only instantiated when configMode
        has the value of text(2). "
    ::= { configGrp 4 }

lerAlarmOn TRAP-TYPE
-- Reverse mappable trap
    ENTERPRISE { iso(1) org(3) dod(6) internet(1) private(4) enterprises(1) cisco(9) workgroup(5) }
    VARIABLES {
        fddimibPORTSMTIndex, fddimibPORTIndex }
--  Status
--    mandatory
    DESCRIPTION
        "A lerAlarmOn trap signifies that the agent entity
        has detected that the fddimibPORTLerFlag object in
        the FDDI-SMT73-MIB (RFC 1512) has transitioned to
        the true(1) state for one of its ports.
        The generation of this trap can be controlled by
        the fddimibPORTLerAlarm object in the
        FDDI-SMT73-MIB for each port."
    ::= 1

lerAlarmOff TRAP-TYPE
-- Reverse mappable trap
    ENTERPRISE { iso(1) org(3) dod(6) internet(1) private(4) enterprises(1) cisco(9) workgroup(5) }
    VARIABLES {
        fddimibPORTSMTIndex, fddimibPORTIndex }
--  Status
--    mandatory
    DESCRIPTION
        "A lerAlarmOff trap signifies that the agent
        entity has detected that the fddimibPORTLerFlag
        object in the FDDI-SMT73-MIB (RFC 1512) has
        transitioned to the false(2) state for one of
        its ports. The generation of this trap can be
        controlled by the fddimibPORTLerAlarm object in
        the FDDI-SMT73-MIB for each port."
    ::= 2

moduleUp TRAP-TYPE
-- Reverse mappable trap
    ENTERPRISE { iso(1) org(3) dod(6) internet(1) private(4) enterprises(1) cisco(9) workgroup(5) }
    VARIABLES {
        moduleIndex, moduleType }
--  Status
--    mandatory
    DESCRIPTION
        "A moduleUp trap signifies that the agent entity
        has detected that the moduleStatus object in this
        MIB has transitioned to the ok(2) state for one of
        its modules.
        The generation of this trap can be controlled by
        the sysEnableModuleTraps object in this MIB."
    ::= 3

moduleDown TRAP-TYPE
-- Reverse mappable trap
    ENTERPRISE { iso(1) org(3) dod(6) internet(1) private(4) enterprises(1) cisco(9) workgroup(5) }
    VARIABLES {
        moduleIndex, moduleType }
--  Status
--    mandatory
    DESCRIPTION
        "A moduleDown trap signifies that the agent entity
        has detected that the moduleStatus object in this
        MIB has transitioned out of the ok(2) state for
        one of its modules.
        The generation of this trap can be controlled by
        the sysEnableModuleTraps object in this MIB."
    ::= 4

chassisAlarmOn TRAP-TYPE
-- Reverse mappable trap
    ENTERPRISE { iso(1) org(3) dod(6) internet(1) private(4) enterprises(1) cisco(9) workgroup(5) }
    VARIABLES {
        chassisTempAlarm, chassisMinorAlarm, chassisMajorAlarm }
--  Status
--    mandatory
    DESCRIPTION
        "A chassisAlarmOn trap signifies that the agent
        entity has detected the chassisTempAlarm,
        chassisMinorAlarm, or chassisMajorAlarm object in
        this MIB has transitioned to the on(2) state.
        The generation of this trap can be controlled by
        the sysEnableChassisTraps object in this MIB."
    ::= 5

chassisAlarmOff TRAP-TYPE
-- Reverse mappable trap
    ENTERPRISE { iso(1) org(3) dod(6) internet(1) private(4) enterprises(1) cisco(9) workgroup(5) }
    VARIABLES {
        chassisTempAlarm, chassisMinorAlarm, chassisMajorAlarm }
--  Status
--    mandatory
    DESCRIPTION
        "A chassisAlarmOff trap signifies that the agent
        entity has detected the chassisTempAlarm,
        chassisMinorAlarm, or chassisMajorAlarm object in
        this MIB has transitioned to the off(1) state.
        The generation of this trap can be controlled by
        the sysEnableChassisTraps object in this MIB."
    ::= 6

ipPermitDeniedTrap TRAP-TYPE
-- Reverse mappable trap
    ENTERPRISE { iso(1) org(3) dod(6) internet(1) private(4) enterprises(1) cisco(9) workgroup(5) }
    VARIABLES {
        ipPermitDeniedAddress, ipPermitDeniedAccess }
--  Status
--    mandatory
    DESCRIPTION
        "ipPermitDeniedTrap indicates that IP permit
        denied access happens. The generation of this
        trap can be controlled by the
        sysEnableIpPermitTraps object in this MIB."
    ::= 7

sysConfigChangeTrap TRAP-TYPE
-- Reverse mappable trap
    ENTERPRISE { iso(1) org(3) dod(6) internet(1) private(4) enterprises(1) cisco(9) workgroup(5) }
    VARIABLES {
        sysConfigChangeTime, sysConfigChangeInfo }
--  Status
--    mandatory
    DESCRIPTION
        "A sysConfigChange trap signifies that the system
        configuration in NVRAM is changed. The generation
        of this trap can be controlled by the
        sysEnableConfigTraps object in this MIB."
    ::= 9

tokenRingSoftErrExceededTrap TRAP-TYPE
-- Reverse mappable trap
    ENTERPRISE { iso(1) org(3) dod(6) internet(1) private(4) enterprises(1) cisco(9) workgroup(5) }
    VARIABLES {
        ringStationMacAddress, ifIndex, ifName }
--  Status
--    mandatory
    DESCRIPTION
        "This trap is generated when a station local to a
         token ring port exceeds its Soft Error Threshold
         within the configured interval."
    ::= 10

systemMiscGroup OBJECT IDENTIFIER ::= { ciscoStackMIBGroups 1 }
-- OBJECT-GROUP
--  Status
--    deprecated
--  Descr
--    A collection of objects providing information
--    about the miscellaneous system features.
--  objects
--    sysMgmtType, sysIpAddr, sysNetMask, sysBroadcast, 
--    sysAttachType, sysReset, sysBaudRate, sysInsertMode, 
--    sysClearMacTime, sysClearPortTime, sysEnableModem, 
--    sysEnableRedirects, sysArpAgingTime, sysCommunityRwa, 
--    sysCommunityRw, sysCommunityRo, sysIpVlan

systemTrapGroup OBJECT IDENTIFIER ::= { ciscoStackMIBGroups 2 }
-- OBJECT-GROUP
--  Status
--    deprecated
--  Descr
--    A collection of objects providing information
--    about the SNMP traps feature.
--  objects
--    sysTrapReceiverAddr, sysTrapReceiverType, sysTrapReceiverComm, 
--    sysEnableChassisTraps, sysEnableModuleTraps, 
--    sysEnableBridgeTraps, sysEnableRepeaterTraps

chassisGroup OBJECT IDENTIFIER ::= { ciscoStackMIBGroups 3 }
-- OBJECT-GROUP
--  Status
--    mandatory
--  Descr
--    A collection of objects providing information
--    about the chassis of the device.
--    
--    Implementation of this group is mandatory.
--  objects
--    chassisSysType, chassisBkplType, chassisPs1Type, 
--    chassisPs1Status, chassisPs1TestResult, chassisPs2Type, 
--    chassisPs2Status, chassisPs2TestResult, chassisFanStatus, 
--    chassisFanTestResult, chassisMinorAlarm, chassisMajorAlarm, 
--    chassisTempAlarm, chassisNumSlots

moduleGroup OBJECT IDENTIFIER ::= { ciscoStackMIBGroups 4 }
-- OBJECT-GROUP
--  Status
--    mandatory
--  Descr
--    A collection of objects providing information
--    about the modules on the device.
--    
--    Implementation of this group is mandatory.
--  objects
--    moduleIndex, moduleType, moduleStatus, moduleTestResult, 
--    moduleAction, moduleName, moduleNumPorts, modulePortStatus, 
--    moduleSubType, moduleSerialNumberString

portGroup OBJECT IDENTIFIER ::= { ciscoStackMIBGroups 5 }
-- OBJECT-GROUP
--  Status
--    deprecated
--  Descr
--    A collection of objects providing information
--    about the ports on the device.
--  objects
--    portModuleIndex, portIndex, portCrossIndex, portName, 
--    portType, portOperStatus, portCrossGroupIndex, 
--    portAdditionalStatus, portAdminSpeed, portDuplex, portIfIndex, 
--    portSpantreeFastStart, portAdminRxFlowControl, 
--    portOperRxFlowControl, portAdminTxFlowControl, 
--    portOperTxFlowControl, portMacControlTransmitFrames, 
--    portMacControlReceiveFrames, 
--    portMacControlPauseTransmitFrames, 
--    portMacControlPauseReceiveFrames, 
--    portMacControlUnknownProtocolFrames, portLinkFaultStatus

optionalSystemMiscGroup OBJECT IDENTIFIER ::= { ciscoStackMIBGroups 6 }
-- OBJECT-GROUP
--  Status
--    mandatory
--  Descr
--    A collection of objects providing information
--    about the miscellaneous system features.
--    
--    Implementation of this group is optional.
--  objects
--    sysConfigChangeTime, sysBannerMotd, sysConfigChangeInfo, 
--    sysConfigRegister, sysBootVariable, sysBootedImage

optionalSystemTrapGroup OBJECT IDENTIFIER ::= { ciscoStackMIBGroups 7 }
-- OBJECT-GROUP
--  Status
--    deprecated
--  Descr
--    A collection of objects providing information
--    about the SNMP traps feature.
--    
--    Implementation of this group is optional.
--  objects
--    sysEnableIpPermitTraps, sysEnableVmpsTraps, 
--    sysEnableConfigTraps, sysEnableEntityTrap, sysEnableStpxTrap

optionalChassisGroup OBJECT IDENTIFIER ::= { ciscoStackMIBGroups 8 }
-- OBJECT-GROUP
--  Status
--    deprecated
--  Descr
--    A collection of objects providing information
--    about the chassis of the device.
--  objects
--    chassisPs1TestResult, chassisPs2TestResult, 
--    chassisFanTestResult, chassisSlotConfig, chassisModel, 
--    chassisComponentIndex, chassisComponentType, 
--    chassisComponentSerialNumber, chassisComponentHwVersion, 
--    chassisComponentModel, chassisSerialNumberString

optionalModuleGroup OBJECT IDENTIFIER ::= { ciscoStackMIBGroups 9 }
-- OBJECT-GROUP
--  Status
--    mandatory
--  Descr
--    A collection of objects providing information
--    about the modules on the device.
--    
--    Implementation of this group is Optional.
--  objects
--    moduleTestResult, moduleModel, moduleHwVersion, 
--    moduleFwVersion, moduleSwVersion, moduleStandbyStatus, 
--    moduleIPAddress, moduleIPAddressVlan, moduleSubType2, 
--    moduleSlotNum

optionalPortGroup OBJECT IDENTIFIER ::= { ciscoStackMIBGroups 10 }
-- OBJECT-GROUP
--  Status
--    deprecated
--  Descr
--    A collection of objects providing information
--    about the ports on the device.
--    
--    Implementation of this group is Optional.
--  objects
--    portSecurityModuleIndex, portSecurityPortIndex, 
--    portSecurityAdminStatus, portSecurityOperStatus, 
--    portSecurityLastSrcAddr, portSecuritySecureSrcAddr, 
--    portChannelModuleIndex, portChannelPortIndex, 
--    portChannelPorts, portChannelAdminStatus, 
--    portChannelOperStatus, portChannelNeighbourDeviceId, 
--    portChannelNeighbourPortId, portChannelProtInPackets, 
--    portChannelProtOutPackets, portChannelIfIndex, 
--    portCpbModuleIndex, portCpbPortIndex, portCpbSpeed, 
--    portCpbDuplex, portCpbTrunkEncapsulationType, 
--    portCpbTrunkMode, portCpbChannel, portCpbBroadcastSuppression, 
--    portCpbFlowControl, portCpbSecurity, portCpbVlanMembership, 
--    portCpbPortfast, portTopNControlIndex, portTopNRateBase, 
--    portTopNType, portTopNMode, portTopNReportStatus, 
--    portTopNDuration, portTopNTimeRemaining, portTopNStartTime, 
--    portTopNRequestedSize, portTopNGrantedSize, portTopNOwner, 
--    portTopNStatus, portTopNIndex, portTopNModuleNumber, 
--    portTopNPortNumber, portTopNUtilization, portTopNIOOctets, 
--    portTopNIOPkts, portTopNIOBroadcast, portTopNIOMulticast, 
--    portTopNInErrors, portTopNBufferOverFlow

systemTrafficGroup OBJECT IDENTIFIER ::= { ciscoStackMIBGroups 11 }
-- OBJECT-GROUP
--  Status
--    mandatory
--  Descr
--    A collection of objects providing information
--    about the traffic meter feature.
--    
--    Implementation of this group is optional. If the
--    traffic meter feature is supported, the entire
--    group should be implemented.
--  objects
--    sysTrafficMeterType, sysTraffic, sysTrafficPeak, 
--    sysTrafficPeakTime, sysTrafficMeter, sysTrafficMeterPeak, 
--    sysTrafficMeterPeakTime

systemFddiGroup OBJECT IDENTIFIER ::= { ciscoStackMIBGroups 12 }
-- OBJECT-GROUP
--  Status
--    mandatory
--  Descr
--    A collection of objects providing information
--    about the FDDI ring feature.
--    
--    Implementation of this group is optional. If the
--    FDDI ring feature is supported, the entire group
--    should be implemented.
--  objects
--    sysFddiRingSMTIndex, sysFddiRingAddress, sysFddiRingNext

systemRmonGroup OBJECT IDENTIFIER ::= { ciscoStackMIBGroups 13 }
-- OBJECT-GROUP
--  Status
--    mandatory
--  Descr
--    A collection of objects providing information
--    about the extended RMON feature.
--    
--    Implementation of this group is optional. If the
--    extended RMON feature is supported, the entire
--    group should be implemented.
--  objects
--    sysEnableRmon, sysExtendedRmonVlanModeEnable, 
--    sysExtendedRmonNetflowPassword, sysExtendedRmonNetflowEnable, 
--    sysExtendedRmonVlanAgentEnable, sysExtendedRmonEnable

authenticationGroup OBJECT IDENTIFIER ::= { ciscoStackMIBGroups 14 }
-- OBJECT-GROUP
--  Status
--    deprecated
--  Descr
--    A collection of objects providing information
--    about the authentication features.
--    
--    Implementation of this group is optional. If the
--    authentication features are supported, the entire
--    group should be implemented.
--  objects
--    sysConsolePrimaryLoginAuthentication, 
--    sysConsolePrimaryEnableAuthentication, 
--    sysTelnetPrimaryLoginAuthentication, 
--    sysTelnetPrimaryEnableAuthentication, 
--    tacacsLoginAuthentication, tacacsEnableAuthentication, 
--    tacacsLocalLoginAuthentication, 
--    tacacsLocalEnableAuthentication, tacacsNumLoginAttempts, 
--    tacacsDirectedRequest, tacacsTimeout, tacacsAuthKey, 
--    tacacsServerAddr, tacacsServerType, radiusLoginAuthentication, 
--    radiusEnableAuthentication, radiusDeadtime, radiusAuthKey, 
--    radiusTimeout, radiusRetransmits, radiusServerAddr, 
--    radiusServerAuthPort, radiusServerType

tftpGroup OBJECT IDENTIFIER ::= { ciscoStackMIBGroups 15 }
-- OBJECT-GROUP
--  Status
--    mandatory
--  Descr
--    A collection of objects providing information
--    about the tftp upload/download features.
--    
--    Implementation of this group is optional. If the
--    tftp upload/download features are supported, the
--    entire group should be implemented.
--  objects
--    tftpHost, tftpFile, tftpModule, tftpAction, tftpResult

brouteEnableGroup OBJECT IDENTIFIER ::= { ciscoStackMIBGroups 16 }
-- OBJECT-GROUP
--  Status
--    mandatory
--  Descr
--    A collection of objects providing information
--    about the combined bridging/routing feature.
--    
--    Implementation of this group is optional. If the
--    combined bridging/routing feature is supported,
--    the group should be implemented.
--  objects
--    brouterPortModule, brouterPort, brouterEnableRip, 
--    brouterEnableSpantree, brouterEnableGiantCheck, 
--    brouterEnableIpFragmentation, brouterEnableUnreachables, 
--    brouterCamMode, brouterIpxSnapToEther, 
--    brouterIpx8023RawToFddi, brouterEthernetReceiveMax, 
--    brouterEthernetTransmitMax, brouterFddiReceiveMax, 
--    brouterFddiTransmitMax, brouterPortIpVlan, brouterPortIpAddr, 
--    brouterPortNetMask, brouterPortBroadcast, 
--    brouterPortBridgeVlan, brouterPortIpHelpers, 
--    brouterIpx8022ToEther, brouterEnableTransitEncapsulation, 
--    brouterEnableFddiCheck, brouterEnableAPaRT

filterGroup OBJECT IDENTIFIER ::= { ciscoStackMIBGroups 17 }
-- OBJECT-GROUP
--  Status
--    mandatory
--  Descr
--    A collection of objects providing information
--    about the port filtering feature.
--    
--    Implementation of this group is optional. If the
--    port filtering feature is supported, parts or all
--    of this group should be implemented.
--  objects
--    filterMacModule, filterMacPort, filterMacAddress, 
--    filterMacType, filterVendorModule, filterVendorPort, 
--    filterVendorId, filterVendorType, filterProtocolModule, 
--    filterProtocolPort, filterProtocolValue, filterProtocolType, 
--    filterTestModule, filterTestPort, filterTestIndex, 
--    filterTestType, filterTestOffset, filterTestValue, 
--    filterTestMask, filterPortModule, filterPort, 
--    filterPortComplex, filterPortBroadcastThrottle, 
--    filterPortBroadcastThreshold, filterPortBroadcastDiscards

monitorGroup OBJECT IDENTIFIER ::= { ciscoStackMIBGroups 18 }
-- OBJECT-GROUP
--  Status
--    deprecated
--  Descr
--    The collection of deprecated objects for
--     managing the Switched Port Analyzer (SPAN)
--     features.
--  objects
--    monitorSourceModule, monitorSourcePort, 
--    monitorDestinationModule, monitorDestinationPort, 
--    monitorDirection, monitorEnable, monitorAdminSourcePorts, 
--    monitorOperSourcePorts

vlanGroup OBJECT IDENTIFIER ::= { ciscoStackMIBGroups 19 }
-- OBJECT-GROUP
--  Status
--    deprecated
--  Descr
--    A collection of objects providing information
--    about the Virtual LAN features.
--    
--    Implementation of this group is optional.
--  objects
--    vlanIndex, vlanSpantreeEnable, vlanIfIndex, vlanPortModule, 
--    vlanPort, vlanPortVlan, vlanPortIslVlansAllowed, 
--    vlanPortSwitchLevel, vlanPortIslAdminStatus, 
--    vlanPortIslOperStatus, vlanPortIslPriorityVlans, 
--    vlanPortAdminStatus, vlanPortOperStatus

vmpsGroup OBJECT IDENTIFIER ::= { ciscoStackMIBGroups 20 }
-- OBJECT-GROUP
--  Status
--    mandatory
--  Descr
--    A collection of objects providing information
--    about the Vlan Membership Policy Server feature.
--    
--    Implementation of this group is optional. If the
--    Vlan Membership Policy Server feature is
--    supported, the entire group should be
--    implemented.
--  objects
--    vmpsAddr, vmpsType, vmpsAction, vmpsAccessed

tokenRingGroup OBJECT IDENTIFIER ::= { ciscoStackMIBGroups 21 }
-- OBJECT-GROUP
--  Status
--    mandatory
--  Descr
--    A collection of objects providing information
--    about the token ring features.
--    
--    Implementation of this group is optional. If the
--    token ring features are supported, the entire
--    group should be implemented.
--  objects
--    tokenRingModuleIndex, tokenRingPortIndex, 
--    tokenRingPortSetACbits, tokenRingPortMode, 
--    tokenRingPortEarlyTokenRel, tokenRingPortPriorityThresh, 
--    tokenRingPortPriorityMinXmit, tokenRingPortCfgLossThresh, 
--    tokenRingPortCfgLossInterval, tokenRingDripDistCrfMode, 
--    tokenRingDripAreReductionMode, tokenRingDripLocalNodeID, 
--    tokenRingDripLastRevision, tokenRingDripLastChangedRevision, 
--    tokenRingDripAdvertsReceived, tokenRingDripAdvertsTransmitted, 
--    tokenRingDripAdvertsProcessed, tokenRingDripInputQueueDrops, 
--    tokenRingDripOutputQueueDrops, tokenRingDripVlan, 
--    tokenRingDripLocalPortStatus, tokenRingDripRemotePortStatus, 
--    tokenRingDripRemotePortConfigured, 
--    tokenRingDripDistributedCrf, tokenRingDripBackupCrf, 
--    tokenRingDripOwnerNodeID

mcastGroup OBJECT IDENTIFIER ::= { ciscoStackMIBGroups 22 }
-- OBJECT-GROUP
--  Status
--    mandatory
--  Descr
--    A collection of objects providing information
--    about the multicast features.
--    
--    Implementation of this group is optional. If the
--    multicast features are supported, the entire group
--    should be implemented.
--  objects
--    mcastRouterModuleIndex, mcastRouterPortIndex, 
--    mcastRouterAdminStatus, mcastRouterOperStatus, 
--    mcastEnableCgmp, mcastEnableIgmp

dnsGroup OBJECT IDENTIFIER ::= { ciscoStackMIBGroups 23 }
-- OBJECT-GROUP
--  Status
--    mandatory
--  Descr
--    A collection of objects providing information
--    about the DNS feature.
--    
--    Implementation of this group is optional. If the
--    DNS feature is supported, the entire group
--    should be implemented.
--  objects
--    dnsEnable, dnsServerAddr, dnsServerType, dnsDomainName

syslogGroup OBJECT IDENTIFIER ::= { ciscoStackMIBGroups 24 }
-- OBJECT-GROUP
--  Status
--    mandatory
--  Descr
--    A collection of objects providing information
--    about the system log feature.
--    
--    Implementation of this group is optional. If the
--    system log feature is supported, the entire group
--    should be implemented.
--  objects
--    syslogServerAddr, syslogServerType, syslogConsoleEnable, 
--    syslogHostEnable, syslogMessageFacility, 
--    syslogMessageSeverity, syslogTimeStampOption

ntpGroup OBJECT IDENTIFIER ::= { ciscoStackMIBGroups 25 }
-- OBJECT-GROUP
--  Status
--    mandatory
--  Descr
--    A collection of objects providing information
--    about the network time protocol feature.
--    
--    Implementation of this group is optional. If the
--    network time protocol feature is supported, the
--    entire group should be implemented.
--  objects
--    ntpBcastClient, ntpBcastDelay, ntpClient, ntpServerAddress, 
--    ntpServerType, ntpSummertimeStatus, ntpSummerTimezoneName, 
--    ntpTimezoneName, ntpTimezoneOffsetHour, 
--    ntpTimezoneOffsetMinute

ipPermitGroup OBJECT IDENTIFIER ::= { ciscoStackMIBGroups 26 }
-- OBJECT-GROUP
--  Status
--    deprecated
--  Descr
--    A collection of objects providing information
--    about the ip permit list feature.
--    
--    Implementation of this group is optional. If the
--    ip permit list feature is supported, the entire
--    group should be implemented.
--  objects
--    ipPermitAddress, ipPermitMask, ipPermitEnable, ipPermitType, 
--    ipPermitDeniedAddress, ipPermitDeniedAccess, 
--    ipPermitDeniedTime

mdgGatewayGroup OBJECT IDENTIFIER ::= { ciscoStackMIBGroups 27 }
-- OBJECT-GROUP
--  Status
--    mandatory
--  Descr
--    A collection of objects providing information
--    about the multiple default gateway feature.
--    
--    Implementation of this group is optional. If the
--    multiple default gateway feature is supported,
--    the entire group should be implemented.
--  objects
--    mdgGatewayAddr, mdgGatewayType

traceRouteGroup OBJECT IDENTIFIER ::= { ciscoStackMIBGroups 28 }
-- OBJECT-GROUP
--  Status
--    mandatory
--  Descr
--    A collection of objects providing information
--    about the trace route feature.
--    
--    Implementation of this group is optional. If the
--    trace route feature is supported, the entire group
--    should be implemented.
--  objects
--    traceRouteMaxQueries, traceRouteQueryIndex, traceRouteHost, 
--    traceRouteQueryDNSEnable, traceRouteQueryWaitingTime, 
--    traceRouteQueryInitTTL, traceRouteQueryMaxTTL, 
--    traceRouteQueryUDPPort, traceRouteQueryPacketCount, 
--    traceRouteQueryPacketSize, traceRouteQueryTOS, 
--    traceRouteQueryResult, traceRouteQueryTime, 
--    traceRouteQueryOwner, traceRouteQueryStatus, 
--    traceRouteDataIndex, traceRouteDataGatewayName, 
--    traceRouteDataGatewayIp, traceRouteDataRtt, 
--    traceRouteDataHopCount, traceRouteDataErrors

deprecatedObjectGroup OBJECT IDENTIFIER ::= { ciscoStackMIBGroups 29 }
-- OBJECT-GROUP
--  Status
--    deprecated
--  Descr
--    A collection of objects that have been
--    deprecated.
--  objects
--    sysCommunityAccess, sysCommunityString, moduleHwHiVersion, 
--    moduleHwLoVersion, moduleFwHiVersion, moduleFwLoVersion, 
--    moduleSwHiVersion, moduleSwLoVersion, brouterCamAgingTime, 
--    chassisSerialNumber, moduleSerialNumber

ntpAuthenticationGroup OBJECT IDENTIFIER ::= { ciscoStackMIBGroups 30 }
-- OBJECT-GROUP
--  Status
--    mandatory
--  Descr
--    A collection of objects providing information
--    about the network time protocol authentication
--    feature.
--    
--    Implementation of this group is optional. If the
--    network time protocol authentication feature is
--    supported, the entire group should be
--    implemented.
--  objects
--    ntpServerPublicKey, ntpAuthenticationEnable, 
--    ntpAuthenticationPublicKey, ntpAuthenticationSecretKey, 
--    ntpAuthenticationTrustedMode, ntpAuthenticationType

tokenRingSoftErrorMonitorGroup OBJECT IDENTIFIER ::= { ciscoStackMIBGroups 31 }
-- OBJECT-GROUP
--  Status
--    mandatory
--  Descr
--    A collection of objects providing information
--    about the token ring port soft error monitoring
--    feature.
--    
--    Implementation of this group is optional. If the
--    token ring features are supported, the entire
--    group should be implemented.
--  objects
--    tokenRingPortSoftErrThresh, 
--    tokenRingPortSoftErrReportInterval, 
--    tokenRingPortSoftErrResetCounters, 
--    tokenRingPortSoftErrLastCounterReset, 
--    tokenRingPortSoftErrEnable

portCpbGroup1 OBJECT IDENTIFIER ::= { ciscoStackMIBGroups 32 }
-- OBJECT-GROUP
--  Status
--    mandatory
--  Descr
--    A collection of objects providing additional
--    information about the port capabilities on the
--    device.
--    
--    Implementation of this group is Optional.
--  objects
--    portCpbUdld

portSecurityGroup1 OBJECT IDENTIFIER ::= { ciscoStackMIBGroups 33 }
-- OBJECT-GROUP
--  Status
--    mandatory
--  Descr
--    A collection of objects providing additional
--    information for supporting port security feature
--    with the multiple secured source MAC addresses.
--    Implementation of this group is optional.
--  objects
--    portSecurityMaxSrcAddr, portSecurityAgingTime, 
--    portSecurityShutdownTimeOut, portSecurityViolationPolicy, 
--    portSecurityExtModuleIndex, portSecurityExtPortIndex, 
--    portSecurityExtSecureSrcAddr, portSecurityExtControlStatus

fileCopyGroup OBJECT IDENTIFIER ::= { ciscoStackMIBGroups 34 }
-- OBJECT-GROUP
--  Status
--    mandatory
--  Descr
--    A collection of objects providing information
--    about the tftp/rcp or local file upload/download
--    features.
--    
--    Implementation of this group is optional. If the
--    tftp upload/download features are supported, the
--    entire group should be implemented.
--  objects
--    fileCopyProtocol, fileCopyRemoteServer, fileCopySrcFileName, 
--    fileCopyDstFileName, fileCopyModuleNumber, fileCopyUserName, 
--    fileCopyAction, fileCopyResult, fileCopyResultRcpErrorMessage

optionalSystemMiscGroup1 OBJECT IDENTIFIER ::= { ciscoStackMIBGroups 35 }
-- OBJECT-GROUP
--  Status
--    mandatory
--  Descr
--    A collection of objects providing information
--    about the miscellaneous system features.
--    
--    Implementation of this group is optional.
--  objects
--    sysStartupConfigSource, sysStartupConfigSourceFile, 
--    sysConfigSupervisorModuleNo, sysStandbyPortEnable

ipPermitGroup1 OBJECT IDENTIFIER ::= { ciscoStackMIBGroups 36 }
-- OBJECT-GROUP
--  Status
--    mandatory
--  Descr
--    A collection of objects providing additional
--    information for allowing the ip permit host with
--    the specified access type.
--    
--    Implementation of this group is optional. If the
--    ip permit list enhancement feature is supported,
--    this group should be implemented.
--  objects
--    ipPermitAccessType

optionalSystemMiscGroup2 OBJECT IDENTIFIER ::= { ciscoStackMIBGroups 37 }
-- OBJECT-GROUP
--  Status
--    deprecated
--  Descr
--    A collection of objects providing information
--    about the miscellaneous system features.
--    
--    Implementation of this group is optional.
--  objects
--    sysPortFastBpduGuard, sysErrDisableTimeoutEnable, 
--    sysErrDisableTimeoutInterval, sysTrafficMonitorHighWaterMark, 
--    sysHighAvailabilityEnable, 
--    sysHighAvailabilityVersioningEnable, 
--    sysHighAvailabilityOperStatus, 
--    sysHighAvailabilityNotRunningReason

filterGroup1 OBJECT IDENTIFIER ::= { ciscoStackMIBGroups 38 }
-- OBJECT-GROUP
--  Status
--    mandatory
--  Descr
--    A collection of objects providing information
--    about the port filtering feature.
--    
--    Implementation of this group is optional. If the
--    port filtering feature is supported, parts or all
--    of this group should be implemented.
--  objects
--    filterPortBroadcastThresholdFraction

mcastGroup1 OBJECT IDENTIFIER ::= { ciscoStackMIBGroups 39 }
-- OBJECT-GROUP
--  Status
--    mandatory
--  Descr
--    A collection of objects providing information
--    about the multicast features.
--    
--    Implementation of this group is optional. If the
--    multicast features are supported, the entire group
--    should be implemented.
--  objects
--    mcastEnableRgmp

portGroup1 OBJECT IDENTIFIER ::= { ciscoStackMIBGroups 40 }
-- OBJECT-GROUP
--  Status
--    mandatory
--  Descr
--    A collection of objects providing information
--    about the ports on the device.
--    
--    Implementation of this group is optional.
--  objects
--    portAdditionalOperStatus, portEntPhysicalIndex

chassisGroup1 OBJECT IDENTIFIER ::= { ciscoStackMIBGroups 41 }
-- OBJECT-GROUP
--  Status
--    mandatory
--  Descr
--    A collection of objects providing information
--    about the chassis of the device.
--    
--    This group must be implemented by systems that can
--    have 3 or more power supplies.
--  objects
--    chassisPs3Type, chassisPs3Status, chassisPs3TestResult, 
--    chassisPEMInstalled

moduleGroup1 OBJECT IDENTIFIER ::= { ciscoStackMIBGroups 42 }
-- OBJECT-GROUP
--  Status
--    mandatory
--  Descr
--    A collection of objects providing information
--    about the modules on the device.
--    
--    Implementation of this group is mandatory.
--  objects
--    moduleEntPhysicalIndex

portCpbGroup2 OBJECT IDENTIFIER ::= { ciscoStackMIBGroups 43 }
-- OBJECT-GROUP
--  Status
--    mandatory
--  Descr
--    A collection of objects providing additional
--    information about the port capabilities on the
--    device.
--    
--    Implementation of this group is Optional.
--  objects
--    portCpbSpan

voiceGroup OBJECT IDENTIFIER ::= { ciscoStackMIBGroups 44 }
-- OBJECT-GROUP
--  Status
--    mandatory
--  Descr
--    A collection of objects providing information
--     about the voice ports on the device.
--    
--     Implemetation of this group is Optional
--  objects
--    voicePortIfDHCPEnabled, voicePortIfIpAddress, 
--    voicePortIfIpNetMask, voicePortIfTftpServerAddress, 
--    voicePortIfGatewayAddress, voicePortIfDnsServerAddress, 
--    voicePortIfDnsDomain, voicePortIfOperDnsDomain, 
--    voicePortCallManagerIpAddr, voicePortOperDnsServerIpAddr, 
--    voicePortOperDnsServerSource

portGroup2 OBJECT IDENTIFIER ::= { ciscoStackMIBGroups 45 }
-- OBJECT-GROUP
--  Status
--    mandatory
--  Descr
--    A collection of objects providing information
--    about the ports on the device.
--    
--    Implementation of this group is optional.
--  objects
--    portInlinePowerDetect

vlanGroup1 OBJECT IDENTIFIER ::= { ciscoStackMIBGroups 46 }
-- OBJECT-GROUP
--  Status
--    deprecated
--  Descr
--    A collection of objects providing information
--    about the Virtual LAN features.
--    
--    Implementation of this group is optional. If the
--    Virtual LAN features are supported, the entire
--    group should be implemented.
--  objects
--    vlanPortAuxiliaryVlan

portCpbGroup3 OBJECT IDENTIFIER ::= { ciscoStackMIBGroups 47 }
-- OBJECT-GROUP
--  Status
--    mandatory
--  Descr
--    A collection of objects providing additional
--    information about the port capabilities on the
--    device.
--    
--    Implementation of this group is Optional.
--  objects
--    portCpbInlinePower, portCpbAuxiliaryVlan

moduleGroup2 OBJECT IDENTIFIER ::= { ciscoStackMIBGroups 48 }
-- OBJECT-GROUP
--  Status
--    mandatory
--  Descr
--    A collection of objects providing information
--    about the modules on the device.
--    
--    Implementation of this group is mandatory.
--  objects
--    moduleAdditionalStatus

switchAccelerationModuleGroup OBJECT IDENTIFIER ::= { ciscoStackMIBGroups 49 }
-- OBJECT-GROUP
--  Status
--    mandatory
--  Descr
--    A collection of objects providing information
--    about the modules switch acceleration
--    configuration.
--    
--    Implementation of this group is mandatory if the
--    module switch acceleration feature is supported.
--  objects
--    switchAccelerationModuleIndex, switchAccelerationModuleEnable

optionalSystemMiscGroup3 OBJECT IDENTIFIER ::= { ciscoStackMIBGroups 50 }
-- OBJECT-GROUP
--  Status
--    mandatory
--  Descr
--    A collection of objects providing information
--    about the miscellaneous system features.
--    The sysExtendedRmonNetflowModuleMask object is
--    optional object and it will only be supported in
--    the platform supporting multiple NAM (Network
--    Analysis Module) cards.
--    Implementation of this group is optional.
--  objects
--    sysExtendedRmonNetflowModuleMask

optionalSystemMiscGroup4 OBJECT IDENTIFIER ::= { ciscoStackMIBGroups 51 }
-- OBJECT-GROUP
--  Status
--    mandatory
--  Descr
--    A collection of objects providing information
--    about the miscellaneous system features.
--  objects
--    sshPublicKeySize

vlanTrunkMappingGroup OBJECT IDENTIFIER ::= { ciscoStackMIBGroups 52 }
-- OBJECT-GROUP
--  Status
--    mandatory
--  Descr
--    A collection of objects providing information
--    about the trunk VLAN to VLAN associations.
--    
--    Implementation of this group is mandatory if the
--    trunk VLAN to VLAN association feature is
--    supported on the device.
--  objects
--    vlanTrunkMappingMax, vlanTrunkMappingToVlan, 
--    vlanTrunkMappingType, vlanTrunkMappingOper, 
--    vlanTrunkMappingStatus

portJumboFrameGroup OBJECT IDENTIFIER ::= { ciscoStackMIBGroups 53 }
-- OBJECT-GROUP
--  Status
--    mandatory
--  Descr
--    A collection of objects providing information
--    about the port jumbo frame feature on the device.
--    
--    Implementation of this group is mandatory if the
--    port jumbo frame feature is supported on the
--    device.
--  objects
--    portJumboFrameModuleIndex, portJumboFramePortIndex, 
--    portJumboFrameEnable

portCpbGroup4 OBJECT IDENTIFIER ::= { ciscoStackMIBGroups 54 }
-- OBJECT-GROUP
--  Status
--    mandatory
--  Descr
--    A collection of objects providing additional
--    information about the port capabilities on the
--    device.
--    Implementation of this group is Optional.
--  objects
--    portCpbCosRewrite, portCpbTosRewrite, portCpbCopsGrouping

fileCopyGroup2 OBJECT IDENTIFIER ::= { ciscoStackMIBGroups 55 }
-- OBJECT-GROUP
--  Status
--    mandatory
--  Descr
--    A collection of objects providing additional
--    information about tftp/rcp or local file
--    upload/download features.
--    
--    Implementation of this group is optional.
--  objects
--    fileCopyRuntimeConfigPart

systemRmonGroup2 OBJECT IDENTIFIER ::= { ciscoStackMIBGroups 56 }
-- OBJECT-GROUP
--  Status
--    mandatory
--  Descr
--    A collection of object providing RMON max memory
--     usage control.
--  objects
--    sysMaxRmonMemory

filterGroup2 OBJECT IDENTIFIER ::= { ciscoStackMIBGroups 57 }
-- OBJECT-GROUP
--  Status
--    mandatory
--  Descr
--    A collection of objects providing information
--    about the unicast/multicast port filtering
--    feature.
--  objects
--    filterPortSuppressionOption

optionalSystemMiscGroup5 OBJECT IDENTIFIER ::= { ciscoStackMIBGroups 58 }
-- OBJECT-GROUP
--  Status
--    mandatory
--  Descr
--    A collection of objects providing information
--    about the miscellaneous system features.
--  objects
--    sysMacReductionAdminEnable, sysMacReductionOperEnable

syslogGroup2 OBJECT IDENTIFIER ::= { ciscoStackMIBGroups 59 }
-- OBJECT-GROUP
--  Status
--    mandatory
--  Descr
--    A collection of object providing control about
--    whether the syslog messages should be sent to
--    telnet sessions.
--    
--    Implementation of this group is optional.
--  objects
--    syslogTelnetEnable

systemStatusGroup OBJECT IDENTIFIER ::= { ciscoStackMIBGroups 60 }
-- OBJECT-GROUP
--  Status
--    mandatory
--  Descr
--    A collection of object providing the system
--     LED status.
--    
--    Implementation of this group is optional.
--  objects
--    sysStatus

configurationGroup OBJECT IDENTIFIER ::= { ciscoStackMIBGroups 61 }
-- OBJECT-GROUP
--  Status
--    mandatory
--  Descr
--    A collection of object providing the information
--    about the configuration mode to store the
--    configuration information.
--    
--    Implementation of this group is optional.
--  objects
--    configMode, configTextFileLocation, configWriteMem, 
--    configWriteMemStatus

filterGroup3 OBJECT IDENTIFIER ::= { ciscoStackMIBGroups 62 }
-- OBJECT-GROUP
--  Status
--    mandatory
--  Descr
--    A collection of objects providing additional
--    information about  about the Broadcast
--    Suppression Violation for port filtering feature.
--    
--    Implementation of this group is optional.
--  objects
--    filterPortSuppressionViolation

portGroup3 OBJECT IDENTIFIER ::= { ciscoStackMIBGroups 63 }
-- OBJECT-GROUP
--  Status
--    mandatory
--  Descr
--    A collection of objects providing additional
--    information about the ports on the device.
--    
--    Implementation of this group is optional.
--  objects
--    portErrDisableTimeOutEnable

portCpbGroup5 OBJECT IDENTIFIER ::= { ciscoStackMIBGroups 64 }
-- OBJECT-GROUP
--  Status
--    mandatory
--  Descr
--    A collection of objects providing additional
--    information about the port capabilities on the
--    device.
--    
--    Implementation of this group is Optional.
--  objects
--    portCpbDot1x, portCpbIgmpFilter

authenticationGroup1 OBJECT IDENTIFIER ::= { ciscoStackMIBGroups 65 }
-- OBJECT-GROUP
--  Status
--    deprecated
--  Descr
--    A collection of objects providing information
--    about the authentication features.
--    
--    Implementation of this group is optional.
--  objects
--    tacacsDirectedRequest, tacacsAuthKey, tacacsServerAddr, 
--    tacacsServerType, radiusDeadtime, radiusAuthKey, 
--    radiusTimeout, radiusRetransmits, radiusServerAddr, 
--    radiusServerAuthPort, radiusServerType

systemMiscGroup1 OBJECT IDENTIFIER ::= { ciscoStackMIBGroups 66 }
-- OBJECT-GROUP
--  Status
--    mandatory
--  Descr
--    A collection of objects providing information
--    about the miscellaneous system features.
--  objects
--    sysMgmtType, sysAttachType, sysBaudRate, sysInsertMode, 
--    sysEnableModem, sysEnableRedirects, sysArpAgingTime, 
--    sysCommunityRwa, sysCommunityRw, sysCommunityRo, sysIpVlan

systemTrapGroup1 OBJECT IDENTIFIER ::= { ciscoStackMIBGroups 67 }
-- OBJECT-GROUP
--  Status
--    deprecated
--  Descr
--    A collection of objects providing information
--    about the SNMP traps feature.
--  objects
--    sysEnableChassisTraps, sysEnableModuleTraps, 
--    sysEnableBridgeTraps, sysEnableRepeaterTraps

optionalSystemMiscGroup6 OBJECT IDENTIFIER ::= { ciscoStackMIBGroups 68 }
-- OBJECT-GROUP
--  Status
--    mandatory
--  Descr
--    A collection of objects providing information
--    about the miscellaneous system features.
--    
--    Implementation of this group is optional.
--  objects
--    sysErrDisableTimeoutEnable, sysErrDisableTimeoutInterval, 
--    sysTrafficMonitorHighWaterMark, sysHighAvailabilityEnable, 
--    sysHighAvailabilityVersioningEnable, 
--    sysHighAvailabilityOperStatus, 
--    sysHighAvailabilityNotRunningReason

optionalChassisGroup1 OBJECT IDENTIFIER ::= { ciscoStackMIBGroups 69 }
-- OBJECT-GROUP
--  Status
--    mandatory
--  Descr
--    A collection of objects providing information
--    about the chassis of the device.
--  objects
--    chassisPs1TestResult, chassisPs2TestResult, 
--    chassisFanTestResult, chassisSlotConfig, chassisModel

portGroup4 OBJECT IDENTIFIER ::= { ciscoStackMIBGroups 70 }
-- OBJECT-GROUP
--  Status
--    mandatory
--  Descr
--    A collection of objects providing information
--    about the ports on the device.
--  objects
--    portModuleIndex, portIndex, portCrossIndex, portName, 
--    portType, portOperStatus, portCrossGroupIndex, 
--    portAdditionalStatus, portAdminSpeed, portDuplex, portIfIndex, 
--    portAdminRxFlowControl, portOperRxFlowControl, 
--    portAdminTxFlowControl, portOperTxFlowControl, 
--    portMacControlTransmitFrames, portMacControlReceiveFrames, 
--    portMacControlPauseTransmitFrames, 
--    portMacControlPauseReceiveFrames, 
--    portMacControlUnknownProtocolFrames, portLinkFaultStatus

vlanGroup2 OBJECT IDENTIFIER ::= { ciscoStackMIBGroups 71 }
-- OBJECT-GROUP
--  Status
--    mandatory
--  Descr
--    A collection of objects providing information
--    about the Virtual LAN features.
--    
--    Implementation of this group is optional.
--  objects
--    vlanPortModule, vlanPort, vlanPortVlan, 
--    vlanPortIslVlansAllowed, vlanPortSwitchLevel, 
--    vlanPortIslAdminStatus, vlanPortIslOperStatus, 
--    vlanPortIslPriorityVlans, vlanPortAdminStatus, 
--    vlanPortOperStatus

ipPermitGroup2 OBJECT IDENTIFIER ::= { ciscoStackMIBGroups 72 }
-- OBJECT-GROUP
--  Status
--    mandatory
--  Descr
--    A collection of objects providing information
--    about the ip permit list feature.
--    
--    Implementation of this group is optional. If the
--    ip permit list feature is supported, the entire
--    group should be implemented.
--  objects
--    ipPermitAddress, ipPermitMask, ipPermitType, 
--    ipPermitDeniedAddress, ipPermitDeniedAccess, 
--    ipPermitDeniedTime, ipPermitAccessTypeEnable

optionalPortGroup1 OBJECT IDENTIFIER ::= { ciscoStackMIBGroups 73 }
-- OBJECT-GROUP
--  Status
--    mandatory
--  Descr
--    A collection of objects providing information
--    about the ports on the device.
--    
--    Implementation of this group is Optional.
--  objects
--    portSecurityModuleIndex, portSecurityPortIndex, 
--    portSecurityAdminStatus, portSecurityOperStatus, 
--    portSecurityLastSrcAddr, portSecuritySecureSrcAddr, 
--    portCpbModuleIndex, portCpbPortIndex, portCpbSpeed, 
--    portCpbDuplex, portCpbTrunkEncapsulationType, 
--    portCpbTrunkMode, portCpbChannel, portCpbBroadcastSuppression, 
--    portCpbFlowControl, portCpbSecurity, portCpbVlanMembership, 
--    portCpbPortfast, portTopNControlIndex, portTopNRateBase, 
--    portTopNType, portTopNMode, portTopNReportStatus, 
--    portTopNDuration, portTopNTimeRemaining, portTopNStartTime, 
--    portTopNRequestedSize, portTopNGrantedSize, portTopNOwner, 
--    portTopNStatus, portTopNIndex, portTopNModuleNumber, 
--    portTopNPortNumber, portTopNUtilization, portTopNIOOctets, 
--    portTopNIOPkts, portTopNIOBroadcast, portTopNIOMulticast, 
--    portTopNInErrors, portTopNBufferOverFlow

optionalSystemTrapGroup1 OBJECT IDENTIFIER ::= { ciscoStackMIBGroups 74 }
-- OBJECT-GROUP
--  Status
--    mandatory
--  Descr
--    A collection of objects providing information
--    about the SNMP traps feature.
--    
--    Implementation of this group is optional.
--  objects
--    sysEnableIpPermitTraps, sysEnableVmpsTraps, 
--    sysEnableConfigTraps, sysEnableEntityTrap

authenticationGroup2 OBJECT IDENTIFIER ::= { ciscoStackMIBGroups 75 }
-- OBJECT-GROUP
--  Status
--    mandatory
--  Descr
--    A collection of objects providing information
--    about the authentication features.
--    
--    Implementation of this group is optional.
--  objects
--    tacacsDirectedRequest, tacacsAuthKey, tacacsServerAddr, 
--    tacacsServerType, radiusDeadtime, radiusAuthKey, 
--    radiusTimeout, radiusRetransmits

systemTrapGroup2 OBJECT IDENTIFIER ::= { ciscoStackMIBGroups 76 }
-- OBJECT-GROUP
--  Status
--    mandatory
--  Descr
--    A collection of objects providing information
--    about the SNMP traps feature.
--  objects
--    sysEnableChassisTraps, sysEnableModuleTraps, 
--    sysEnableRepeaterTraps

ipPermitGroup3 OBJECT IDENTIFIER ::= { ciscoStackMIBGroups 78 }
-- OBJECT-GROUP
--  Status
--    mandatory
--  Descr
--    A collection of objects providing configuration 
--    information on ip permit connection limit for a 
--    specific host.
--  objects
--    ipPermitTelnetConnectLimit, ipPermitSshConnectLimit

notificationGroup OBJECT IDENTIFIER ::= { ciscoStackMIBGroups 77 }
-- NOTIFICATION-GROUP
--  Status
--    mandatory
--  Descr
--    A collection of notifications supported on the device.
--  notifications
--    lerAlarmOn, lerAlarmOff, moduleUp, moduleDown, chassisAlarmOn, 
--    chassisAlarmOff, ipPermitDeniedTrap, sysConfigChangeTrap, 
--    tokenRingSoftErrExceededTrap

ciscoStackgMIBCompliance OBJECT IDENTIFIER ::= { ciscoStackMIBCompliances 1 }
-- MODULE-COMPLIANCE
--  Status
--    deprecated
--  Descr
--    The compliance statement for entities which
--     implement the Cisco stack MIB.
--  Module
--    >>current<<
--   MandGroup
--    systemMiscGroup
--   MandGroup
--    systemTrapGroup
--   MandGroup
--    chassisGroup
--   MandGroup
--    moduleGroup
--   MandGroup
--    portGroup
--   OptGroup
--    optionalSystemMiscGroup
--   OptGroup
--    optionalSystemTrapGroup
--   OptGroup
--    optionalChassisGroup
--   OptGroup
--    optionalModuleGroup
--   OptGroup
--    optionalPortGroup
--   OptGroup
--    systemTrafficGroup
--   OptGroup
--    systemFddiGroup
--   OptGroup
--    systemRmonGroup
--   OptGroup
--    authenticationGroup
--   OptGroup
--    tftpGroup
--   OptGroup
--    brouteEnableGroup
--   OptGroup
--    filterGroup
--   OptGroup
--    monitorGroup
--   OptGroup
--    vlanGroup
--   OptGroup
--    vmpsGroup
--   OptGroup
--    tokenRingGroup
--   OptGroup
--    mcastGroup
--   OptGroup
--    dnsGroup
--   OptGroup
--    syslogGroup
--   OptGroup
--    ntpGroup
--   OptGroup
--    ipPermitGroup
--   OptGroup
--    mdgGatewayGroup
--   OptGroup
--    traceRouteGroup
--   OptGroup
--    ntpAuthenticationGroup
--   OptGroup
--    tokenRingSoftErrorMonitorGroup
--   OptGroup
--    portCpbGroup1
--   OptGroup
--    portSecurityGroup1
--   OptGroup
--    fileCopyGroup
--   OptGroup
--    optionalSystemMiscGroup1

ciscoStackgMIBCompliance2 OBJECT IDENTIFIER ::= { ciscoStackMIBCompliances 2 }
-- MODULE-COMPLIANCE
--  Status
--    deprecated
--  Descr
--    The compliance statement for entities which
--    implement the Cisco stack MIB.
--  Module
--    >>current<<
--   MandGroup
--    systemMiscGroup
--   MandGroup
--    systemTrapGroup
--   MandGroup
--    chassisGroup
--   MandGroup
--    moduleGroup
--   MandGroup
--    portGroup
--   OptGroup
--    optionalSystemMiscGroup
--   OptGroup
--    optionalSystemTrapGroup
--   OptGroup
--    optionalChassisGroup
--   OptGroup
--    optionalModuleGroup
--   OptGroup
--    optionalPortGroup
--   OptGroup
--    systemTrafficGroup
--   OptGroup
--    systemFddiGroup
--   OptGroup
--    systemRmonGroup
--   OptGroup
--    authenticationGroup
--   OptGroup
--    tftpGroup
--   OptGroup
--    brouteEnableGroup
--   OptGroup
--    filterGroup
--   OptGroup
--    monitorGroup
--   OptGroup
--    vlanGroup
--   OptGroup
--    vmpsGroup
--   OptGroup
--    tokenRingGroup
--   OptGroup
--    mcastGroup
--   OptGroup
--    dnsGroup
--   OptGroup
--    syslogGroup
--   OptGroup
--    ntpGroup
--   OptGroup
--    ipPermitGroup
--   OptGroup
--    mdgGatewayGroup
--   OptGroup
--    traceRouteGroup
--   OptGroup
--    ntpAuthenticationGroup
--   OptGroup
--    tokenRingSoftErrorMonitorGroup
--   OptGroup
--    portCpbGroup1
--   OptGroup
--    portSecurityGroup1
--   OptGroup
--    fileCopyGroup
--   OptGroup
--    optionalSystemMiscGroup1
--   OptGroup
--    ipPermitGroup1
--   OptGroup
--    optionalSystemMiscGroup2
--   OptGroup
--    filterGroup1
--   OptGroup
--    mcastGroup1
--   OptGroup
--    portGroup1
--   OptGroup
--    chassisGroup1
--   OptGroup
--    moduleGroup1
--   OptGroup
--    portCpbGroup2

ciscoStackgMIBCompliance3 OBJECT IDENTIFIER ::= { ciscoStackMIBCompliances 3 }
-- MODULE-COMPLIANCE
--  Status
--    deprecated
--  Descr
--    The compliance statement for entities which
--    implement the Cisco stack MIB.
--  Module
--    >>current<<
--   MandGroup
--    systemMiscGroup
--   MandGroup
--    systemTrapGroup
--   MandGroup
--    chassisGroup
--   MandGroup
--    moduleGroup
--   MandGroup
--    portGroup
--   OptGroup
--    optionalSystemMiscGroup
--   OptGroup
--    optionalSystemTrapGroup
--   OptGroup
--    optionalChassisGroup
--   OptGroup
--    optionalModuleGroup
--   OptGroup
--    optionalPortGroup
--   OptGroup
--    systemTrafficGroup
--   OptGroup
--    systemFddiGroup
--   OptGroup
--    systemRmonGroup
--   OptGroup
--    authenticationGroup
--   OptGroup
--    tftpGroup
--   OptGroup
--    brouteEnableGroup
--   OptGroup
--    filterGroup
--   OptGroup
--    monitorGroup
--   OptGroup
--    vlanGroup
--   OptGroup
--    vmpsGroup
--   OptGroup
--    tokenRingGroup
--   OptGroup
--    mcastGroup
--   OptGroup
--    dnsGroup
--   OptGroup
--    syslogGroup
--   OptGroup
--    ntpGroup
--   OptGroup
--    ipPermitGroup
--   OptGroup
--    mdgGatewayGroup
--   OptGroup
--    traceRouteGroup
--   OptGroup
--    ntpAuthenticationGroup
--   OptGroup
--    tokenRingSoftErrorMonitorGroup
--   OptGroup
--    portCpbGroup1
--   OptGroup
--    portSecurityGroup1
--   OptGroup
--    fileCopyGroup
--   OptGroup
--    optionalSystemMiscGroup1
--   OptGroup
--    ipPermitGroup1
--   OptGroup
--    optionalSystemMiscGroup2
--   OptGroup
--    filterGroup1
--   OptGroup
--    mcastGroup1
--   OptGroup
--    portGroup1
--   OptGroup
--    chassisGroup1
--   OptGroup
--    moduleGroup1
--   OptGroup
--    portCpbGroup2
--   OptGroup
--    voiceGroup
--   OptGroup
--    moduleGroup2
--   OptGroup
--    portCpbGroup3
--   OptGroup
--    vlanGroup1
--   OptGroup
--    portGroup2
--   OptGroup
--    switchAccelerationModuleGroup
--   OptGroup
--    optionalSystemMiscGroup3

ciscoStackgMIBCompliance4 OBJECT IDENTIFIER ::= { ciscoStackMIBCompliances 4 }
-- MODULE-COMPLIANCE
--  Status
--    deprecated
--  Descr
--    The compliance statement for entities which
--    implement the Cisco stack MIB.
--  Module
--    >>current<<
--   MandGroup
--    systemMiscGroup
--   MandGroup
--    systemTrapGroup
--   MandGroup
--    chassisGroup
--   MandGroup
--    moduleGroup
--   MandGroup
--    portGroup
--   OptGroup
--    optionalSystemMiscGroup
--   OptGroup
--    optionalSystemTrapGroup
--   OptGroup
--    optionalChassisGroup
--   OptGroup
--    optionalModuleGroup
--   OptGroup
--    optionalPortGroup
--   OptGroup
--    systemTrafficGroup
--   OptGroup
--    systemFddiGroup
--   OptGroup
--    systemRmonGroup
--   OptGroup
--    authenticationGroup
--   OptGroup
--    tftpGroup
--   OptGroup
--    brouteEnableGroup
--   OptGroup
--    filterGroup
--   OptGroup
--    monitorGroup
--   OptGroup
--    vlanGroup
--   OptGroup
--    vmpsGroup
--   OptGroup
--    tokenRingGroup
--   OptGroup
--    mcastGroup
--   OptGroup
--    dnsGroup
--   OptGroup
--    syslogGroup
--   OptGroup
--    ntpGroup
--   OptGroup
--    ipPermitGroup
--   OptGroup
--    mdgGatewayGroup
--   OptGroup
--    traceRouteGroup
--   OptGroup
--    ntpAuthenticationGroup
--   OptGroup
--    tokenRingSoftErrorMonitorGroup
--   OptGroup
--    portCpbGroup1
--   OptGroup
--    portSecurityGroup1
--   OptGroup
--    fileCopyGroup
--   OptGroup
--    optionalSystemMiscGroup1
--   OptGroup
--    ipPermitGroup1
--   OptGroup
--    optionalSystemMiscGroup2
--   OptGroup
--    filterGroup1
--   OptGroup
--    mcastGroup1
--   OptGroup
--    portGroup1
--   OptGroup
--    chassisGroup1
--   OptGroup
--    moduleGroup1
--   OptGroup
--    portCpbGroup2
--   OptGroup
--    voiceGroup
--   OptGroup
--    moduleGroup2
--   OptGroup
--    portCpbGroup3
--   OptGroup
--    vlanGroup1
--   OptGroup
--    portGroup2
--   OptGroup
--    switchAccelerationModuleGroup
--   OptGroup
--    optionalSystemMiscGroup3
--   OptGroup
--    optionalSystemMiscGroup4
--   OptGroup
--    vlanTrunkMappingGroup
--   OptGroup
--    portJumboFrameGroup
--   OptGroup
--    portCpbGroup4

ciscoStackgMIBCompliance5 OBJECT IDENTIFIER ::= { ciscoStackMIBCompliances 5 }
-- MODULE-COMPLIANCE
--  Status
--    deprecated
--  Descr
--    The compliance statement for entities which
--    implement the Cisco stack MIB.
--  Module
--    >>current<<
--   MandGroup
--    systemMiscGroup
--   MandGroup
--    systemTrapGroup
--   MandGroup
--    chassisGroup
--   MandGroup
--    moduleGroup
--   MandGroup
--    portGroup
--   OptGroup
--    optionalSystemMiscGroup
--   OptGroup
--    optionalSystemTrapGroup
--   OptGroup
--    optionalChassisGroup
--   OptGroup
--    optionalModuleGroup
--   OptGroup
--    optionalPortGroup
--   OptGroup
--    systemTrafficGroup
--   OptGroup
--    systemFddiGroup
--   OptGroup
--    systemRmonGroup
--   OptGroup
--    tftpGroup
--   OptGroup
--    brouteEnableGroup
--   OptGroup
--    filterGroup
--   OptGroup
--    vlanGroup
--   OptGroup
--    vmpsGroup
--   OptGroup
--    tokenRingGroup
--   OptGroup
--    mcastGroup
--   OptGroup
--    dnsGroup
--   OptGroup
--    syslogGroup
--   OptGroup
--    ntpGroup
--   OptGroup
--    ipPermitGroup
--   OptGroup
--    mdgGatewayGroup
--   OptGroup
--    traceRouteGroup
--   OptGroup
--    ntpAuthenticationGroup
--   OptGroup
--    tokenRingSoftErrorMonitorGroup
--   OptGroup
--    portCpbGroup1
--   OptGroup
--    portSecurityGroup1
--   OptGroup
--    fileCopyGroup
--   OptGroup
--    optionalSystemMiscGroup1
--   OptGroup
--    ipPermitGroup1
--   OptGroup
--    optionalSystemMiscGroup2
--   OptGroup
--    filterGroup1
--   OptGroup
--    mcastGroup1
--   OptGroup
--    portGroup1
--   OptGroup
--    chassisGroup1
--   OptGroup
--    moduleGroup1
--   OptGroup
--    portCpbGroup2
--   OptGroup
--    voiceGroup
--   OptGroup
--    moduleGroup2
--   OptGroup
--    portCpbGroup3
--   OptGroup
--    portGroup2
--   OptGroup
--    switchAccelerationModuleGroup
--   OptGroup
--    optionalSystemMiscGroup3
--   OptGroup
--    optionalSystemMiscGroup4
--   OptGroup
--    vlanTrunkMappingGroup
--   OptGroup
--    portJumboFrameGroup
--   OptGroup
--    portCpbGroup4
--   OptGroup
--    fileCopyGroup2
--   OptGroup
--    systemRmonGroup2
--   OptGroup
--    filterGroup2
--   OptGroup
--    optionalSystemMiscGroup5
--   OptGroup
--    syslogGroup2
--   OptGroup
--    systemStatusGroup
--   OptGroup
--    configurationGroup
--   OptGroup
--    filterGroup3
--   OptGroup
--    portGroup3
--   OptGroup
--    portCpbGroup5
--   OptGroup
--    authenticationGroup1

ciscoStackgMIBCompliance6 OBJECT IDENTIFIER ::= { ciscoStackMIBCompliances 6 }
-- MODULE-COMPLIANCE
--  Status
--    deprecated
--  Descr
--    The compliance statement for entities which
--    implement the Cisco stack MIB.
--  Module
--    >>current<<
--   MandGroup
--    systemMiscGroup1
--   MandGroup
--    systemTrapGroup1
--   MandGroup
--    chassisGroup
--   MandGroup
--    moduleGroup
--   MandGroup
--    portGroup4
--   OptGroup
--    optionalSystemMiscGroup
--   OptGroup
--    optionalSystemTrapGroup
--   OptGroup
--    optionalChassisGroup1
--   OptGroup
--    optionalModuleGroup
--   OptGroup
--    optionalPortGroup1
--   OptGroup
--    systemTrafficGroup
--   OptGroup
--    systemFddiGroup
--   OptGroup
--    systemRmonGroup
--   OptGroup
--    tftpGroup
--   OptGroup
--    brouteEnableGroup
--   OptGroup
--    filterGroup
--   OptGroup
--    vlanGroup2
--   OptGroup
--    vmpsGroup
--   OptGroup
--    tokenRingGroup
--   OptGroup
--    mcastGroup
--   OptGroup
--    dnsGroup
--   OptGroup
--    syslogGroup
--   OptGroup
--    ntpGroup
--   OptGroup
--    ipPermitGroup2
--   OptGroup
--    mdgGatewayGroup
--   OptGroup
--    traceRouteGroup
--   OptGroup
--    ntpAuthenticationGroup
--   OptGroup
--    tokenRingSoftErrorMonitorGroup
--   OptGroup
--    portCpbGroup1
--   OptGroup
--    portSecurityGroup1
--   OptGroup
--    fileCopyGroup
--   OptGroup
--    optionalSystemMiscGroup1
--   OptGroup
--    ipPermitGroup1
--   OptGroup
--    optionalSystemMiscGroup6
--   OptGroup
--    filterGroup1
--   OptGroup
--    mcastGroup1
--   OptGroup
--    portGroup1
--   OptGroup
--    chassisGroup1
--   OptGroup
--    moduleGroup1
--   OptGroup
--    portCpbGroup2
--   OptGroup
--    voiceGroup
--   OptGroup
--    moduleGroup2
--   OptGroup
--    portCpbGroup3
--   OptGroup
--    portGroup2
--   OptGroup
--    switchAccelerationModuleGroup
--   OptGroup
--    optionalSystemMiscGroup3
--   OptGroup
--    optionalSystemMiscGroup4
--   OptGroup
--    vlanTrunkMappingGroup
--   OptGroup
--    portJumboFrameGroup
--   OptGroup
--    portCpbGroup4
--   OptGroup
--    fileCopyGroup2
--   OptGroup
--    systemRmonGroup2
--   OptGroup
--    filterGroup2
--   OptGroup
--    optionalSystemMiscGroup5
--   OptGroup
--    syslogGroup2
--   OptGroup
--    systemStatusGroup
--   OptGroup
--    configurationGroup
--   OptGroup
--    filterGroup3
--   OptGroup
--    portGroup3
--   OptGroup
--    portCpbGroup5
--   OptGroup
--    authenticationGroup1

ciscoStackgMIBCompliance7 OBJECT IDENTIFIER ::= { ciscoStackMIBCompliances 7 }
-- MODULE-COMPLIANCE
--  Status
--    deprecated
--  Descr
--    The compliance statement for entities which
--    implement the Cisco stack MIB.
--  Module
--    >>current<<
--   MandGroup
--    systemMiscGroup1
--   MandGroup
--    systemTrapGroup2
--   MandGroup
--    chassisGroup
--   MandGroup
--    moduleGroup
--   MandGroup
--    portGroup4
--   OptGroup
--    optionalSystemMiscGroup
--   OptGroup
--    optionalChassisGroup1
--   OptGroup
--    optionalModuleGroup
--   OptGroup
--    optionalPortGroup1
--   OptGroup
--    systemTrafficGroup
--   OptGroup
--    systemFddiGroup
--   OptGroup
--    systemRmonGroup
--   OptGroup
--    tftpGroup
--   OptGroup
--    brouteEnableGroup
--   OptGroup
--    filterGroup
--   OptGroup
--    vlanGroup2
--   OptGroup
--    vmpsGroup
--   OptGroup
--    tokenRingGroup
--   OptGroup
--    mcastGroup
--   OptGroup
--    dnsGroup
--   OptGroup
--    syslogGroup
--   OptGroup
--    ntpGroup
--   OptGroup
--    ipPermitGroup2
--   OptGroup
--    mdgGatewayGroup
--   OptGroup
--    traceRouteGroup
--   OptGroup
--    ntpAuthenticationGroup
--   OptGroup
--    tokenRingSoftErrorMonitorGroup
--   OptGroup
--    portCpbGroup1
--   OptGroup
--    portSecurityGroup1
--   OptGroup
--    fileCopyGroup
--   OptGroup
--    optionalSystemMiscGroup1
--   OptGroup
--    ipPermitGroup1
--   OptGroup
--    optionalSystemMiscGroup6
--   OptGroup
--    filterGroup1
--   OptGroup
--    mcastGroup1
--   OptGroup
--    portGroup1
--   OptGroup
--    chassisGroup1
--   OptGroup
--    moduleGroup1
--   OptGroup
--    portCpbGroup2
--   OptGroup
--    voiceGroup
--   OptGroup
--    moduleGroup2
--   OptGroup
--    portCpbGroup3
--   OptGroup
--    portGroup2
--   OptGroup
--    switchAccelerationModuleGroup
--   OptGroup
--    optionalSystemMiscGroup3
--   OptGroup
--    optionalSystemMiscGroup4
--   OptGroup
--    vlanTrunkMappingGroup
--   OptGroup
--    portJumboFrameGroup
--   OptGroup
--    portCpbGroup4
--   OptGroup
--    fileCopyGroup2
--   OptGroup
--    systemRmonGroup2
--   OptGroup
--    filterGroup2
--   OptGroup
--    optionalSystemMiscGroup5
--   OptGroup
--    syslogGroup2
--   OptGroup
--    systemStatusGroup
--   OptGroup
--    configurationGroup
--   OptGroup
--    filterGroup3
--   OptGroup
--    portGroup3
--   OptGroup
--    portCpbGroup5
--   OptGroup
--    optionalSystemTrapGroup1
--   OptGroup
--    authenticationGroup2
--   OptGroup
--    notificationGroup

ciscoStackgMIBCompliance8 OBJECT IDENTIFIER ::= { ciscoStackMIBCompliances 8 }
-- MODULE-COMPLIANCE
--  Status
--    mandatory
--  Descr
--    The compliance statement for entities which
--    implement the Cisco stack MIB.
--  Module
--    >>current<<
--   MandGroup
--    systemMiscGroup1
--   MandGroup
--    systemTrapGroup2
--   MandGroup
--    chassisGroup
--   MandGroup
--    moduleGroup
--   MandGroup
--    portGroup4
--   OptGroup
--    optionalSystemMiscGroup
--   OptGroup
--    optionalChassisGroup1
--   OptGroup
--    optionalModuleGroup
--   OptGroup
--    optionalPortGroup1
--   OptGroup
--    systemTrafficGroup
--   OptGroup
--    systemFddiGroup
--   OptGroup
--    systemRmonGroup
--   OptGroup
--    tftpGroup
--   OptGroup
--    brouteEnableGroup
--   OptGroup
--    filterGroup
--   OptGroup
--    vlanGroup2
--   OptGroup
--    vmpsGroup
--   OptGroup
--    tokenRingGroup
--   OptGroup
--    mcastGroup
--   OptGroup
--    dnsGroup
--   OptGroup
--    syslogGroup
--   OptGroup
--    ntpGroup
--   OptGroup
--    ipPermitGroup2
--   OptGroup
--    mdgGatewayGroup
--   OptGroup
--    traceRouteGroup
--   OptGroup
--    ntpAuthenticationGroup
--   OptGroup
--    tokenRingSoftErrorMonitorGroup
--   OptGroup
--    portCpbGroup1
--   OptGroup
--    portSecurityGroup1
--   OptGroup
--    fileCopyGroup
--   OptGroup
--    optionalSystemMiscGroup1
--   OptGroup
--    ipPermitGroup1
--   OptGroup
--    optionalSystemMiscGroup6
--   OptGroup
--    filterGroup1
--   OptGroup
--    mcastGroup1
--   OptGroup
--    portGroup1
--   OptGroup
--    chassisGroup1
--   OptGroup
--    moduleGroup1
--   OptGroup
--    portCpbGroup2
--   OptGroup
--    voiceGroup
--   OptGroup
--    moduleGroup2
--   OptGroup
--    portCpbGroup3
--   OptGroup
--    portGroup2
--   OptGroup
--    switchAccelerationModuleGroup
--   OptGroup
--    optionalSystemMiscGroup3
--   OptGroup
--    optionalSystemMiscGroup4
--   OptGroup
--    vlanTrunkMappingGroup
--   OptGroup
--    portJumboFrameGroup
--   OptGroup
--    portCpbGroup4
--   OptGroup
--    fileCopyGroup2
--   OptGroup
--    systemRmonGroup2
--   OptGroup
--    filterGroup2
--   OptGroup
--    optionalSystemMiscGroup5
--   OptGroup
--    syslogGroup2
--   OptGroup
--    systemStatusGroup
--   OptGroup
--    configurationGroup
--   OptGroup
--    filterGroup3
--   OptGroup
--    portGroup3
--   OptGroup
--    portCpbGroup5
--   OptGroup
--    optionalSystemTrapGroup1
--   OptGroup
--    authenticationGroup2
--   OptGroup
--    notificationGroup
--   OptGroup
--    ipPermitGroup3


END
