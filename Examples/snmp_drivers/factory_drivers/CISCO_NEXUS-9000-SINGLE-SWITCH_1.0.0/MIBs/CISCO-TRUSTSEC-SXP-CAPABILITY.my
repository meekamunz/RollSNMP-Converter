-- *****************************************************************
-- CISCO-TRUSTSEC-SXP-CAPABILITY.my:
-- Cisco CISCO-TRUSTSEC-SXP-MIB AGENT-CAPABILITIES
--   
-- March 2010, Dipesh Gorashia
--   
-- Copyright (c) 2010-2012 by Cisco Systems Inc.
-- All rights reserved.
-- ****************************************************************

CISCO-TRUSTSEC-SXP-CAPABILITY DEFINITIONS ::= BEGIN

IMPORTS
    MODULE-IDENTITY,
    Unsigned32
        FROM SNMPv2-SMI
    AGENT-CAPABILITIES
        FROM SNMPv2-CONF
    SnmpAdminString
        FROM SNMP-FRAMEWORK-MIB
    RowStatus
        FROM SNMPv2-TC
    CiscoVrfName
        FROM CISCO-TC
    ciscoAgentCapability
        FROM CISCO-SMI;


ciscoTrustSecSxpCapability MODULE-IDENTITY
    LAST-UPDATED    "201204100000Z"
    ORGANIZATION    "Cisco Systems, Inc."
    CONTACT-INFO
            "Cisco Systems
            Customer Service

            Postal: 170 West Tasman Drive
            San Jose, CA  95134
            USA

            Tel: +1 800 553-NETS

            E-mail: cs-san@cisco.com,
                    cs-lan-switch-snmp@cisco.com"
    DESCRIPTION
        "The capabilities description of
        CISCO-TRUSTSEC-SXP-MIB."
    REVISION        "201204100000Z"
    DESCRIPTION
        "Added capability statement
        ciscoTrustSecSxpCapV15R0101SGPCat4k."
    REVISION        "201109280000Z"
    DESCRIPTION
        "Added capability statement
        ciscoTrustSecSxpCapV15R0001SYPCat6k."
    REVISION        "201103230000Z"
    DESCRIPTION
        "Added capability statement
        ciscoTrustSecSxpCapV12R0233SXJPCat6k."
    REVISION        "201011030000Z"
    DESCRIPTION
        "Added agent capabilities statement
        ciscoTrustSecSxpCapV12R0250SYPCat6k."
    REVISION        "201003250000Z"
    DESCRIPTION
        "Initial version of this MIB module."
    ::= { ciscoAgentCapability 591 }



ciscoTrustSecSxpCapV12R0233SXI4PCat6k AGENT-CAPABILITIES
    PRODUCT-RELEASE "Cisco IOS 12.2(33)SXI4 on Catalyst 6000/6500
                     series devices."
    STATUS          current
    DESCRIPTION
        "CISCO-TRUSTSEC-SXP-MIB capabilities."

    SUPPORTS        CISCO-TRUSTSEC-SXP-MIB
    INCLUDES        {
                        ctsxSxpGlobalGroup,
                        ctsxSxpConnectionGroup,
                        ctsxIpSgtMappingGroup
                    }
    VARIATION       ctsxSxpConfigDefaultPassword
    SYNTAX          SnmpAdminString (SIZE (0..162))
    DESCRIPTION
        "Only a limited set of values is supported.
        The object supports 1 to 80 octets when value
        of ctsxSxpConfigDefaultPasswordType is 'clearText'.
        The object supports 1 to 162 octets when the value
        of ctsxSxpConfigDefaultPasswordType is 'typeSix'
        or 'typeSeven'."

    VARIATION       ctsxSxpDefaultSourceAddrType
    SYNTAX          INTEGER  {
                        unknown(0),
                        ipv4(1)
                    }
    DESCRIPTION
        "Only a limited set of enumerated values is supported."

    VARIATION       ctsxSxpRetryPeriod
    SYNTAX          Unsigned32 (0..64000)
    DESCRIPTION
        "Only limited set of values is supported."

    VARIATION       ctsxSxpReconPeriod
    SYNTAX          Unsigned32 (0..64000)
    DESCRIPTION
        "Only limited set of values is supported."

    VARIATION       ctsxSxpConnVrfName
    SYNTAX          CiscoVrfName
    DESCRIPTION
        "Only zero length VRF name is supported."

    VARIATION       ctsxSxpConnPeerAddrType
    SYNTAX          INTEGER  {
                        ipv4(1)
                    }
    DESCRIPTION
        "Only a limited set of enumerated values is supported."

    VARIATION       ctsxSxpConnSourceAddrType
    SYNTAX          INTEGER  {
                        unknown(0),
                        ipv4(1)
                    }
    DESCRIPTION
        "Only a limited set of enumerated values is supported."

    VARIATION       ctsxSxpConnPasswordUsed
    SYNTAX          INTEGER  {
                        none(1),
                        default(2)
                    }
    DESCRIPTION
        "Only a limited set of enumerated values is supported."

    VARIATION       ctsxSxpConnStorageType
    ACCESS          read-only
    DESCRIPTION
        "Write access is not supported."

    VARIATION       ctsxSxpConnRowStatus
    SYNTAX          RowStatus {
                        active(1),
                        createAndGo(4),
                        destroy(6)
                    }
    DESCRIPTION
        "Only a limited set of enumerated values is
        supported."

    ::= { ciscoTrustSecSxpCapability 1 }

ciscoTrustSecSxpCapV12R0250SYPCat6k AGENT-CAPABILITIES
    PRODUCT-RELEASE "Cisco IOS 12.2(50)SY on Catalyst 6000/6500
                     series devices."
    STATUS          current
    DESCRIPTION
        "CISCO-TRUSTSEC-SXP-MIB capabilities."

    SUPPORTS        CISCO-TRUSTSEC-SXP-MIB
    INCLUDES        {
                        ctsxSxpGlobalGroup,
                        ctsxSxpConnectionGroup,
                        ctsxIpSgtMappingGroup
                    }
    VARIATION       ctsxSxpConfigDefaultPassword
    SYNTAX          SnmpAdminString (SIZE (0..162))
    DESCRIPTION
        "Only a limited set of values is supported.
        The object supports 1 to 80 octets when value
        of ctsxSxpConfigDefaultPasswordType is 'clearText'.
        The object supports 1 to 162 octets when the value
        of ctsxSxpConfigDefaultPasswordType is 'typeSix'
        or 'typeSeven'."

    VARIATION       ctsxSxpDefaultSourceAddrType
    SYNTAX          INTEGER  {
                        unknown(0),
                        ipv4(1)
                    }
    DESCRIPTION
        "Only a limited set of enumerated values is supported."

    VARIATION       ctsxSxpRetryPeriod
    SYNTAX          Unsigned32 (0..64000)
    DESCRIPTION
        "Only limited set of values is supported."

    VARIATION       ctsxSxpReconPeriod
    SYNTAX          Unsigned32 (0..64000)
    DESCRIPTION
        "Only limited set of values is supported."

    VARIATION       ctsxSxpConnPeerAddrType
    SYNTAX          INTEGER  {
                        ipv4(1)
                    }
    DESCRIPTION
        "Only a limited set of enumerated values is supported."

    VARIATION       ctsxSxpConnSourceAddrType
    SYNTAX          INTEGER  {
                        unknown(0),
                        ipv4(1)
                    }
    DESCRIPTION
        "Only a limited set of enumerated values is supported."

    VARIATION       ctsxSxpConnPasswordUsed
    SYNTAX          INTEGER  {
                        none(1),
                        default(2)
                    }
    DESCRIPTION
        "Only a limited set of enumerated values is supported."

    VARIATION       ctsxSxpConnStorageType
    ACCESS          read-only
    DESCRIPTION
        "Write access is not supported."

    VARIATION       ctsxSxpConnRowStatus
    SYNTAX          RowStatus {
                        active(1),
                        createAndGo(4),
                        destroy(6)
                    }
    DESCRIPTION
        "Only a limited set of enumerated values is
        supported."

    ::= { ciscoTrustSecSxpCapability 2 }

ciscoTrustSecSxpCapV12R0233SXJPCat6k AGENT-CAPABILITIES
    PRODUCT-RELEASE "Cisco IOS 12.2(33)SXJ on Catalyst 6000/6500
                     series devices."
    STATUS          current
    DESCRIPTION
        "CISCO-TRUSTSEC-SXP-MIB capabilities."

    SUPPORTS        CISCO-TRUSTSEC-SXP-MIB
    INCLUDES        {
                        ctsxSxpGlobalGroup,
                        ctsxSxpConnectionGroup,
                        ctsxIpSgtMappingGroup,
                        ctsxSxpVersionGroup
                    }
    VARIATION       ctsxSxpConfigDefaultPassword
    SYNTAX          SnmpAdminString (SIZE (0..162))
    DESCRIPTION
        "Only a limited set of values is supported.
        The object supports 1 to 80 octets when value
        of ctsxSxpConfigDefaultPasswordType is 'clearText'.
        The object supports 1 to 162 octets when the value
        of ctsxSxpConfigDefaultPasswordType is 'typeSix'
        or 'typeSeven'."

    VARIATION       ctsxSxpDefaultSourceAddrType
    SYNTAX          INTEGER  {
                        unknown(0),
                        ipv4(1)
                    }
    DESCRIPTION
        "Only a limited set of enumerated values is supported."

    VARIATION       ctsxSxpRetryPeriod
    SYNTAX          Unsigned32 (0..64000)
    DESCRIPTION
        "Only limited set of values is supported."

    VARIATION       ctsxSxpReconPeriod
    SYNTAX          Unsigned32 (0..64000)
    DESCRIPTION
        "Only limited set of values is supported."

    VARIATION       ctsxSxpConnPeerAddrType
    SYNTAX          INTEGER  {
                        ipv4(1)
                    }
    DESCRIPTION
        "Only a limited set of enumerated values is supported."

    VARIATION       ctsxSxpConnSourceAddrType
    SYNTAX          INTEGER  {
                        unknown(0),
                        ipv4(1)
                    }
    DESCRIPTION
        "Only a limited set of enumerated values is supported."

    VARIATION       ctsxSxpConnPasswordUsed
    SYNTAX          INTEGER  {
                        none(1),
                        default(2)
                    }
    DESCRIPTION
        "Only a limited set of enumerated values is supported."

    VARIATION       ctsxSxpConnStorageType
    ACCESS          read-only
    DESCRIPTION
        "Write access is not supported."

    VARIATION       ctsxSxpConnRowStatus
    SYNTAX          RowStatus {
                        active(1),
                        createAndGo(4),
                        destroy(6)
                    }
    DESCRIPTION
        "Only a limited set of enumerated values is
        supported."

    ::= { ciscoTrustSecSxpCapability 3 }

ciscoTrustSecSxpCapV15R0001SYPCat6k AGENT-CAPABILITIES
    PRODUCT-RELEASE "Cisco IOS 15.0(1)SY on Catalyst 6000/6500
                     series devices."
    STATUS          current
    DESCRIPTION
        "CISCO-TRUSTSEC-SXP-MIB capabilities."

    SUPPORTS        CISCO-TRUSTSEC-SXP-MIB
    INCLUDES        {
                        ctsxSxpGlobalGroup,
                        ctsxSxpConnectionGroup,
                        ctsxIpSgtMappingGroup,
                        ctsxSxpVersionGroup
                    }
    VARIATION       ctsxSxpConfigDefaultPassword
    SYNTAX          SnmpAdminString (SIZE (0..162))
    DESCRIPTION
        "Only a limited set of values is supported.
        The object supports 1 to 80 octets when value
        of ctsxSxpConfigDefaultPasswordType is 'clearText'.
        The object supports 1 to 162 octets when the value
        of ctsxSxpConfigDefaultPasswordType is 'typeSix'
        or 'typeSeven'."

    VARIATION       ctsxSxpDefaultSourceAddrType
    SYNTAX          INTEGER  {
                        unknown(0),
                        ipv4(1)
                    }
    DESCRIPTION
        "Only a limited set of enumerated values is supported."

    VARIATION       ctsxSxpRetryPeriod
    SYNTAX          Unsigned32 (0..64000)
    DESCRIPTION
        "Only limited set of values is supported."

    VARIATION       ctsxSxpReconPeriod
    SYNTAX          Unsigned32 (0..64000)
    DESCRIPTION
        "Only limited set of values is supported."

    VARIATION       ctsxSxpConnPeerAddrType
    SYNTAX          INTEGER  {
                        ipv4(1)
                    }
    DESCRIPTION
        "Only a limited set of enumerated values is supported."

    VARIATION       ctsxSxpConnSourceAddrType
    SYNTAX          INTEGER  {
                        unknown(0),
                        ipv4(1)
                    }
    DESCRIPTION
        "Only a limited set of enumerated values is supported."

    VARIATION       ctsxSxpConnPasswordUsed
    SYNTAX          INTEGER  {
                        none(1),
                        default(2)
                    }
    DESCRIPTION
        "Only a limited set of enumerated values is supported."

    VARIATION       ctsxSxpConnStorageType
    ACCESS          read-only
    DESCRIPTION
        "Write access is not supported."

    VARIATION       ctsxSxpConnRowStatus
    SYNTAX          RowStatus {
                        active(1),
                        createAndGo(4),
                        destroy(6)
                    }
    DESCRIPTION
        "Only a limited set of enumerated values is
        supported."

    ::= { ciscoTrustSecSxpCapability 4 }

ciscoTrustSecSxpCapV15R0101SGPCat4k AGENT-CAPABILITIES
    PRODUCT-RELEASE "Cisco IOS 15.1(1)SG on Cat4K family switches."
    STATUS          current
    DESCRIPTION
        "CISCO-TRUSTSEC-SXP-MIB capabilities."

    SUPPORTS        CISCO-TRUSTSEC-SXP-MIB
    INCLUDES        {
                        ctsxSxpGlobalGroup,
                        ctsxSxpConnectionGroup,
                        ctsxIpSgtMappingGroup,
                        ctsxSxpVersionGroup
                    }
    VARIATION       ctsxSxpConfigDefaultPassword
    SYNTAX          SnmpAdminString (SIZE (0..162))
    DESCRIPTION
        "Only a limited set of values is supported.
        The object supports 1 to 80 octets when value
        of ctsxSxpConfigDefaultPasswordType is 'clearText'.
        The object supports 1 to 162 octets when the value
        of ctsxSxpConfigDefaultPasswordType is 'typeSix'
        or 'typeSeven'."

    VARIATION       ctsxSxpDefaultSourceAddrType
    SYNTAX          INTEGER  {
                        unknown(0),
                        ipv4(1)
                    }
    DESCRIPTION
        "Only a limited set of enumerated values is supported."

    VARIATION       ctsxSxpRetryPeriod
    SYNTAX          Unsigned32 (0..64000)
    DESCRIPTION
        "Only limited set of values is supported."

    VARIATION       ctsxSxpReconPeriod
    SYNTAX          Unsigned32 (0..64000)
    DESCRIPTION
        "Only limited set of values is supported."

    VARIATION       ctsxSxpConnPeerAddrType
    SYNTAX          INTEGER  {
                        ipv4(1)
                    }
    DESCRIPTION
        "Only a limited set of enumerated values is supported."

    VARIATION       ctsxSxpConnSourceAddrType
    SYNTAX          INTEGER  {
                        unknown(0),
                        ipv4(1)
                    }
    DESCRIPTION
        "Only a limited set of enumerated values is supported."

    VARIATION       ctsxSxpConnPasswordUsed
    SYNTAX          INTEGER  {
                        none(1),
                        default(2)
                    }
    DESCRIPTION
        "Only a limited set of enumerated values is supported."

    VARIATION       ctsxSxpConnStorageType
    ACCESS          read-only
    DESCRIPTION
        "Write access is not supported."

    VARIATION       ctsxSxpConnRowStatus
    SYNTAX          RowStatus {
                        active(1),
                        createAndGo(4),
                        destroy(6)
                    }
    DESCRIPTION
        "Only a limited set of enumerated values is
        supported."

    ::= { ciscoTrustSecSxpCapability 5 }

END
