-- MIB file created 20-Jun-2007 17:13:17, by
--   SMICng version 2.2.11-beta(PRO)(Solaris), January 20, 2001. Enterprise key cisco.com

CISCO-LWAPP-QOS-MIB DEFINITIONS ::= BEGIN

-- From file: "CISCO-LWAPP-QOS-MIB.my"
-- Compile options "4 7 F H N O W 03 06 0B 0G 0N 0T"

IMPORTS
    TruthValue
            FROM SNMPv2-TC-v1
    cLApSysMacAddress, cLApDot11IfSlotId
            FROM CISCO-LWAPP-AP-MIB
    cLWlanIndex
            FROM CISCO-LWAPP-WLAN-MIB
    ciscoMgmt
            FROM CISCO-SMI
    Counter, Gauge
            FROM RFC1155-SMI
    OBJECT-TYPE
            FROM RFC-1212;

ciscoLwappQosMIB OBJECT IDENTIFIER ::= { ciscoMgmt 524 }
-- MODULE-IDENTITY
--  LastUpdated
--    200701070000Z
--  OrgName
--    Cisco Systems Inc.
--  ContactInfo
--    Cisco Systems,
--    Customer Service
--    Postal: 170 West Tasman Drive
--    San Jose, CA  95134
--    USA
--    Tel: +1 800 553-NETS
--    
--    Email: cs-wnbu-snmp@cisco.com
--  Descr
--    This MIB is intended to be implemented on all those
--    devices operating as Central controllers, that
--    terminate the Light Weight Access Point Protocol
--    tunnel from Cisco Light-weight LWAPP Access Points.
--    
--    Information provided by this MIB is used to study
--    the quality of service in the voice and video traffic
--    on the WLAN.
--    
--    The relationship between CC and the LWAPP APs
--    can be depicted as follows:
--    
--          +......+     +......+     +......+
--          +      +     +      +     +      +
--          +  CC  +     +  CC  +     +  CC  +
--          +      +     +      +     +      +
--          +......+     +......+     +......+
--            ..            .             .
--            ..            .             .
--           .  .            .             .
--          .    .            .             .
--         .      .            .             .
--        .        .            .             .
--    +......+ +......+     +......+      +......+
--    +      + +      +     +      +      +      +
--    +  AP  + +  AP  +     +  AP  +      +  AP  +
--    +      + +      +     +      +      +      +
--    +......+ +......+     +......+      +......+
--               .              .             .
--             .  .              .             .
--            .    .              .             .
--           .      .              .             .
--          .        .              .             .
--       +......+ +......+     +......+      +......+
--       +      + +      +     +      +      +      +
--       +  MN  + +  MN  +     +  MN  +      +  MN  +
--       +      + +      +     +      +      +      +
--       +......+ +......+     +......+      +......+
--    
--    
--    The LWAPP tunnel exists between the controller and
--    the APs.  The MNs communicate with the APs through
--    the protocol defined by the 802.11 standard.
--    
--    LWAPP APs, upon bootup, discover and join one of the
--    controllers and the controller pushes the configuration,
--    that includes the WLAN parameters, to the LWAPP APs.
--    The APs then encapsulate all the 802.11 frames from
--    wireless clients inside LWAPP frames and forward
--    the LWAPP frames to the controller.
--    
--                       GLOSSARY
--    
--    Access Point ( AP )
--    
--    An entity that contains an 802.11 medium access
--    control ( MAC ) and physical layer ( PHY ) interface
--    and provides access to the distribution services via
--    the wireless medium for associated clients.  
--    
--    LWAPP APs encapsulate all the 802.11 frames in
--    LWAPP frames and sends them to the controller to which
--    it is logically connected.
--    
--    Gratuitous Probe Response (GPR)
--    
--    The Gratuitous Probe Response feature aids in conserving
--    battery power of WLAN-enabled cell phones by providing
--    a high rate packet on the order of tens of milliseconds
--    such that these kind of phones can wake up and wait at
--    predefined intervals, to reduce battery power.  The 
--    GPR packet is transmitted from the AP at a predefined
--    time interval.
--    
--    
--    Light Weight Access Point Protocol ( LWAPP )
--    
--    This is a generic protocol that defines the 
--    communication between the Access Points and the
--    Central Controller. 
--    
--    Mobile Node ( MN )
--    
--    A roaming 802.11 wireless device in a wireless
--    network associated with an access point. Mobile Node 
--    and client are used interchangeably. 
--    
--    TU
--    
--    A measurement of time in units of 1024 microseconds.
--    
--    User Priority ( UP )
--    
--    Specifies a the priority rules in QOS for handling user 
--    priority.
--    
--    REFERENCE
--    
--    [1] Wireless LAN Medium Access Control ( MAC ) and
--    Physical Layer ( PHY ) Specifications
--    
--    [2] Draft-obara-capwap-lwapp-00.txt, IETF Light 
--    Weight Access Point Protocol
--  RevDate
--    200701070000Z
--  RevDescr
--    Added ciscoLwappQosDot11aConfigGroupSup1 and
--    ciscoLwappQosDot11bConfigGroupSup1 objects.
--  RevDate
--    200604130000Z
--  RevDescr
--    Initial version of this MIB module.

ciscoLwappQosMIBNotifs OBJECT IDENTIFIER ::= { ciscoLwappQosMIB 0 }
ciscoLwappQosMIBObjects OBJECT IDENTIFIER ::= { ciscoLwappQosMIB 1 }
ciscoLwappQosMIBConform OBJECT IDENTIFIER ::= { ciscoLwappQosMIB 2 }
cLQd11aCACConfig OBJECT IDENTIFIER ::= { ciscoLwappQosMIBObjects 1 }
cLQd11bCACConfig OBJECT IDENTIFIER ::= { ciscoLwappQosMIBObjects 2 }
cLQd11GprConfig OBJECT IDENTIFIER ::= { ciscoLwappQosMIBObjects 3 }
cLQd11CACStats  OBJECT IDENTIFIER ::= { ciscoLwappQosMIBObjects 4 }
cLQEntConfConfig OBJECT IDENTIFIER ::= { ciscoLwappQosMIBObjects 5 }
ciscoLwappQosMIBCompliances OBJECT IDENTIFIER ::= { ciscoLwappQosMIBConform 1 }
ciscoLwappQosMIBGroups OBJECT IDENTIFIER ::= { ciscoLwappQosMIBConform 2 }

cLQd11aVoiceAdmCtrlSupport OBJECT-TYPE
    SYNTAX TruthValue
--    Rsyntax INTEGER {
--        true(1),
--        false(2)
--        }
    ACCESS read-write
    STATUS mandatory
    DESCRIPTION
        "This object is used to enable or disable admission
        control for voice traffic flowing through the 802.11a 
        interfaces in the controller.
        
        When set to 'true', controller will reserve and manage 
        max-bandwidth (cLQd11aVoiceMaxAdmBandwidth) 
        and roaming-bandwidth
        (cLQd11aVoiceMaxRoamBandwidth) as per user 
        configured values.
        
        When disabled, admission control will not be enforced. 
        This may delay voice traffic depending on load on
        the WLAN."
    DEFVAL { true }
    ::= { cLQd11aCACConfig 1 }

cLQd11aVoiceMaxAdmBandwidth OBJECT-TYPE
    SYNTAX Gauge(0..100)
--  Units
--    Percent
    ACCESS read-write
    STATUS mandatory
    DESCRIPTION
        "This object denotes the maximum bandwidth
        that can be allocated by controller for voice
        traffic when admission control is enabled for
        for 802.11a interfaces in the controller.
        
        Please note that the write operation on this
        object will be successful only if the 802.11a
        network is not operational and the total
        value populated for this object for all the
        admission control attributes (voice, video)
        together does not exceed 100%."
    ::= { cLQd11aCACConfig 2 }

cLQd11aVoiceMaxRoamBandwidth OBJECT-TYPE
    SYNTAX Gauge(0..100)
--  Units
--    Percent
    ACCESS read-write
    STATUS mandatory
    DESCRIPTION
        "This object represents the bandwidth relative
        to the maximum allocated bandwidth indicated by
        cLQd11aVoiceMaxAdmBandwidth, that can be 
        allocated to roaming clients for voice traffic,
        when admission control is enabled for 802.11a
        interfaces in the controller.
        
        Please note that the write operation on this
        object will be successful only if the 802.11a
        network is disabled and not operational.  The
        value configured through this object takes
        effect when the 802.11a network is enabled."
    DEFVAL { 0 }
    ::= { cLQd11aCACConfig 3 }

cLQd11aVideoAdmCtrlSupport OBJECT-TYPE
    SYNTAX TruthValue
--    Rsyntax INTEGER {
--        true(1),
--        false(2)
--        }
    ACCESS read-write
    STATUS mandatory
    DESCRIPTION
        "This object is used to enable or disable admission
        control for video traffic flowing through the 802.11a 
        interfaces in the controller.
        
        When set to 'true', controller will reserve and manage 
        max-bandwidth (cLQd11aVideoMaxAdmBandwidth) 
        and roaming-bandwidth
        (cLQd11aVideoMaxRoamBandwidth) as per user  
        configured values.
        
        When disabled, admission control will not be enforced. 
        This may delay video traffic depending on load on
        the WLAN."
    DEFVAL { true }
    ::= { cLQd11aCACConfig 4 }

cLQd11aVideoMaxAdmBandwidth OBJECT-TYPE
    SYNTAX Gauge(0..100)
--  Units
--    Percent
    ACCESS read-write
    STATUS mandatory
    DESCRIPTION
        "This object denotes the maximum bandwidth
        that can be allocated by controller for video traffic
        when admission control is enabled for 802.11a 
        interfaces in the controller.  When set to 0, all
        available bandwidth in 802.11a interfaces can be
        allocated to video traffic.
        
        Please note that the write operation on this
        object will be successful only if the 802.11a
        network is not operational and the total
        value populated for this object for all the
        admission control attributes (voice, video)
        together does not exceed 100%."
    DEFVAL { 0 }
    ::= { cLQd11aCACConfig 5 }

cLQd11aVideoMaxRoamBandwidth OBJECT-TYPE
    SYNTAX Gauge(0..100)
--  Units
--    Percent
    ACCESS read-write
    STATUS mandatory
    DESCRIPTION
        "This object represents the bandwidth relative
        to the maximum allocated bandwidth indicated by
        cLQd11aVideoMaxAdmBandwidth, that can be 
        allocated to roaming clients for video traffic,
        when admission control is enabled for 802.11a
        interfaces in the controller.
        
        Please note that the write operation on this
        object will be successful only if the 802.11a
        network is disabled and not operational.  The
        value configured through this object takes effect 
        when the 802.11a network is enabled and 
        operational."
    DEFVAL { 0 }
    ::= { cLQd11aCACConfig 6 }

cLQd11bVoiceAdmCtrlSupport OBJECT-TYPE
    SYNTAX TruthValue
--    Rsyntax INTEGER {
--        true(1),
--        false(2)
--        }
    ACCESS read-write
    STATUS mandatory
    DESCRIPTION
        "This object is used to enable or disable admission
        control for voice traffic flowing through the 
        802.11b/g interfaces in the controller.
        
        When set to 'true', controller will reserve and manage
        max-bandwidth (cLQd11bVoiceMaxAdmBandwidth)
        and roaming-bandwidth
        (cLQd11bVoiceMaxRoamingBandwidth) as per user
        configured values.
        
        When disabled, admission control will not be enforced. 
        This may delay voice traffic depending on load on the 
        WLAN."
    DEFVAL { true }
    ::= { cLQd11bCACConfig 1 }

cLQd11bVoiceMaxAdmBandwidth OBJECT-TYPE
    SYNTAX Gauge(0..100)
--  Units
--    Percent
    ACCESS read-write
    STATUS mandatory
    DESCRIPTION
        "This object denotes the maximum bandwidth that
        can be allocated by controller for voice traffic 
        when admission control is enabled for 802.11b/g
        interfaces in the controller.
        
        Please note that the write operation on this
        object will be successful only if the 802.11b/g
        network is not operational and the total
        value populated for this object for all the
        admission control attributes (voice, video)
        together does not exceed 100%."
    ::= { cLQd11bCACConfig 2 }

cLQd11bVoiceMaxRoamBandwidth OBJECT-TYPE
    SYNTAX Gauge(0..100)
--  Units
--    Percent
    ACCESS read-write
    STATUS mandatory
    DESCRIPTION
        "This object represents the bandwidth relative
        to the maximum allocated bandwidth indicated by
        cLQd11bVoiceMaxAdmBandwidth, that can be 
        allocated to roaming clients for voice traffic,
        when admission control is enabled for 802.11b
        interfaces in the controller.
        
        Please note that the write operation on this
        object will be successful only if the 802.11b/g
        network is not operational.  The value configured
        through this object takes effect when the 802.11b/g
        network is enabled and operational."
    DEFVAL { 0 }
    ::= { cLQd11bCACConfig 3 }

cLQd11bVideoAdmCtrlSupport OBJECT-TYPE
    SYNTAX TruthValue
--    Rsyntax INTEGER {
--        true(1),
--        false(2)
--        }
    ACCESS read-write
    STATUS mandatory
    DESCRIPTION
        "This object is used to enable or disable admission
        control for video traffic flowing through the 
        802.11b/g interfaces in the controller.
        
        When set to 'true', controller will reserve and manage
        max-bandwidth (cLQd11bVideoMaxAdmBandwidth) 
        and roaming-bandwidth
        (cLQd11bVideoMaxRoamBandwidth) as per user 
        configured values.
        
        When disabled, admission control will not be enforced. 
        This may delay video traffic depending on load on the 
        WLAN."
    DEFVAL { true }
    ::= { cLQd11bCACConfig 4 }

cLQd11bVideoMaxAdmBandwidth OBJECT-TYPE
    SYNTAX Gauge(0..100)
--  Units
--    Percent
    ACCESS read-write
    STATUS mandatory
    DESCRIPTION
        "This object denotes the maximum bandwidth that
        can be allocated by controller for video traffic when
        admission control is enabled for 802.11b/g interfaces 
        in the controller.  When set to 0, all available
        bandwidth in 802.11b/g interfaces can be allocated
        to video traffic.
        
        Please note that the write operation on this
        object will be successful only if the 802.11b/g
        network is not operational and the total
        value populated for this object for all the
        admission control attributes (voice, video)
        together does not exceed 100%."
    DEFVAL { 0 }
    ::= { cLQd11bCACConfig 5 }

cLQd11bVideoMaxRoamBandwidth OBJECT-TYPE
    SYNTAX Gauge(0..100)
--  Units
--    Percent
    ACCESS read-write
    STATUS mandatory
    DESCRIPTION
        "This objects represents the bandwidth relative
        to the maximum allocated bandwidth indicated by
        cLQd11bVideoMaxAdmBandwidth, that can be 
        allocated to roaming clients for video traffic,
        when admission control is enabled for 802.11b
        interfaces in the controller.
        
        Please note that the write operation on this
        object will be successful only if the 802.11b/g
        network is not operational.  The value configured
        through this object takes effect when the 802.11b/g
        network is enabled and operational."
    DEFVAL { 0 }
    ::= { cLQd11bCACConfig 6 }

cLQd11aGprProbeInterval OBJECT-TYPE
    SYNTAX Gauge(10..100)
--  Units
--    TU
    ACCESS read-write
    STATUS mandatory
    DESCRIPTION
        "This object is used to set GPR probe interval
        period to be used by all 802.11a interfaces in the 
        controller, when the radios are advertising any 
        WLAN with GPR support enabled.
        
        Please note that the write operation on this
        object will be successful only if the 802.11a
        network is not operational.  The value configured
        through this object takes effect when the 802.11a
        network is enabled and operational."
    DEFVAL { 10 }
    ::= { cLQd11aCACConfig 7 }

cLQd11aVoiceCtrl OBJECT-TYPE
    SYNTAX INTEGER {
        loadBased(1),
        static(2)
        }
    ACCESS read-write
    STATUS mandatory
    DESCRIPTION
        "When admission control is enabled these parameters
        can be modified.
            loadBased - controller will reserve and manage
                        max-bandwidth and roaming-bandwidth
                        based on the load on the WLAN. 
            static    - controller will reserve and
                        manage max-bandwidth 
                        (cLQd11aVoiceMaxAdmBandwidth)
                        and roaming-bandwidth
                        (cLQd11aVoiceMaxRoamBandwidth) 
                        as per user configured values.
         When ACM is disabled, admission control will not 
         be enforced. This may delay voice traffic depending 
         on the traffic on the WLAN."
    DEFVAL { loadBased }
    ::= { cLQd11aCACConfig 8 }

cLQd11aExpeditedBw OBJECT-TYPE
    SYNTAX TruthValue
--    Rsyntax INTEGER {
--        true(1),
--        false(2)
--        }
    ACCESS read-write
    STATUS mandatory
    DESCRIPTION
        "This object specifies if expedited BW feature is
        enabled or not.
        A value of 'true' will ensure that the APs advertise
        the expedited BW support in their beacons and 
        association responses.
        A value of 'false' will ensure that the APs do not
        advertise the expedited BW support in their beacons 
        and association responses."
    ::= { cLQd11aCACConfig 9 }

cLQd11bGprProbeInterval OBJECT-TYPE
    SYNTAX Gauge(10..100)
--  Units
--    TU
    ACCESS read-write
    STATUS mandatory
    DESCRIPTION
        "This object is used to set GPR probe interval
        period to be used by all 802.11b/g interfaces in the 
        controller, when the radios are advertising any 
        WLAN with GPR support enabled.
        
        Please note that the write operation on this
        object will be successful only if the 802.11b/g
        network is not operational.  The value configured
        through this object takes effect when the 802.11b/g
        network is enabled."
    DEFVAL { 10 }
    ::= { cLQd11bCACConfig 7 }

cLQd11bVoiceCtrl OBJECT-TYPE
    SYNTAX INTEGER {
        loadBased(1),
        static(2)
        }
    ACCESS read-write
    STATUS mandatory
    DESCRIPTION
        "When admission control is enabled these parameters
        can be modified.
            loadBased - controller will reserve and manage
                        max-bandwidth and roaming-bandwidth
                        based on the load on the WLAN. 
            static    - controller will reserve and
                        manage max-bandwidth 
                        (cLQd11bVoiceMaxAdmBandwidth)
                        and roaming-bandwidth
                        (cLQd11bVoiceMaxRoamBandwidth) 
                        as per user configured values.
         When ACM is disabled, admission control will not 
         be enforced. This may delay voice traffic depending 
         on the traffic on the WLAN."
    DEFVAL { loadBased }
    ::= { cLQd11bCACConfig 8 }

cLQd11bExpeditedBw OBJECT-TYPE
    SYNTAX TruthValue
--    Rsyntax INTEGER {
--        true(1),
--        false(2)
--        }
    ACCESS read-write
    STATUS mandatory
    DESCRIPTION
        "This object specifies if expedited BW feature is
        enabled or not.
        A value of 'true' will ensure that the APs advertise
        the expedited BW support in their beacons and 
        association responses.
        A value of 'false' will ensure that the APs do not
        advertise the expedited BW support in their beacons 
        and association responses."
    ::= { cLQd11bCACConfig 9 }

cLQd11GprTable OBJECT-TYPE
    SYNTAX SEQUENCE OF CLQd11GprEntry
    ACCESS not-accessible
    STATUS mandatory
    DESCRIPTION
        "This table populates the GPR configuration on the
        WLANs configured on this controller.  
        
        There exists a row in this table for each WLAN
        configured through cLWlanConfigTable.  A row is added
        is to this table by the agent when a WLAN is created
        by the user through an explicit management action
        initiated from a network management station.
        Similarly a row gets deleted automatically when the
        user deletes the particular WLAN."
    ::= { cLQd11GprConfig 1 }

cLQd11GprEntry OBJECT-TYPE
    SYNTAX CLQd11GprEntry
    ACCESS not-accessible
    STATUS mandatory
    DESCRIPTION
        "Each entry represents a conceptual row in
        cLQd11GprTable and corresponds to the
        GPR configuration on a WLAN."
    INDEX { cLWlanIndex }
-- Augments cLWlanConfigEntry FROM CISCO-LWAPP-WLAN-MIB
    ::= { cLQd11GprTable 1 }

CLQd11GprEntry ::= SEQUENCE {
    cLQd11GprSupport TruthValue
    }

cLQd11GprSupport OBJECT-TYPE
    SYNTAX TruthValue
--    Rsyntax INTEGER {
--        true(1),
--        false(2)
--        }
    ACCESS read-write
    STATUS mandatory
    DESCRIPTION
        "If 'true', then the corresponding radios that
        advertise this WLAN, will send Gratuitous Probe 
        Response.  If 'false', then the corresponding radios 
        that advertise this WLAN, will not send Gratuitous 
        Probe Response."
    DEFVAL { false }
    ::= { cLQd11GprEntry 1 }

cLQd11CACStatsTable OBJECT-TYPE
    SYNTAX SEQUENCE OF CLQd11CACStatsEntry
    ACCESS not-accessible
    STATUS mandatory
    DESCRIPTION
        "This table populates the call admission control
        metrics collected by observing the voice or video
        traffic on the dot11 interface of a particular
        AP. 
        
        There exists a row in this table for each row
        corresponding to a dot11 interface found in
        cLApDot11IfTable.  A row corresponding to a
        dot11 interface is added when an AP joins the
        controller.  The row gets deleted when the AP
        dissociates from the controller."
    ::= { cLQd11CACStats 1 }

cLQd11CACStatsEntry OBJECT-TYPE
    SYNTAX CLQd11CACStatsEntry
    ACCESS not-accessible
    STATUS mandatory
    DESCRIPTION
        "Each entry represents a conceptual row in
        CLQd11CACStatsTable and corresponds to the 
        admission control statistics for a particular
        dot11 interface."
    INDEX { cLApSysMacAddress, cLApDot11IfSlotId }
-- Augments cLApDot11IfEntry FROM CISCO-LWAPP-AP-MIB
    ::= { cLQd11CACStatsTable 1 }

CLQd11CACStatsEntry ::= SEQUENCE {
    cLQd11CacVoiceBwInUse Gauge,
    cLQd11CacVideoBwInUse Gauge,
    cLQd11CacVoiceCallsInProgress Gauge,
    cLQd11CacRoamVoiceCallsInProg Gauge,
    cLQd11CacTotalVoiceCallsAP Counter,
    cLQd11CacTotalRoamCallsAP Counter,
    cLQd11CacVoiceCallsRejectedAP Counter,
    cLQd11CacRoamCallsRejectedAP Counter,
    cLQd11CacRejCallsInsufBw Counter,
    cLQd11CacRejCallsBadParams Counter,
    cLQd11CacRejCallsPhyRate Counter,
    cLQd11CacRejCallsQosPolicy Counter
    }

cLQd11CacVoiceBwInUse OBJECT-TYPE
    SYNTAX Gauge(0..100)
--  Units
--    Percent
    ACCESS read-only
    STATUS mandatory
    DESCRIPTION
        "This object indicates the voice bandwidth in use
        as a percentage of the bandwidth configured through
        cLQd11aVoiceMaxAdmBandwidth or
        cLQd11bVoiceMaxAdmBandwidth, depending on the type
        of this dot11 interface."
    ::= { cLQd11CACStatsEntry 1 }

cLQd11CacVideoBwInUse OBJECT-TYPE
    SYNTAX Gauge(0..100)
--  Units
--    Percent
    ACCESS read-only
    STATUS mandatory
    DESCRIPTION
        "This object indicates the video bandwidth in use
        as a percentage of the bandwidth configured through
        cLQd11aVideoMaxAdmBandwidth or
        cLQd11bVideoMaxAdmBandwidth, depending on the type
        of this dot11 interface."
    ::= { cLQd11CACStatsEntry 2 }

cLQd11CacVoiceCallsInProgress OBJECT-TYPE
    SYNTAX Gauge
    ACCESS read-only
    STATUS mandatory
    DESCRIPTION
        "This object indicates the count of the number of
        voice calls currently in progress on this dot11
        interface."
    ::= { cLQd11CACStatsEntry 3 }

cLQd11CacRoamVoiceCallsInProg OBJECT-TYPE
    SYNTAX Gauge
    ACCESS read-only
    STATUS mandatory
    DESCRIPTION
        "This object indicates the count of the number of
        voice calls initiated from roaming clients
        currently in progress on this dot11 interface."
    ::= { cLQd11CACStatsEntry 4 }

cLQd11CacTotalVoiceCallsAP OBJECT-TYPE
    SYNTAX Counter
    ACCESS read-only
    STATUS mandatory
    DESCRIPTION
        "This object indicates the count of the number of
        voice calls observed on this dot11 interface
        ever since this AP has joined the controller."
    ::= { cLQd11CACStatsEntry 5 }

cLQd11CacTotalRoamCallsAP OBJECT-TYPE
    SYNTAX Counter
    ACCESS read-only
    STATUS mandatory
    DESCRIPTION
        "This object indicates the count of the number of
        voice and video calls initiated from roaming clients
        observed on this dot11 interface ever since
        this AP has joined the controller."
    ::= { cLQd11CACStatsEntry 6 }

cLQd11CacVoiceCallsRejectedAP OBJECT-TYPE
    SYNTAX Counter
    ACCESS read-only
    STATUS mandatory
    DESCRIPTION
        "This object indicates the count of the number of
        voice calls observed as rejected on this dot11
        interface, ever since this AP has joined the
        controller."
    ::= { cLQd11CACStatsEntry 7 }

cLQd11CacRoamCallsRejectedAP OBJECT-TYPE
    SYNTAX Counter
    ACCESS read-only
    STATUS mandatory
    DESCRIPTION
        "This object indicates the count of the number of
        voice and video calls initiated from roaming
        clients observed as rejected on this dot11
        interface, ever since this AP has joined the
        controller."
    ::= { cLQd11CACStatsEntry 8 }

cLQd11CacRejCallsInsufBw OBJECT-TYPE
    SYNTAX Counter
    ACCESS read-only
    STATUS mandatory
    DESCRIPTION
        "This object indicates the count of the number of
        calls observed as rejected on this dot11
        interface due to insufficient bandwidth, ever
        since this AP has joined the controller."
    ::= { cLQd11CACStatsEntry 9 }

cLQd11CacRejCallsBadParams OBJECT-TYPE
    SYNTAX Counter
    ACCESS read-only
    STATUS mandatory
    DESCRIPTION
        "This object indicates the count of the number of
        calls observed as rejected on this dot11
        interface due to mismatch in call parameters, ever
        since this AP has joined the controller."
    ::= { cLQd11CACStatsEntry 10 }

cLQd11CacRejCallsPhyRate OBJECT-TYPE
    SYNTAX Counter
    ACCESS read-only
    STATUS mandatory
    DESCRIPTION
        "This object indicates the count of the number of
        calls observed as rejected on this dot11
        interface due to mismatch in 802.11 data rates,
        ever since this AP has joined the controller."
    ::= { cLQd11CACStatsEntry 11 }

cLQd11CacRejCallsQosPolicy OBJECT-TYPE
    SYNTAX Counter
    ACCESS read-only
    STATUS mandatory
    DESCRIPTION
        "This object indicates the count of the number of
        calls observed as rejected on this dot11
        interface due to restrictions imposed by QOS
        policies, ever since this AP has joined the
        controller."
    ::= { cLQd11CACStatsEntry 12 }

ciscoLwappQosDot11aConfigGroup OBJECT IDENTIFIER ::= { ciscoLwappQosMIBGroups 1 }
-- OBJECT-GROUP
--  Status
--    mandatory
--  Descr
--    This collection of objects represents the
--    quality-of-service parameters 802.11a networks.
--  objects
--    cLQd11aVoiceAdmCtrlSupport, cLQd11aVoiceMaxAdmBandwidth, 
--    cLQd11aVoiceMaxRoamBandwidth, cLQd11aVideoAdmCtrlSupport, 
--    cLQd11aVideoMaxAdmBandwidth, cLQd11aVideoMaxRoamBandwidth, 
--    cLQd11aGprProbeInterval

ciscoLwappQosDot11bConfigGroup OBJECT IDENTIFIER ::= { ciscoLwappQosMIBGroups 2 }
-- OBJECT-GROUP
--  Status
--    mandatory
--  Descr
--    This collection of objects represents the
--    quality-of-service parameters 802.11b networks.
--  objects
--    cLQd11bVoiceAdmCtrlSupport, cLQd11bVoiceMaxAdmBandwidth, 
--    cLQd11bVoiceMaxRoamBandwidth, cLQd11bVideoAdmCtrlSupport, 
--    cLQd11bVideoMaxAdmBandwidth, cLQd11bVideoMaxRoamBandwidth, 
--    cLQd11bGprProbeInterval

ciscoLwappQosDot11WlanConfigGroup OBJECT IDENTIFIER ::= { ciscoLwappQosMIBGroups 3 }
-- OBJECT-GROUP
--  Status
--    mandatory
--  Descr
--    This collection of objects represents the
--    quality-of-services parameters on a particular WLAN.
--  objects
--    cLQd11GprSupport

ciscoLwappQosDot11CacStatsGroup OBJECT IDENTIFIER ::= { ciscoLwappQosMIBGroups 4 }
-- OBJECT-GROUP
--  Status
--    mandatory
--  Descr
--    This collection of objects provide the call
--    admission control statistics observed on the
--    dot11 interfaces of an AP.
--  objects
--    cLQd11CacVoiceBwInUse, cLQd11CacVideoBwInUse, 
--    cLQd11CacVoiceCallsInProgress, cLQd11CacRoamVoiceCallsInProg, 
--    cLQd11CacTotalVoiceCallsAP, cLQd11CacTotalRoamCallsAP, 
--    cLQd11CacVoiceCallsRejectedAP, cLQd11CacRoamCallsRejectedAP, 
--    cLQd11CacRejCallsInsufBw, cLQd11CacRejCallsBadParams, 
--    cLQd11CacRejCallsPhyRate, cLQd11CacRejCallsQosPolicy

ciscoLwappQosDot11aConfigGroupSup1 OBJECT IDENTIFIER ::= { ciscoLwappQosMIBGroups 5 }
-- OBJECT-GROUP
--  Status
--    mandatory
--  Descr
--    This collection of objects represents the
--    quality-of-service parameters 802.11a networks.
--  objects
--    cLQd11aVoiceCtrl, cLQd11aExpeditedBw

ciscoLwappQosDot11bConfigGroupSup1 OBJECT IDENTIFIER ::= { ciscoLwappQosMIBGroups 6 }
-- OBJECT-GROUP
--  Status
--    mandatory
--  Descr
--    This collection of objects represents the
--    quality-of-service parameters 802.11b networks.
--  objects
--    cLQd11bVoiceCtrl, cLQd11bExpeditedBw

ciscoLwappQosMIBCompliance OBJECT IDENTIFIER ::= { ciscoLwappQosMIBCompliances 1 }
-- MODULE-COMPLIANCE
--  Status
--    deprecated
--  Descr
--    The compliance statement for the SNMP entities that
--    implement the ciscoLwappQosMIB module.
--  Module
--    >>current<<
--   MandGroup
--    ciscoLwappQosDot11aConfigGroup
--   MandGroup
--    ciscoLwappQosDot11bConfigGroup
--   MandGroup
--    ciscoLwappQosDot11WlanConfigGroup
--   MandGroup
--    ciscoLwappQosDot11CacStatsGroup

ciscoLwappQosMIBComplianceRev1 OBJECT IDENTIFIER ::= { ciscoLwappQosMIBCompliances 2 }
-- MODULE-COMPLIANCE
--  Status
--    mandatory
--  Descr
--    The compliance statement for the SNMP entities that
--    implement the ciscoLwappQosMIB module.
--  Module
--    >>current<<
--   MandGroup
--    ciscoLwappQosDot11aConfigGroup
--   MandGroup
--    ciscoLwappQosDot11bConfigGroup
--   MandGroup
--    ciscoLwappQosDot11WlanConfigGroup
--   MandGroup
--    ciscoLwappQosDot11CacStatsGroup
--   MandGroup
--    ciscoLwappQosDot11aConfigGroupSup1
--   MandGroup
--    ciscoLwappQosDot11bConfigGroupSup1


END
