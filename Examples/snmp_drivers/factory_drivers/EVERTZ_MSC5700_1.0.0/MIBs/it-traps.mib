-- Copyright Evertz Microsystems Ltd.

IT-TRAPS DEFINITIONS ::= BEGIN

IMPORTS
	itInstance, itTraps
		FROM IT-MIB
	TRAP-TYPE
		FROM RFC-1215;

	trapFault	OBJECT IDENTIFIER ::= { itTraps 1 }

-- beginning of opticalLinkLoss  trap

	faultopticalLinkLossFalse TRAP-TYPE
		ENTERPRISE	trapFault
		VARIABLES	{ itInstance }
		DESCRIPTION
			"Optical Link Loss False"
	::= 1000

	faultopticalLinkLossTrue TRAP-TYPE
		ENTERPRISE	trapFault
		VARIABLES	{ itInstance }
		DESCRIPTION
			"Optical Link Loss True"
	::= 1001

-- end of opticalLinkLoss  trap
-- beginning of laserError  trap

	faultlaserErrorFalse TRAP-TYPE
		ENTERPRISE	trapFault
		VARIABLES	{ itInstance }
		DESCRIPTION
			"Laser Error False"
	::= 1002

	faultlaserErrorTrue TRAP-TYPE
		ENTERPRISE	trapFault
		VARIABLES	{ itInstance }
		DESCRIPTION
			"Laser Error True"
	::= 1003

-- end of laserError  trap
-- beginning of opticalPowerAlarmThreshold  trap

	faultopticalPowerAlarmThresholdFalse TRAP-TYPE
		ENTERPRISE	trapFault
		VARIABLES	{ itInstance }
		DESCRIPTION
			"Optical Power Alarm Threshold False"
	::= 1004

	faultopticalPowerAlarmThresholdTrue TRAP-TYPE
		ENTERPRISE	trapFault
		VARIABLES	{ itInstance }
		DESCRIPTION
			"Optical Power Alarm Threshold True"
	::= 1005

-- end of opticalPowerAlarmThreshold  trap


END
