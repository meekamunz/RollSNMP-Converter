-- Copyright 2005 Evertz Microsystems Ltd.
-- Thu Aug 25 12:55:50 2005
-- Confidential

OV-TRAPS DEFINITIONS ::= BEGIN

IMPORTS
    trapTag, ovTraps
        FROM OV-MIB
    TRAP-TYPE
        FROM RFC-1215;

    trapFault OBJECT IDENTIFIER ::= { ovTraps 1 }


-- beginning of lossOfVideoSync Input1 trap

    faultlossOfVideoSyncInput1False TRAP-TYPE
        ENTERPRISE  trapFault
        VARIABLES   { trapTag }
        DESCRIPTION
            "Loss of Video Sync Cleared on Input1"
    ::= 1000
    
    faultlossOfVideoSyncInput1True TRAP-TYPE
        ENTERPRISE  trapFault
        VARIABLES   { trapTag }
        DESCRIPTION
            "Loss of Video Sync Alert on Input1"
    ::= 1001

-- end of lossOfVideoSync Input1 trap

-- beginning of lossOfVideoSync Input2 trap

    faultlossOfVideoSyncInput2False TRAP-TYPE
        ENTERPRISE  trapFault
        VARIABLES   { trapTag }
        DESCRIPTION
            "Loss of Video Sync Cleared on Input2"
    ::= 1002
    
    faultlossOfVideoSyncInput2True TRAP-TYPE
        ENTERPRISE  trapFault
        VARIABLES   { trapTag }
        DESCRIPTION
            "Loss of Video Sync Alert on Input2"
    ::= 1003

-- end of lossOfVideoSync Input2 trap

-- beginning of lossOfVideoSync Input3 trap

    faultlossOfVideoSyncInput3False TRAP-TYPE
        ENTERPRISE  trapFault
        VARIABLES   { trapTag }
        DESCRIPTION
            "Loss of Video Sync Cleared on Input3"
    ::= 1004
    
    faultlossOfVideoSyncInput3True TRAP-TYPE
        ENTERPRISE  trapFault
        VARIABLES   { trapTag }
        DESCRIPTION
            "Loss of Video Sync Alert on Input3"
    ::= 1005

-- end of lossOfVideoSync Input3 trap

-- beginning of lossOfVideoSync Input4 trap

    faultlossOfVideoSyncInput4False TRAP-TYPE
        ENTERPRISE  trapFault
        VARIABLES   { trapTag }
        DESCRIPTION
            "Loss of Video Sync Cleared on Input4"
    ::= 1006
    
    faultlossOfVideoSyncInput4True TRAP-TYPE
        ENTERPRISE  trapFault
        VARIABLES   { trapTag }
        DESCRIPTION
            "Loss of Video Sync Alert on Input4"
    ::= 1007

-- end of lossOfVideoSync Input4 trap

-- beginning of lossOfVideoSync Input5 trap

    faultlossOfVideoSyncInput5False TRAP-TYPE
        ENTERPRISE  trapFault
        VARIABLES   { trapTag }
        DESCRIPTION
            "Loss of Video Sync Cleared on Input5"
    ::= 1008
    
    faultlossOfVideoSyncInput5True TRAP-TYPE
        ENTERPRISE  trapFault
        VARIABLES   { trapTag }
        DESCRIPTION
            "Loss of Video Sync Alert on Input5"
    ::= 1009

-- end of lossOfVideoSync Input5 trap

-- beginning of lossOfVideoSync Input6 trap

    faultlossOfVideoSyncInput6False TRAP-TYPE
        ENTERPRISE  trapFault
        VARIABLES   { trapTag }
        DESCRIPTION
            "Loss of Video Sync Cleared on Input6"
    ::= 1010
    
    faultlossOfVideoSyncInput6True TRAP-TYPE
        ENTERPRISE  trapFault
        VARIABLES   { trapTag }
        DESCRIPTION
            "Loss of Video Sync Alert on Input6"
    ::= 1011

-- end of lossOfVideoSync Input6 trap

-- beginning of lossOfVideoSync Input7 trap

    faultlossOfVideoSyncInput7False TRAP-TYPE
        ENTERPRISE  trapFault
        VARIABLES   { trapTag }
        DESCRIPTION
            "Loss of Video Sync Cleared on Input7"
    ::= 1012
    
    faultlossOfVideoSyncInput7True TRAP-TYPE
        ENTERPRISE  trapFault
        VARIABLES   { trapTag }
        DESCRIPTION
            "Loss of Video Sync Alert on Input7"
    ::= 1013

-- end of lossOfVideoSync Input7 trap

-- beginning of lossOfVideoSync Input8 trap

    faultlossOfVideoSyncInput8False TRAP-TYPE
        ENTERPRISE  trapFault
        VARIABLES   { trapTag }
        DESCRIPTION
            "Loss of Video Sync Cleared on Input8"
    ::= 1014
    
    faultlossOfVideoSyncInput8True TRAP-TYPE
        ENTERPRISE  trapFault
        VARIABLES   { trapTag }
        DESCRIPTION
            "Loss of Video Sync Alert on Input8"
    ::= 1015

-- end of lossOfVideoSync Input8 trap

-- beginning of lossOfVideoBurst Input1 trap

    faultlossOfVideoBurstInput1False TRAP-TYPE
        ENTERPRISE  trapFault
        VARIABLES   { trapTag }
        DESCRIPTION
            "Loss of Video Burst Cleared on Input1"
    ::= 1016
    
    faultlossOfVideoBurstInput1True TRAP-TYPE
        ENTERPRISE  trapFault
        VARIABLES   { trapTag }
        DESCRIPTION
            "Loss of Video Burst Alert on Input1"
    ::= 1017

-- end of lossOfVideoBurst Input1 trap

-- beginning of lossOfVideoBurst Input2 trap

    faultlossOfVideoBurstInput2False TRAP-TYPE
        ENTERPRISE  trapFault
        VARIABLES   { trapTag }
        DESCRIPTION
            "Loss of Video Burst Cleared on Input2"
    ::= 1018
    
    faultlossOfVideoBurstInput2True TRAP-TYPE
        ENTERPRISE  trapFault
        VARIABLES   { trapTag }
        DESCRIPTION
            "Loss of Video Burst Alert on Input2"
    ::= 1019

-- end of lossOfVideoBurst Input2 trap

-- beginning of lossOfVideoBurst Input3 trap

    faultlossOfVideoBurstInput3False TRAP-TYPE
        ENTERPRISE  trapFault
        VARIABLES   { trapTag }
        DESCRIPTION
            "Loss of Video Burst Cleared on Input3"
    ::= 1020
    
    faultlossOfVideoBurstInput3True TRAP-TYPE
        ENTERPRISE  trapFault
        VARIABLES   { trapTag }
        DESCRIPTION
            "Loss of Video Burst Alert on Input3"
    ::= 1021

-- end of lossOfVideoBurst Input3 trap

-- beginning of lossOfVideoBurst Input4 trap

    faultlossOfVideoBurstInput4False TRAP-TYPE
        ENTERPRISE  trapFault
        VARIABLES   { trapTag }
        DESCRIPTION
            "Loss of Video Burst Cleared on Input4"
    ::= 1022
    
    faultlossOfVideoBurstInput4True TRAP-TYPE
        ENTERPRISE  trapFault
        VARIABLES   { trapTag }
        DESCRIPTION
            "Loss of Video Burst Alert on Input4"
    ::= 1023

-- end of lossOfVideoBurst Input4 trap

-- beginning of lossOfVideoBurst Input5 trap

    faultlossOfVideoBurstInput5False TRAP-TYPE
        ENTERPRISE  trapFault
        VARIABLES   { trapTag }
        DESCRIPTION
            "Loss of Video Burst Cleared on Input5"
    ::= 1024
    
    faultlossOfVideoBurstInput5True TRAP-TYPE
        ENTERPRISE  trapFault
        VARIABLES   { trapTag }
        DESCRIPTION
            "Loss of Video Burst Alert on Input5"
    ::= 1025

-- end of lossOfVideoBurst Input5 trap

-- beginning of lossOfVideoBurst Input6 trap

    faultlossOfVideoBurstInput6False TRAP-TYPE
        ENTERPRISE  trapFault
        VARIABLES   { trapTag }
        DESCRIPTION
            "Loss of Video Burst Cleared on Input6"
    ::= 1026
    
    faultlossOfVideoBurstInput6True TRAP-TYPE
        ENTERPRISE  trapFault
        VARIABLES   { trapTag }
        DESCRIPTION
            "Loss of Video Burst Alert on Input6"
    ::= 1027

-- end of lossOfVideoBurst Input6 trap

-- beginning of lossOfVideoBurst Input7 trap

    faultlossOfVideoBurstInput7False TRAP-TYPE
        ENTERPRISE  trapFault
        VARIABLES   { trapTag }
        DESCRIPTION
            "Loss of Video Burst Cleared on Input7"
    ::= 1028
    
    faultlossOfVideoBurstInput7True TRAP-TYPE
        ENTERPRISE  trapFault
        VARIABLES   { trapTag }
        DESCRIPTION
            "Loss of Video Burst Alert on Input7"
    ::= 1029

-- end of lossOfVideoBurst Input7 trap

-- beginning of lossOfVideoBurst Input8 trap

    faultlossOfVideoBurstInput8False TRAP-TYPE
        ENTERPRISE  trapFault
        VARIABLES   { trapTag }
        DESCRIPTION
            "Loss of Video Burst Cleared on Input8"
    ::= 1030
    
    faultlossOfVideoBurstInput8True TRAP-TYPE
        ENTERPRISE  trapFault
        VARIABLES   { trapTag }
        DESCRIPTION
            "Loss of Video Burst Alert on Input8"
    ::= 1031

-- end of lossOfVideoBurst Input8 trap

-- beginning of lossOfVideo Input1 trap

    faultlossOfVideoInput1False TRAP-TYPE
        ENTERPRISE  trapFault
        VARIABLES   { trapTag }
        DESCRIPTION
            "Loss of Video Cleared on Input1"
    ::= 1032
    
    faultlossOfVideoInput1True TRAP-TYPE
        ENTERPRISE  trapFault
        VARIABLES   { trapTag }
        DESCRIPTION
            "Loss of Video Alert on Input1"
    ::= 1033

-- end of lossOfVideo Input1 trap

-- beginning of lossOfVideo Input2 trap

    faultlossOfVideoInput2False TRAP-TYPE
        ENTERPRISE  trapFault
        VARIABLES   { trapTag }
        DESCRIPTION
            "Loss of Video Cleared on Input2"
    ::= 1034
    
    faultlossOfVideoInput2True TRAP-TYPE
        ENTERPRISE  trapFault
        VARIABLES   { trapTag }
        DESCRIPTION
            "Loss of Video Alert on Input2"
    ::= 1035

-- end of lossOfVideo Input2 trap

-- beginning of lossOfVideo Input3 trap

    faultlossOfVideoInput3False TRAP-TYPE
        ENTERPRISE  trapFault
        VARIABLES   { trapTag }
        DESCRIPTION
            "Loss of Video Cleared on Input3"
    ::= 1036
    
    faultlossOfVideoInput3True TRAP-TYPE
        ENTERPRISE  trapFault
        VARIABLES   { trapTag }
        DESCRIPTION
            "Loss of Video Alert on Input3"
    ::= 1037

-- end of lossOfVideo Input3 trap

-- beginning of lossOfVideo Input4 trap

    faultlossOfVideoInput4False TRAP-TYPE
        ENTERPRISE  trapFault
        VARIABLES   { trapTag }
        DESCRIPTION
            "Loss of Video Cleared on Input4"
    ::= 1038
    
    faultlossOfVideoInput4True TRAP-TYPE
        ENTERPRISE  trapFault
        VARIABLES   { trapTag }
        DESCRIPTION
            "Loss of Video Alert on Input4"
    ::= 1039

-- end of lossOfVideo Input4 trap

-- beginning of lossOfVideo Input5 trap

    faultlossOfVideoInput5False TRAP-TYPE
        ENTERPRISE  trapFault
        VARIABLES   { trapTag }
        DESCRIPTION
            "Loss of Video Cleared on Input5"
    ::= 1040
    
    faultlossOfVideoInput5True TRAP-TYPE
        ENTERPRISE  trapFault
        VARIABLES   { trapTag }
        DESCRIPTION
            "Loss of Video Alert on Input5"
    ::= 1041

-- end of lossOfVideo Input5 trap

-- beginning of lossOfVideo Input6 trap

    faultlossOfVideoInput6False TRAP-TYPE
        ENTERPRISE  trapFault
        VARIABLES   { trapTag }
        DESCRIPTION
            "Loss of Video Cleared on Input6"
    ::= 1042
    
    faultlossOfVideoInput6True TRAP-TYPE
        ENTERPRISE  trapFault
        VARIABLES   { trapTag }
        DESCRIPTION
            "Loss of Video Alert on Input6"
    ::= 1043

-- end of lossOfVideo Input6 trap

-- beginning of lossOfVideo Input7 trap

    faultlossOfVideoInput7False TRAP-TYPE
        ENTERPRISE  trapFault
        VARIABLES   { trapTag }
        DESCRIPTION
            "Loss of Video Cleared on Input7"
    ::= 1044
    
    faultlossOfVideoInput7True TRAP-TYPE
        ENTERPRISE  trapFault
        VARIABLES   { trapTag }
        DESCRIPTION
            "Loss of Video Alert on Input7"
    ::= 1045

-- end of lossOfVideo Input7 trap

-- beginning of lossOfVideo Input8 trap

    faultlossOfVideoInput8False TRAP-TYPE
        ENTERPRISE  trapFault
        VARIABLES   { trapTag }
        DESCRIPTION
            "Loss of Video Cleared on Input8"
    ::= 1046
    
    faultlossOfVideoInput8True TRAP-TYPE
        ENTERPRISE  trapFault
        VARIABLES   { trapTag }
        DESCRIPTION
            "Loss of Video Alert on Input8"
    ::= 1047

-- end of lossOfVideo Input8 trap

-- beginning of maxAPLError Input1 trap

    faultmaxAPLErrorInput1False TRAP-TYPE
        ENTERPRISE  trapFault
        VARIABLES   { trapTag }
        DESCRIPTION
            "APL Above Max Cleared on Input1"
    ::= 1048
    
    faultmaxAPLErrorInput1True TRAP-TYPE
        ENTERPRISE  trapFault
        VARIABLES   { trapTag }
        DESCRIPTION
            "APL Above Max Alert on Input1"
    ::= 1049

-- end of maxAPLError Input1 trap

-- beginning of maxAPLError Input2 trap

    faultmaxAPLErrorInput2False TRAP-TYPE
        ENTERPRISE  trapFault
        VARIABLES   { trapTag }
        DESCRIPTION
            "APL Above Max Cleared on Input2"
    ::= 1050
    
    faultmaxAPLErrorInput2True TRAP-TYPE
        ENTERPRISE  trapFault
        VARIABLES   { trapTag }
        DESCRIPTION
            "APL Above Max Alert on Input2"
    ::= 1051

-- end of maxAPLError Input2 trap

-- beginning of maxAPLError Input3 trap

    faultmaxAPLErrorInput3False TRAP-TYPE
        ENTERPRISE  trapFault
        VARIABLES   { trapTag }
        DESCRIPTION
            "APL Above Max Cleared on Input3"
    ::= 1052
    
    faultmaxAPLErrorInput3True TRAP-TYPE
        ENTERPRISE  trapFault
        VARIABLES   { trapTag }
        DESCRIPTION
            "APL Above Max Alert on Input3"
    ::= 1053

-- end of maxAPLError Input3 trap

-- beginning of maxAPLError Input4 trap

    faultmaxAPLErrorInput4False TRAP-TYPE
        ENTERPRISE  trapFault
        VARIABLES   { trapTag }
        DESCRIPTION
            "APL Above Max Cleared on Input4"
    ::= 1054
    
    faultmaxAPLErrorInput4True TRAP-TYPE
        ENTERPRISE  trapFault
        VARIABLES   { trapTag }
        DESCRIPTION
            "APL Above Max Alert on Input4"
    ::= 1055

-- end of maxAPLError Input4 trap

-- beginning of maxAPLError Input5 trap

    faultmaxAPLErrorInput5False TRAP-TYPE
        ENTERPRISE  trapFault
        VARIABLES   { trapTag }
        DESCRIPTION
            "APL Above Max Cleared on Input5"
    ::= 1056
    
    faultmaxAPLErrorInput5True TRAP-TYPE
        ENTERPRISE  trapFault
        VARIABLES   { trapTag }
        DESCRIPTION
            "APL Above Max Alert on Input5"
    ::= 1057

-- end of maxAPLError Input5 trap

-- beginning of maxAPLError Input6 trap

    faultmaxAPLErrorInput6False TRAP-TYPE
        ENTERPRISE  trapFault
        VARIABLES   { trapTag }
        DESCRIPTION
            "APL Above Max Cleared on Input6"
    ::= 1058
    
    faultmaxAPLErrorInput6True TRAP-TYPE
        ENTERPRISE  trapFault
        VARIABLES   { trapTag }
        DESCRIPTION
            "APL Above Max Alert on Input6"
    ::= 1059

-- end of maxAPLError Input6 trap

-- beginning of maxAPLError Input7 trap

    faultmaxAPLErrorInput7False TRAP-TYPE
        ENTERPRISE  trapFault
        VARIABLES   { trapTag }
        DESCRIPTION
            "APL Above Max Cleared on Input7"
    ::= 1060
    
    faultmaxAPLErrorInput7True TRAP-TYPE
        ENTERPRISE  trapFault
        VARIABLES   { trapTag }
        DESCRIPTION
            "APL Above Max Alert on Input7"
    ::= 1061

-- end of maxAPLError Input7 trap

-- beginning of maxAPLError Input8 trap

    faultmaxAPLErrorInput8False TRAP-TYPE
        ENTERPRISE  trapFault
        VARIABLES   { trapTag }
        DESCRIPTION
            "APL Above Max Cleared on Input8"
    ::= 1062
    
    faultmaxAPLErrorInput8True TRAP-TYPE
        ENTERPRISE  trapFault
        VARIABLES   { trapTag }
        DESCRIPTION
            "APL Above Max Alert on Input8"
    ::= 1063

-- end of maxAPLError Input8 trap

-- beginning of minAPLError Input1 trap

    faultminAPLErrorInput1False TRAP-TYPE
        ENTERPRISE  trapFault
        VARIABLES   { trapTag }
        DESCRIPTION
            "APL Below Min Cleared on Input1"
    ::= 1064
    
    faultminAPLErrorInput1True TRAP-TYPE
        ENTERPRISE  trapFault
        VARIABLES   { trapTag }
        DESCRIPTION
            "APL Below Min Alert on Input1"
    ::= 1065

-- end of minAPLError Input1 trap

-- beginning of minAPLError Input2 trap

    faultminAPLErrorInput2False TRAP-TYPE
        ENTERPRISE  trapFault
        VARIABLES   { trapTag }
        DESCRIPTION
            "APL Below Min Cleared on Input2"
    ::= 1066
    
    faultminAPLErrorInput2True TRAP-TYPE
        ENTERPRISE  trapFault
        VARIABLES   { trapTag }
        DESCRIPTION
            "APL Below Min Alert on Input2"
    ::= 1067

-- end of minAPLError Input2 trap

-- beginning of minAPLError Input3 trap

    faultminAPLErrorInput3False TRAP-TYPE
        ENTERPRISE  trapFault
        VARIABLES   { trapTag }
        DESCRIPTION
            "APL Below Min Cleared on Input3"
    ::= 1068
    
    faultminAPLErrorInput3True TRAP-TYPE
        ENTERPRISE  trapFault
        VARIABLES   { trapTag }
        DESCRIPTION
            "APL Below Min Alert on Input3"
    ::= 1069

-- end of minAPLError Input3 trap

-- beginning of minAPLError Input4 trap

    faultminAPLErrorInput4False TRAP-TYPE
        ENTERPRISE  trapFault
        VARIABLES   { trapTag }
        DESCRIPTION
            "APL Below Min Cleared on Input4"
    ::= 1070
    
    faultminAPLErrorInput4True TRAP-TYPE
        ENTERPRISE  trapFault
        VARIABLES   { trapTag }
        DESCRIPTION
            "APL Below Min Alert on Input4"
    ::= 1071

-- end of minAPLError Input4 trap

-- beginning of minAPLError Input5 trap

    faultminAPLErrorInput5False TRAP-TYPE
        ENTERPRISE  trapFault
        VARIABLES   { trapTag }
        DESCRIPTION
            "APL Below Min Cleared on Input5"
    ::= 1072
    
    faultminAPLErrorInput5True TRAP-TYPE
        ENTERPRISE  trapFault
        VARIABLES   { trapTag }
        DESCRIPTION
            "APL Below Min Alert on Input5"
    ::= 1073

-- end of minAPLError Input5 trap

-- beginning of minAPLError Input6 trap

    faultminAPLErrorInput6False TRAP-TYPE
        ENTERPRISE  trapFault
        VARIABLES   { trapTag }
        DESCRIPTION
            "APL Below Min Cleared on Input6"
    ::= 1074
    
    faultminAPLErrorInput6True TRAP-TYPE
        ENTERPRISE  trapFault
        VARIABLES   { trapTag }
        DESCRIPTION
            "APL Below Min Alert on Input6"
    ::= 1075

-- end of minAPLError Input6 trap

-- beginning of minAPLError Input7 trap

    faultminAPLErrorInput7False TRAP-TYPE
        ENTERPRISE  trapFault
        VARIABLES   { trapTag }
        DESCRIPTION
            "APL Below Min Cleared on Input7"
    ::= 1076
    
    faultminAPLErrorInput7True TRAP-TYPE
        ENTERPRISE  trapFault
        VARIABLES   { trapTag }
        DESCRIPTION
            "APL Below Min Alert on Input7"
    ::= 1077

-- end of minAPLError Input7 trap

-- beginning of minAPLError Input8 trap

    faultminAPLErrorInput8False TRAP-TYPE
        ENTERPRISE  trapFault
        VARIABLES   { trapTag }
        DESCRIPTION
            "APL Below Min Cleared on Input8"
    ::= 1078
    
    faultminAPLErrorInput8True TRAP-TYPE
        ENTERPRISE  trapFault
        VARIABLES   { trapTag }
        DESCRIPTION
            "APL Below Min Alert on Input8"
    ::= 1079

-- end of minAPLError Input8 trap

-- beginning of apEDHError Input1 trap

    faultapEDHErrorInput1False TRAP-TYPE
        ENTERPRISE  trapFault
        VARIABLES   { trapTag }
        DESCRIPTION
            "Active Picture EDH Error Cleared on Input1"
    ::= 1080
    
    faultapEDHErrorInput1True TRAP-TYPE
        ENTERPRISE  trapFault
        VARIABLES   { trapTag }
        DESCRIPTION
            "Active Picture EDH Error Alert on Input1"
    ::= 1081

-- end of apEDHError Input1 trap

-- beginning of apEDHError Input2 trap

    faultapEDHErrorInput2False TRAP-TYPE
        ENTERPRISE  trapFault
        VARIABLES   { trapTag }
        DESCRIPTION
            "Active Picture EDH Error Cleared on Input2"
    ::= 1082
    
    faultapEDHErrorInput2True TRAP-TYPE
        ENTERPRISE  trapFault
        VARIABLES   { trapTag }
        DESCRIPTION
            "Active Picture EDH Error Alert on Input2"
    ::= 1083

-- end of apEDHError Input2 trap

-- beginning of apEDHError Input3 trap

    faultapEDHErrorInput3False TRAP-TYPE
        ENTERPRISE  trapFault
        VARIABLES   { trapTag }
        DESCRIPTION
            "Active Picture EDH Error Cleared on Input3"
    ::= 1084
    
    faultapEDHErrorInput3True TRAP-TYPE
        ENTERPRISE  trapFault
        VARIABLES   { trapTag }
        DESCRIPTION
            "Active Picture EDH Error Alert on Input3"
    ::= 1085

-- end of apEDHError Input3 trap

-- beginning of apEDHError Input4 trap

    faultapEDHErrorInput4False TRAP-TYPE
        ENTERPRISE  trapFault
        VARIABLES   { trapTag }
        DESCRIPTION
            "Active Picture EDH Error Cleared on Input4"
    ::= 1086
    
    faultapEDHErrorInput4True TRAP-TYPE
        ENTERPRISE  trapFault
        VARIABLES   { trapTag }
        DESCRIPTION
            "Active Picture EDH Error Alert on Input4"
    ::= 1087

-- end of apEDHError Input4 trap

-- beginning of apEDHError Input5 trap

    faultapEDHErrorInput5False TRAP-TYPE
        ENTERPRISE  trapFault
        VARIABLES   { trapTag }
        DESCRIPTION
            "Active Picture EDH Error Cleared on Input5"
    ::= 1088
    
    faultapEDHErrorInput5True TRAP-TYPE
        ENTERPRISE  trapFault
        VARIABLES   { trapTag }
        DESCRIPTION
            "Active Picture EDH Error Alert on Input5"
    ::= 1089

-- end of apEDHError Input5 trap

-- beginning of apEDHError Input6 trap

    faultapEDHErrorInput6False TRAP-TYPE
        ENTERPRISE  trapFault
        VARIABLES   { trapTag }
        DESCRIPTION
            "Active Picture EDH Error Cleared on Input6"
    ::= 1090
    
    faultapEDHErrorInput6True TRAP-TYPE
        ENTERPRISE  trapFault
        VARIABLES   { trapTag }
        DESCRIPTION
            "Active Picture EDH Error Alert on Input6"
    ::= 1091

-- end of apEDHError Input6 trap

-- beginning of apEDHError Input7 trap

    faultapEDHErrorInput7False TRAP-TYPE
        ENTERPRISE  trapFault
        VARIABLES   { trapTag }
        DESCRIPTION
            "Active Picture EDH Error Cleared on Input7"
    ::= 1092
    
    faultapEDHErrorInput7True TRAP-TYPE
        ENTERPRISE  trapFault
        VARIABLES   { trapTag }
        DESCRIPTION
            "Active Picture EDH Error Alert on Input7"
    ::= 1093

-- end of apEDHError Input7 trap

-- beginning of apEDHError Input8 trap

    faultapEDHErrorInput8False TRAP-TYPE
        ENTERPRISE  trapFault
        VARIABLES   { trapTag }
        DESCRIPTION
            "Active Picture EDH Error Cleared on Input8"
    ::= 1094
    
    faultapEDHErrorInput8True TRAP-TYPE
        ENTERPRISE  trapFault
        VARIABLES   { trapTag }
        DESCRIPTION
            "Active Picture EDH Error Alert on Input8"
    ::= 1095

-- end of apEDHError Input8 trap

-- beginning of ffEDHError Input1 trap

    faultffEDHErrorInput1False TRAP-TYPE
        ENTERPRISE  trapFault
        VARIABLES   { trapTag }
        DESCRIPTION
            "Full Field EDH Error Cleared on Input1"
    ::= 1096
    
    faultffEDHErrorInput1True TRAP-TYPE
        ENTERPRISE  trapFault
        VARIABLES   { trapTag }
        DESCRIPTION
            "Full Field EDH Error Alert on Input1"
    ::= 1097

-- end of ffEDHError Input1 trap

-- beginning of ffEDHError Input2 trap

    faultffEDHErrorInput2False TRAP-TYPE
        ENTERPRISE  trapFault
        VARIABLES   { trapTag }
        DESCRIPTION
            "Full Field EDH Error Cleared on Input2"
    ::= 1098
    
    faultffEDHErrorInput2True TRAP-TYPE
        ENTERPRISE  trapFault
        VARIABLES   { trapTag }
        DESCRIPTION
            "Full Field EDH Error Alert on Input2"
    ::= 1099

-- end of ffEDHError Input2 trap

-- beginning of ffEDHError Input3 trap

    faultffEDHErrorInput3False TRAP-TYPE
        ENTERPRISE  trapFault
        VARIABLES   { trapTag }
        DESCRIPTION
            "Full Field EDH Error Cleared on Input3"
    ::= 1100
    
    faultffEDHErrorInput3True TRAP-TYPE
        ENTERPRISE  trapFault
        VARIABLES   { trapTag }
        DESCRIPTION
            "Full Field EDH Error Alert on Input3"
    ::= 1101

-- end of ffEDHError Input3 trap

-- beginning of ffEDHError Input4 trap

    faultffEDHErrorInput4False TRAP-TYPE
        ENTERPRISE  trapFault
        VARIABLES   { trapTag }
        DESCRIPTION
            "Full Field EDH Error Cleared on Input4"
    ::= 1102
    
    faultffEDHErrorInput4True TRAP-TYPE
        ENTERPRISE  trapFault
        VARIABLES   { trapTag }
        DESCRIPTION
            "Full Field EDH Error Alert on Input4"
    ::= 1103

-- end of ffEDHError Input4 trap

-- beginning of ffEDHError Input5 trap

    faultffEDHErrorInput5False TRAP-TYPE
        ENTERPRISE  trapFault
        VARIABLES   { trapTag }
        DESCRIPTION
            "Full Field EDH Error Cleared on Input5"
    ::= 1104
    
    faultffEDHErrorInput5True TRAP-TYPE
        ENTERPRISE  trapFault
        VARIABLES   { trapTag }
        DESCRIPTION
            "Full Field EDH Error Alert on Input5"
    ::= 1105

-- end of ffEDHError Input5 trap

-- beginning of ffEDHError Input6 trap

    faultffEDHErrorInput6False TRAP-TYPE
        ENTERPRISE  trapFault
        VARIABLES   { trapTag }
        DESCRIPTION
            "Full Field EDH Error Cleared on Input6"
    ::= 1106
    
    faultffEDHErrorInput6True TRAP-TYPE
        ENTERPRISE  trapFault
        VARIABLES   { trapTag }
        DESCRIPTION
            "Full Field EDH Error Alert on Input6"
    ::= 1107

-- end of ffEDHError Input6 trap

-- beginning of ffEDHError Input7 trap

    faultffEDHErrorInput7False TRAP-TYPE
        ENTERPRISE  trapFault
        VARIABLES   { trapTag }
        DESCRIPTION
            "Full Field EDH Error Cleared on Input7"
    ::= 1108
    
    faultffEDHErrorInput7True TRAP-TYPE
        ENTERPRISE  trapFault
        VARIABLES   { trapTag }
        DESCRIPTION
            "Full Field EDH Error Alert on Input7"
    ::= 1109

-- end of ffEDHError Input7 trap

-- beginning of ffEDHError Input8 trap

    faultffEDHErrorInput8False TRAP-TYPE
        ENTERPRISE  trapFault
        VARIABLES   { trapTag }
        DESCRIPTION
            "Full Field EDH Error Cleared on Input8"
    ::= 1110
    
    faultffEDHErrorInput8True TRAP-TYPE
        ENTERPRISE  trapFault
        VARIABLES   { trapTag }
        DESCRIPTION
            "Full Field EDH Error Alert on Input8"
    ::= 1111

-- end of ffEDHError Input8 trap

-- beginning of videoTypeChange Input1 trap

    faultvideoTypeChangeInput1False TRAP-TYPE
        ENTERPRISE  trapFault
        VARIABLES   { trapTag }
        DESCRIPTION
            "Video Type Change Cleared on Input1"
    ::= 1112
    
    faultvideoTypeChangeInput1True TRAP-TYPE
        ENTERPRISE  trapFault
        VARIABLES   { trapTag }
        DESCRIPTION
            "Video Type Change Alert on Input1"
    ::= 1113

-- end of videoTypeChange Input1 trap

-- beginning of videoTypeChange Input2 trap

    faultvideoTypeChangeInput2False TRAP-TYPE
        ENTERPRISE  trapFault
        VARIABLES   { trapTag }
        DESCRIPTION
            "Video Type Change Cleared on Input2"
    ::= 1114
    
    faultvideoTypeChangeInput2True TRAP-TYPE
        ENTERPRISE  trapFault
        VARIABLES   { trapTag }
        DESCRIPTION
            "Video Type Change Alert on Input2"
    ::= 1115

-- end of videoTypeChange Input2 trap

-- beginning of videoTypeChange Input3 trap

    faultvideoTypeChangeInput3False TRAP-TYPE
        ENTERPRISE  trapFault
        VARIABLES   { trapTag }
        DESCRIPTION
            "Video Type Change Cleared on Input3"
    ::= 1116
    
    faultvideoTypeChangeInput3True TRAP-TYPE
        ENTERPRISE  trapFault
        VARIABLES   { trapTag }
        DESCRIPTION
            "Video Type Change Alert on Input3"
    ::= 1117

-- end of videoTypeChange Input3 trap

-- beginning of videoTypeChange Input4 trap

    faultvideoTypeChangeInput4False TRAP-TYPE
        ENTERPRISE  trapFault
        VARIABLES   { trapTag }
        DESCRIPTION
            "Video Type Change Cleared on Input4"
    ::= 1118
    
    faultvideoTypeChangeInput4True TRAP-TYPE
        ENTERPRISE  trapFault
        VARIABLES   { trapTag }
        DESCRIPTION
            "Video Type Change Alert on Input4"
    ::= 1119

-- end of videoTypeChange Input4 trap

-- beginning of videoTypeChange Input5 trap

    faultvideoTypeChangeInput5False TRAP-TYPE
        ENTERPRISE  trapFault
        VARIABLES   { trapTag }
        DESCRIPTION
            "Video Type Change Cleared on Input5"
    ::= 1120
    
    faultvideoTypeChangeInput5True TRAP-TYPE
        ENTERPRISE  trapFault
        VARIABLES   { trapTag }
        DESCRIPTION
            "Video Type Change Alert on Input5"
    ::= 1121

-- end of videoTypeChange Input5 trap

-- beginning of videoTypeChange Input6 trap

    faultvideoTypeChangeInput6False TRAP-TYPE
        ENTERPRISE  trapFault
        VARIABLES   { trapTag }
        DESCRIPTION
            "Video Type Change Cleared on Input6"
    ::= 1122
    
    faultvideoTypeChangeInput6True TRAP-TYPE
        ENTERPRISE  trapFault
        VARIABLES   { trapTag }
        DESCRIPTION
            "Video Type Change Alert on Input6"
    ::= 1123

-- end of videoTypeChange Input6 trap

-- beginning of videoTypeChange Input7 trap

    faultvideoTypeChangeInput7False TRAP-TYPE
        ENTERPRISE  trapFault
        VARIABLES   { trapTag }
        DESCRIPTION
            "Video Type Change Cleared on Input7"
    ::= 1124
    
    faultvideoTypeChangeInput7True TRAP-TYPE
        ENTERPRISE  trapFault
        VARIABLES   { trapTag }
        DESCRIPTION
            "Video Type Change Alert on Input7"
    ::= 1125

-- end of videoTypeChange Input7 trap

-- beginning of videoTypeChange Input8 trap

    faultvideoTypeChangeInput8False TRAP-TYPE
        ENTERPRISE  trapFault
        VARIABLES   { trapTag }
        DESCRIPTION
            "Video Type Change Cleared on Input8"
    ::= 1126
    
    faultvideoTypeChangeInput8True TRAP-TYPE
        ENTERPRISE  trapFault
        VARIABLES   { trapTag }
        DESCRIPTION
            "Video Type Change Alert on Input8"
    ::= 1127

-- end of videoTypeChange Input8 trap

-- beginning of videoSourceChange Input1 trap

    faultvideoSourceChangeInput1False TRAP-TYPE
        ENTERPRISE  trapFault
        VARIABLES   { trapTag }
        DESCRIPTION
            "Video Source Changed Cleared on Input1"
    ::= 1128
    
    faultvideoSourceChangeInput1True TRAP-TYPE
        ENTERPRISE  trapFault
        VARIABLES   { trapTag }
        DESCRIPTION
            "Video Source Changed Alert on Input1"
    ::= 1129

-- end of videoSourceChange Input1 trap

-- beginning of videoSourceChange Input2 trap

    faultvideoSourceChangeInput2False TRAP-TYPE
        ENTERPRISE  trapFault
        VARIABLES   { trapTag }
        DESCRIPTION
            "Video Source Changed Cleared on Input2"
    ::= 1130
    
    faultvideoSourceChangeInput2True TRAP-TYPE
        ENTERPRISE  trapFault
        VARIABLES   { trapTag }
        DESCRIPTION
            "Video Source Changed Alert on Input2"
    ::= 1131

-- end of videoSourceChange Input2 trap

-- beginning of videoSourceChange Input3 trap

    faultvideoSourceChangeInput3False TRAP-TYPE
        ENTERPRISE  trapFault
        VARIABLES   { trapTag }
        DESCRIPTION
            "Video Source Changed Cleared on Input3"
    ::= 1132
    
    faultvideoSourceChangeInput3True TRAP-TYPE
        ENTERPRISE  trapFault
        VARIABLES   { trapTag }
        DESCRIPTION
            "Video Source Changed Alert on Input3"
    ::= 1133

-- end of videoSourceChange Input3 trap

-- beginning of videoSourceChange Input4 trap

    faultvideoSourceChangeInput4False TRAP-TYPE
        ENTERPRISE  trapFault
        VARIABLES   { trapTag }
        DESCRIPTION
            "Video Source Changed Cleared on Input4"
    ::= 1134
    
    faultvideoSourceChangeInput4True TRAP-TYPE
        ENTERPRISE  trapFault
        VARIABLES   { trapTag }
        DESCRIPTION
            "Video Source Changed Alert on Input4"
    ::= 1135

-- end of videoSourceChange Input4 trap

-- beginning of videoSourceChange Input5 trap

    faultvideoSourceChangeInput5False TRAP-TYPE
        ENTERPRISE  trapFault
        VARIABLES   { trapTag }
        DESCRIPTION
            "Video Source Changed Cleared on Input5"
    ::= 1136
    
    faultvideoSourceChangeInput5True TRAP-TYPE
        ENTERPRISE  trapFault
        VARIABLES   { trapTag }
        DESCRIPTION
            "Video Source Changed Alert on Input5"
    ::= 1137

-- end of videoSourceChange Input5 trap

-- beginning of videoSourceChange Input6 trap

    faultvideoSourceChangeInput6False TRAP-TYPE
        ENTERPRISE  trapFault
        VARIABLES   { trapTag }
        DESCRIPTION
            "Video Source Changed Cleared on Input6"
    ::= 1138
    
    faultvideoSourceChangeInput6True TRAP-TYPE
        ENTERPRISE  trapFault
        VARIABLES   { trapTag }
        DESCRIPTION
            "Video Source Changed Alert on Input6"
    ::= 1139

-- end of videoSourceChange Input6 trap

-- beginning of videoSourceChange Input7 trap

    faultvideoSourceChangeInput7False TRAP-TYPE
        ENTERPRISE  trapFault
        VARIABLES   { trapTag }
        DESCRIPTION
            "Video Source Changed Cleared on Input7"
    ::= 1140
    
    faultvideoSourceChangeInput7True TRAP-TYPE
        ENTERPRISE  trapFault
        VARIABLES   { trapTag }
        DESCRIPTION
            "Video Source Changed Alert on Input7"
    ::= 1141

-- end of videoSourceChange Input7 trap

-- beginning of videoSourceChange Input8 trap

    faultvideoSourceChangeInput8False TRAP-TYPE
        ENTERPRISE  trapFault
        VARIABLES   { trapTag }
        DESCRIPTION
            "Video Source Changed Cleared on Input8"
    ::= 1142
    
    faultvideoSourceChangeInput8True TRAP-TYPE
        ENTERPRISE  trapFault
        VARIABLES   { trapTag }
        DESCRIPTION
            "Video Source Changed Alert on Input8"
    ::= 1143

-- end of videoSourceChange Input8 trap

-- beginning of apPictureFreeze Input1 trap

    faultapPictureFreezeInput1False TRAP-TYPE
        ENTERPRISE  trapFault
        VARIABLES   { trapTag }
        DESCRIPTION
            "Active Picture Frozen Cleared on Input1"
    ::= 1144
    
    faultapPictureFreezeInput1True TRAP-TYPE
        ENTERPRISE  trapFault
        VARIABLES   { trapTag }
        DESCRIPTION
            "Active Picture Frozen Alert on Input1"
    ::= 1145

-- end of apPictureFreeze Input1 trap

-- beginning of apPictureFreeze Input2 trap

    faultapPictureFreezeInput2False TRAP-TYPE
        ENTERPRISE  trapFault
        VARIABLES   { trapTag }
        DESCRIPTION
            "Active Picture Frozen Cleared on Input2"
    ::= 1146
    
    faultapPictureFreezeInput2True TRAP-TYPE
        ENTERPRISE  trapFault
        VARIABLES   { trapTag }
        DESCRIPTION
            "Active Picture Frozen Alert on Input2"
    ::= 1147

-- end of apPictureFreeze Input2 trap

-- beginning of apPictureFreeze Input3 trap

    faultapPictureFreezeInput3False TRAP-TYPE
        ENTERPRISE  trapFault
        VARIABLES   { trapTag }
        DESCRIPTION
            "Active Picture Frozen Cleared on Input3"
    ::= 1148
    
    faultapPictureFreezeInput3True TRAP-TYPE
        ENTERPRISE  trapFault
        VARIABLES   { trapTag }
        DESCRIPTION
            "Active Picture Frozen Alert on Input3"
    ::= 1149

-- end of apPictureFreeze Input3 trap

-- beginning of apPictureFreeze Input4 trap

    faultapPictureFreezeInput4False TRAP-TYPE
        ENTERPRISE  trapFault
        VARIABLES   { trapTag }
        DESCRIPTION
            "Active Picture Frozen Cleared on Input4"
    ::= 1150
    
    faultapPictureFreezeInput4True TRAP-TYPE
        ENTERPRISE  trapFault
        VARIABLES   { trapTag }
        DESCRIPTION
            "Active Picture Frozen Alert on Input4"
    ::= 1151

-- end of apPictureFreeze Input4 trap

-- beginning of apPictureFreeze Input5 trap

    faultapPictureFreezeInput5False TRAP-TYPE
        ENTERPRISE  trapFault
        VARIABLES   { trapTag }
        DESCRIPTION
            "Active Picture Frozen Cleared on Input5"
    ::= 1152
    
    faultapPictureFreezeInput5True TRAP-TYPE
        ENTERPRISE  trapFault
        VARIABLES   { trapTag }
        DESCRIPTION
            "Active Picture Frozen Alert on Input5"
    ::= 1153

-- end of apPictureFreeze Input5 trap

-- beginning of apPictureFreeze Input6 trap

    faultapPictureFreezeInput6False TRAP-TYPE
        ENTERPRISE  trapFault
        VARIABLES   { trapTag }
        DESCRIPTION
            "Active Picture Frozen Cleared on Input6"
    ::= 1154
    
    faultapPictureFreezeInput6True TRAP-TYPE
        ENTERPRISE  trapFault
        VARIABLES   { trapTag }
        DESCRIPTION
            "Active Picture Frozen Alert on Input6"
    ::= 1155

-- end of apPictureFreeze Input6 trap

-- beginning of apPictureFreeze Input7 trap

    faultapPictureFreezeInput7False TRAP-TYPE
        ENTERPRISE  trapFault
        VARIABLES   { trapTag }
        DESCRIPTION
            "Active Picture Frozen Cleared on Input7"
    ::= 1156
    
    faultapPictureFreezeInput7True TRAP-TYPE
        ENTERPRISE  trapFault
        VARIABLES   { trapTag }
        DESCRIPTION
            "Active Picture Frozen Alert on Input7"
    ::= 1157

-- end of apPictureFreeze Input7 trap

-- beginning of apPictureFreeze Input8 trap

    faultapPictureFreezeInput8False TRAP-TYPE
        ENTERPRISE  trapFault
        VARIABLES   { trapTag }
        DESCRIPTION
            "Active Picture Frozen Cleared on Input8"
    ::= 1158
    
    faultapPictureFreezeInput8True TRAP-TYPE
        ENTERPRISE  trapFault
        VARIABLES   { trapTag }
        DESCRIPTION
            "Active Picture Frozen Alert on Input8"
    ::= 1159

-- end of apPictureFreeze Input8 trap

-- beginning of raPictureFreeze Input1 trap

    faultraPictureFreezeInput1False TRAP-TYPE
        ENTERPRISE  trapFault
        VARIABLES   { trapTag }
        DESCRIPTION
            "Regionalized Area Picture Frozen Cleared on Input1"
    ::= 1160
    
    faultraPictureFreezeInput1True TRAP-TYPE
        ENTERPRISE  trapFault
        VARIABLES   { trapTag }
        DESCRIPTION
            "Regionalized Area Picture Frozen Alert on Input1"
    ::= 1161

-- end of raPictureFreeze Input1 trap

-- beginning of raPictureFreeze Input2 trap

    faultraPictureFreezeInput2False TRAP-TYPE
        ENTERPRISE  trapFault
        VARIABLES   { trapTag }
        DESCRIPTION
            "Regionalized Area Picture Frozen Cleared on Input2"
    ::= 1162
    
    faultraPictureFreezeInput2True TRAP-TYPE
        ENTERPRISE  trapFault
        VARIABLES   { trapTag }
        DESCRIPTION
            "Regionalized Area Picture Frozen Alert on Input2"
    ::= 1163

-- end of raPictureFreeze Input2 trap

-- beginning of raPictureFreeze Input3 trap

    faultraPictureFreezeInput3False TRAP-TYPE
        ENTERPRISE  trapFault
        VARIABLES   { trapTag }
        DESCRIPTION
            "Regionalized Area Picture Frozen Cleared on Input3"
    ::= 1164
    
    faultraPictureFreezeInput3True TRAP-TYPE
        ENTERPRISE  trapFault
        VARIABLES   { trapTag }
        DESCRIPTION
            "Regionalized Area Picture Frozen Alert on Input3"
    ::= 1165

-- end of raPictureFreeze Input3 trap

-- beginning of raPictureFreeze Input4 trap

    faultraPictureFreezeInput4False TRAP-TYPE
        ENTERPRISE  trapFault
        VARIABLES   { trapTag }
        DESCRIPTION
            "Regionalized Area Picture Frozen Cleared on Input4"
    ::= 1166
    
    faultraPictureFreezeInput4True TRAP-TYPE
        ENTERPRISE  trapFault
        VARIABLES   { trapTag }
        DESCRIPTION
            "Regionalized Area Picture Frozen Alert on Input4"
    ::= 1167

-- end of raPictureFreeze Input4 trap

-- beginning of raPictureFreeze Input5 trap

    faultraPictureFreezeInput5False TRAP-TYPE
        ENTERPRISE  trapFault
        VARIABLES   { trapTag }
        DESCRIPTION
            "Regionalized Area Picture Frozen Cleared on Input5"
    ::= 1168
    
    faultraPictureFreezeInput5True TRAP-TYPE
        ENTERPRISE  trapFault
        VARIABLES   { trapTag }
        DESCRIPTION
            "Regionalized Area Picture Frozen Alert on Input5"
    ::= 1169

-- end of raPictureFreeze Input5 trap

-- beginning of raPictureFreeze Input6 trap

    faultraPictureFreezeInput6False TRAP-TYPE
        ENTERPRISE  trapFault
        VARIABLES   { trapTag }
        DESCRIPTION
            "Regionalized Area Picture Frozen Cleared on Input6"
    ::= 1170
    
    faultraPictureFreezeInput6True TRAP-TYPE
        ENTERPRISE  trapFault
        VARIABLES   { trapTag }
        DESCRIPTION
            "Regionalized Area Picture Frozen Alert on Input6"
    ::= 1171

-- end of raPictureFreeze Input6 trap

-- beginning of raPictureFreeze Input7 trap

    faultraPictureFreezeInput7False TRAP-TYPE
        ENTERPRISE  trapFault
        VARIABLES   { trapTag }
        DESCRIPTION
            "Regionalized Area Picture Frozen Cleared on Input7"
    ::= 1172
    
    faultraPictureFreezeInput7True TRAP-TYPE
        ENTERPRISE  trapFault
        VARIABLES   { trapTag }
        DESCRIPTION
            "Regionalized Area Picture Frozen Alert on Input7"
    ::= 1173

-- end of raPictureFreeze Input7 trap

-- beginning of raPictureFreeze Input8 trap

    faultraPictureFreezeInput8False TRAP-TYPE
        ENTERPRISE  trapFault
        VARIABLES   { trapTag }
        DESCRIPTION
            "Regionalized Area Picture Frozen Cleared on Input8"
    ::= 1174
    
    faultraPictureFreezeInput8True TRAP-TYPE
        ENTERPRISE  trapFault
        VARIABLES   { trapTag }
        DESCRIPTION
            "Regionalized Area Picture Frozen Alert on Input8"
    ::= 1175

-- end of raPictureFreeze Input8 trap

-- beginning of apPictureMotion Input1 trap

    faultapPictureMotionInput1False TRAP-TYPE
        ENTERPRISE  trapFault
        VARIABLES   { trapTag }
        DESCRIPTION
            "Active Picture Motion Cleared on Input1"
    ::= 1176
    
    faultapPictureMotionInput1True TRAP-TYPE
        ENTERPRISE  trapFault
        VARIABLES   { trapTag }
        DESCRIPTION
            "Active Picture Motion Alert on Input1"
    ::= 1177

-- end of apPictureMotion Input1 trap

-- beginning of apPictureMotion Input2 trap

    faultapPictureMotionInput2False TRAP-TYPE
        ENTERPRISE  trapFault
        VARIABLES   { trapTag }
        DESCRIPTION
            "Active Picture Motion Cleared on Input2"
    ::= 1178
    
    faultapPictureMotionInput2True TRAP-TYPE
        ENTERPRISE  trapFault
        VARIABLES   { trapTag }
        DESCRIPTION
            "Active Picture Motion Alert on Input2"
    ::= 1179

-- end of apPictureMotion Input2 trap

-- beginning of apPictureMotion Input3 trap

    faultapPictureMotionInput3False TRAP-TYPE
        ENTERPRISE  trapFault
        VARIABLES   { trapTag }
        DESCRIPTION
            "Active Picture Motion Cleared on Input3"
    ::= 1180
    
    faultapPictureMotionInput3True TRAP-TYPE
        ENTERPRISE  trapFault
        VARIABLES   { trapTag }
        DESCRIPTION
            "Active Picture Motion Alert on Input3"
    ::= 1181

-- end of apPictureMotion Input3 trap

-- beginning of apPictureMotion Input4 trap

    faultapPictureMotionInput4False TRAP-TYPE
        ENTERPRISE  trapFault
        VARIABLES   { trapTag }
        DESCRIPTION
            "Active Picture Motion Cleared on Input4"
    ::= 1182
    
    faultapPictureMotionInput4True TRAP-TYPE
        ENTERPRISE  trapFault
        VARIABLES   { trapTag }
        DESCRIPTION
            "Active Picture Motion Alert on Input4"
    ::= 1183

-- end of apPictureMotion Input4 trap

-- beginning of apPictureMotion Input5 trap

    faultapPictureMotionInput5False TRAP-TYPE
        ENTERPRISE  trapFault
        VARIABLES   { trapTag }
        DESCRIPTION
            "Active Picture Motion Cleared on Input5"
    ::= 1184
    
    faultapPictureMotionInput5True TRAP-TYPE
        ENTERPRISE  trapFault
        VARIABLES   { trapTag }
        DESCRIPTION
            "Active Picture Motion Alert on Input5"
    ::= 1185

-- end of apPictureMotion Input5 trap

-- beginning of apPictureMotion Input6 trap

    faultapPictureMotionInput6False TRAP-TYPE
        ENTERPRISE  trapFault
        VARIABLES   { trapTag }
        DESCRIPTION
            "Active Picture Motion Cleared on Input6"
    ::= 1186
    
    faultapPictureMotionInput6True TRAP-TYPE
        ENTERPRISE  trapFault
        VARIABLES   { trapTag }
        DESCRIPTION
            "Active Picture Motion Alert on Input6"
    ::= 1187

-- end of apPictureMotion Input6 trap

-- beginning of apPictureMotion Input7 trap

    faultapPictureMotionInput7False TRAP-TYPE
        ENTERPRISE  trapFault
        VARIABLES   { trapTag }
        DESCRIPTION
            "Active Picture Motion Cleared on Input7"
    ::= 1188
    
    faultapPictureMotionInput7True TRAP-TYPE
        ENTERPRISE  trapFault
        VARIABLES   { trapTag }
        DESCRIPTION
            "Active Picture Motion Alert on Input7"
    ::= 1189

-- end of apPictureMotion Input7 trap

-- beginning of apPictureMotion Input8 trap

    faultapPictureMotionInput8False TRAP-TYPE
        ENTERPRISE  trapFault
        VARIABLES   { trapTag }
        DESCRIPTION
            "Active Picture Motion Cleared on Input8"
    ::= 1190
    
    faultapPictureMotionInput8True TRAP-TYPE
        ENTERPRISE  trapFault
        VARIABLES   { trapTag }
        DESCRIPTION
            "Active Picture Motion Alert on Input8"
    ::= 1191

-- end of apPictureMotion Input8 trap

-- beginning of raPictureMotion Input1 trap

    faultraPictureMotionInput1False TRAP-TYPE
        ENTERPRISE  trapFault
        VARIABLES   { trapTag }
        DESCRIPTION
            "Regionalized Area Picture Motion Cleared on Input1"
    ::= 1192
    
    faultraPictureMotionInput1True TRAP-TYPE
        ENTERPRISE  trapFault
        VARIABLES   { trapTag }
        DESCRIPTION
            "Regionalized Area Picture Motion Alert on Input1"
    ::= 1193

-- end of raPictureMotion Input1 trap

-- beginning of raPictureMotion Input2 trap

    faultraPictureMotionInput2False TRAP-TYPE
        ENTERPRISE  trapFault
        VARIABLES   { trapTag }
        DESCRIPTION
            "Regionalized Area Picture Motion Cleared on Input2"
    ::= 1194
    
    faultraPictureMotionInput2True TRAP-TYPE
        ENTERPRISE  trapFault
        VARIABLES   { trapTag }
        DESCRIPTION
            "Regionalized Area Picture Motion Alert on Input2"
    ::= 1195

-- end of raPictureMotion Input2 trap

-- beginning of raPictureMotion Input3 trap

    faultraPictureMotionInput3False TRAP-TYPE
        ENTERPRISE  trapFault
        VARIABLES   { trapTag }
        DESCRIPTION
            "Regionalized Area Picture Motion Cleared on Input3"
    ::= 1196
    
    faultraPictureMotionInput3True TRAP-TYPE
        ENTERPRISE  trapFault
        VARIABLES   { trapTag }
        DESCRIPTION
            "Regionalized Area Picture Motion Alert on Input3"
    ::= 1197

-- end of raPictureMotion Input3 trap

-- beginning of raPictureMotion Input4 trap

    faultraPictureMotionInput4False TRAP-TYPE
        ENTERPRISE  trapFault
        VARIABLES   { trapTag }
        DESCRIPTION
            "Regionalized Area Picture Motion Cleared on Input4"
    ::= 1198
    
    faultraPictureMotionInput4True TRAP-TYPE
        ENTERPRISE  trapFault
        VARIABLES   { trapTag }
        DESCRIPTION
            "Regionalized Area Picture Motion Alert on Input4"
    ::= 1199

-- end of raPictureMotion Input4 trap

-- beginning of raPictureMotion Input5 trap

    faultraPictureMotionInput5False TRAP-TYPE
        ENTERPRISE  trapFault
        VARIABLES   { trapTag }
        DESCRIPTION
            "Regionalized Area Picture Motion Cleared on Input5"
    ::= 1200
    
    faultraPictureMotionInput5True TRAP-TYPE
        ENTERPRISE  trapFault
        VARIABLES   { trapTag }
        DESCRIPTION
            "Regionalized Area Picture Motion Alert on Input5"
    ::= 1201

-- end of raPictureMotion Input5 trap

-- beginning of raPictureMotion Input6 trap

    faultraPictureMotionInput6False TRAP-TYPE
        ENTERPRISE  trapFault
        VARIABLES   { trapTag }
        DESCRIPTION
            "Regionalized Area Picture Motion Cleared on Input6"
    ::= 1202
    
    faultraPictureMotionInput6True TRAP-TYPE
        ENTERPRISE  trapFault
        VARIABLES   { trapTag }
        DESCRIPTION
            "Regionalized Area Picture Motion Alert on Input6"
    ::= 1203

-- end of raPictureMotion Input6 trap

-- beginning of raPictureMotion Input7 trap

    faultraPictureMotionInput7False TRAP-TYPE
        ENTERPRISE  trapFault
        VARIABLES   { trapTag }
        DESCRIPTION
            "Regionalized Area Picture Motion Cleared on Input7"
    ::= 1204
    
    faultraPictureMotionInput7True TRAP-TYPE
        ENTERPRISE  trapFault
        VARIABLES   { trapTag }
        DESCRIPTION
            "Regionalized Area Picture Motion Alert on Input7"
    ::= 1205

-- end of raPictureMotion Input7 trap

-- beginning of raPictureMotion Input8 trap

    faultraPictureMotionInput8False TRAP-TYPE
        ENTERPRISE  trapFault
        VARIABLES   { trapTag }
        DESCRIPTION
            "Regionalized Area Picture Motion Cleared on Input8"
    ::= 1206
    
    faultraPictureMotionInput8True TRAP-TYPE
        ENTERPRISE  trapFault
        VARIABLES   { trapTag }
        DESCRIPTION
            "Regionalized Area Picture Motion Alert on Input8"
    ::= 1207

-- end of raPictureMotion Input8 trap

-- beginning of apPictureBlack Input1 trap

    faultapPictureBlackInput1False TRAP-TYPE
        ENTERPRISE  trapFault
        VARIABLES   { trapTag }
        DESCRIPTION
            "Active Picture Black Cleared on Input1"
    ::= 1208
    
    faultapPictureBlackInput1True TRAP-TYPE
        ENTERPRISE  trapFault
        VARIABLES   { trapTag }
        DESCRIPTION
            "Active Picture Black Alert on Input1"
    ::= 1209

-- end of apPictureBlack Input1 trap

-- beginning of apPictureBlack Input2 trap

    faultapPictureBlackInput2False TRAP-TYPE
        ENTERPRISE  trapFault
        VARIABLES   { trapTag }
        DESCRIPTION
            "Active Picture Black Cleared on Input2"
    ::= 1210
    
    faultapPictureBlackInput2True TRAP-TYPE
        ENTERPRISE  trapFault
        VARIABLES   { trapTag }
        DESCRIPTION
            "Active Picture Black Alert on Input2"
    ::= 1211

-- end of apPictureBlack Input2 trap

-- beginning of apPictureBlack Input3 trap

    faultapPictureBlackInput3False TRAP-TYPE
        ENTERPRISE  trapFault
        VARIABLES   { trapTag }
        DESCRIPTION
            "Active Picture Black Cleared on Input3"
    ::= 1212
    
    faultapPictureBlackInput3True TRAP-TYPE
        ENTERPRISE  trapFault
        VARIABLES   { trapTag }
        DESCRIPTION
            "Active Picture Black Alert on Input3"
    ::= 1213

-- end of apPictureBlack Input3 trap

-- beginning of apPictureBlack Input4 trap

    faultapPictureBlackInput4False TRAP-TYPE
        ENTERPRISE  trapFault
        VARIABLES   { trapTag }
        DESCRIPTION
            "Active Picture Black Cleared on Input4"
    ::= 1214
    
    faultapPictureBlackInput4True TRAP-TYPE
        ENTERPRISE  trapFault
        VARIABLES   { trapTag }
        DESCRIPTION
            "Active Picture Black Alert on Input4"
    ::= 1215

-- end of apPictureBlack Input4 trap

-- beginning of apPictureBlack Input5 trap

    faultapPictureBlackInput5False TRAP-TYPE
        ENTERPRISE  trapFault
        VARIABLES   { trapTag }
        DESCRIPTION
            "Active Picture Black Cleared on Input5"
    ::= 1216
    
    faultapPictureBlackInput5True TRAP-TYPE
        ENTERPRISE  trapFault
        VARIABLES   { trapTag }
        DESCRIPTION
            "Active Picture Black Alert on Input5"
    ::= 1217

-- end of apPictureBlack Input5 trap

-- beginning of apPictureBlack Input6 trap

    faultapPictureBlackInput6False TRAP-TYPE
        ENTERPRISE  trapFault
        VARIABLES   { trapTag }
        DESCRIPTION
            "Active Picture Black Cleared on Input6"
    ::= 1218
    
    faultapPictureBlackInput6True TRAP-TYPE
        ENTERPRISE  trapFault
        VARIABLES   { trapTag }
        DESCRIPTION
            "Active Picture Black Alert on Input6"
    ::= 1219

-- end of apPictureBlack Input6 trap

-- beginning of apPictureBlack Input7 trap

    faultapPictureBlackInput7False TRAP-TYPE
        ENTERPRISE  trapFault
        VARIABLES   { trapTag }
        DESCRIPTION
            "Active Picture Black Cleared on Input7"
    ::= 1220
    
    faultapPictureBlackInput7True TRAP-TYPE
        ENTERPRISE  trapFault
        VARIABLES   { trapTag }
        DESCRIPTION
            "Active Picture Black Alert on Input7"
    ::= 1221

-- end of apPictureBlack Input7 trap

-- beginning of apPictureBlack Input8 trap

    faultapPictureBlackInput8False TRAP-TYPE
        ENTERPRISE  trapFault
        VARIABLES   { trapTag }
        DESCRIPTION
            "Active Picture Black Cleared on Input8"
    ::= 1222
    
    faultapPictureBlackInput8True TRAP-TYPE
        ENTERPRISE  trapFault
        VARIABLES   { trapTag }
        DESCRIPTION
            "Active Picture Black Alert on Input8"
    ::= 1223

-- end of apPictureBlack Input8 trap

-- beginning of raPictureBlack Input1 trap

    faultraPictureBlackInput1False TRAP-TYPE
        ENTERPRISE  trapFault
        VARIABLES   { trapTag }
        DESCRIPTION
            "Regionalized Area Picture Black Cleared on Input1"
    ::= 1224
    
    faultraPictureBlackInput1True TRAP-TYPE
        ENTERPRISE  trapFault
        VARIABLES   { trapTag }
        DESCRIPTION
            "Regionalized Area Picture Black Alert on Input1"
    ::= 1225

-- end of raPictureBlack Input1 trap

-- beginning of raPictureBlack Input2 trap

    faultraPictureBlackInput2False TRAP-TYPE
        ENTERPRISE  trapFault
        VARIABLES   { trapTag }
        DESCRIPTION
            "Regionalized Area Picture Black Cleared on Input2"
    ::= 1226
    
    faultraPictureBlackInput2True TRAP-TYPE
        ENTERPRISE  trapFault
        VARIABLES   { trapTag }
        DESCRIPTION
            "Regionalized Area Picture Black Alert on Input2"
    ::= 1227

-- end of raPictureBlack Input2 trap

-- beginning of raPictureBlack Input3 trap

    faultraPictureBlackInput3False TRAP-TYPE
        ENTERPRISE  trapFault
        VARIABLES   { trapTag }
        DESCRIPTION
            "Regionalized Area Picture Black Cleared on Input3"
    ::= 1228
    
    faultraPictureBlackInput3True TRAP-TYPE
        ENTERPRISE  trapFault
        VARIABLES   { trapTag }
        DESCRIPTION
            "Regionalized Area Picture Black Alert on Input3"
    ::= 1229

-- end of raPictureBlack Input3 trap

-- beginning of raPictureBlack Input4 trap

    faultraPictureBlackInput4False TRAP-TYPE
        ENTERPRISE  trapFault
        VARIABLES   { trapTag }
        DESCRIPTION
            "Regionalized Area Picture Black Cleared on Input4"
    ::= 1230
    
    faultraPictureBlackInput4True TRAP-TYPE
        ENTERPRISE  trapFault
        VARIABLES   { trapTag }
        DESCRIPTION
            "Regionalized Area Picture Black Alert on Input4"
    ::= 1231

-- end of raPictureBlack Input4 trap

-- beginning of raPictureBlack Input5 trap

    faultraPictureBlackInput5False TRAP-TYPE
        ENTERPRISE  trapFault
        VARIABLES   { trapTag }
        DESCRIPTION
            "Regionalized Area Picture Black Cleared on Input5"
    ::= 1232
    
    faultraPictureBlackInput5True TRAP-TYPE
        ENTERPRISE  trapFault
        VARIABLES   { trapTag }
        DESCRIPTION
            "Regionalized Area Picture Black Alert on Input5"
    ::= 1233

-- end of raPictureBlack Input5 trap

-- beginning of raPictureBlack Input6 trap

    faultraPictureBlackInput6False TRAP-TYPE
        ENTERPRISE  trapFault
        VARIABLES   { trapTag }
        DESCRIPTION
            "Regionalized Area Picture Black Cleared on Input6"
    ::= 1234
    
    faultraPictureBlackInput6True TRAP-TYPE
        ENTERPRISE  trapFault
        VARIABLES   { trapTag }
        DESCRIPTION
            "Regionalized Area Picture Black Alert on Input6"
    ::= 1235

-- end of raPictureBlack Input6 trap

-- beginning of raPictureBlack Input7 trap

    faultraPictureBlackInput7False TRAP-TYPE
        ENTERPRISE  trapFault
        VARIABLES   { trapTag }
        DESCRIPTION
            "Regionalized Area Picture Black Cleared on Input7"
    ::= 1236
    
    faultraPictureBlackInput7True TRAP-TYPE
        ENTERPRISE  trapFault
        VARIABLES   { trapTag }
        DESCRIPTION
            "Regionalized Area Picture Black Alert on Input7"
    ::= 1237

-- end of raPictureBlack Input7 trap

-- beginning of raPictureBlack Input8 trap

    faultraPictureBlackInput8False TRAP-TYPE
        ENTERPRISE  trapFault
        VARIABLES   { trapTag }
        DESCRIPTION
            "Regionalized Area Picture Black Cleared on Input8"
    ::= 1238
    
    faultraPictureBlackInput8True TRAP-TYPE
        ENTERPRISE  trapFault
        VARIABLES   { trapTag }
        DESCRIPTION
            "Regionalized Area Picture Black Alert on Input8"
    ::= 1239

-- end of raPictureBlack Input8 trap

-- beginning of lossOfVITC Input1 trap

    faultlossOfVITCInput1False TRAP-TYPE
        ENTERPRISE  trapFault
        VARIABLES   { trapTag }
        DESCRIPTION
            "Loss of VITC Cleared on Input1"
    ::= 1240
    
    faultlossOfVITCInput1True TRAP-TYPE
        ENTERPRISE  trapFault
        VARIABLES   { trapTag }
        DESCRIPTION
            "Loss of VITC Alert on Input1"
    ::= 1241

-- end of lossOfVITC Input1 trap

-- beginning of lossOfVITC Input2 trap

    faultlossOfVITCInput2False TRAP-TYPE
        ENTERPRISE  trapFault
        VARIABLES   { trapTag }
        DESCRIPTION
            "Loss of VITC Cleared on Input2"
    ::= 1242
    
    faultlossOfVITCInput2True TRAP-TYPE
        ENTERPRISE  trapFault
        VARIABLES   { trapTag }
        DESCRIPTION
            "Loss of VITC Alert on Input2"
    ::= 1243

-- end of lossOfVITC Input2 trap

-- beginning of lossOfVITC Input3 trap

    faultlossOfVITCInput3False TRAP-TYPE
        ENTERPRISE  trapFault
        VARIABLES   { trapTag }
        DESCRIPTION
            "Loss of VITC Cleared on Input3"
    ::= 1244
    
    faultlossOfVITCInput3True TRAP-TYPE
        ENTERPRISE  trapFault
        VARIABLES   { trapTag }
        DESCRIPTION
            "Loss of VITC Alert on Input3"
    ::= 1245

-- end of lossOfVITC Input3 trap

-- beginning of lossOfVITC Input4 trap

    faultlossOfVITCInput4False TRAP-TYPE
        ENTERPRISE  trapFault
        VARIABLES   { trapTag }
        DESCRIPTION
            "Loss of VITC Cleared on Input4"
    ::= 1246
    
    faultlossOfVITCInput4True TRAP-TYPE
        ENTERPRISE  trapFault
        VARIABLES   { trapTag }
        DESCRIPTION
            "Loss of VITC Alert on Input4"
    ::= 1247

-- end of lossOfVITC Input4 trap

-- beginning of lossOfVITC Input5 trap

    faultlossOfVITCInput5False TRAP-TYPE
        ENTERPRISE  trapFault
        VARIABLES   { trapTag }
        DESCRIPTION
            "Loss of VITC Cleared on Input5"
    ::= 1248
    
    faultlossOfVITCInput5True TRAP-TYPE
        ENTERPRISE  trapFault
        VARIABLES   { trapTag }
        DESCRIPTION
            "Loss of VITC Alert on Input5"
    ::= 1249

-- end of lossOfVITC Input5 trap

-- beginning of lossOfVITC Input6 trap

    faultlossOfVITCInput6False TRAP-TYPE
        ENTERPRISE  trapFault
        VARIABLES   { trapTag }
        DESCRIPTION
            "Loss of VITC Cleared on Input6"
    ::= 1250
    
    faultlossOfVITCInput6True TRAP-TYPE
        ENTERPRISE  trapFault
        VARIABLES   { trapTag }
        DESCRIPTION
            "Loss of VITC Alert on Input6"
    ::= 1251

-- end of lossOfVITC Input6 trap

-- beginning of lossOfVITC Input7 trap

    faultlossOfVITCInput7False TRAP-TYPE
        ENTERPRISE  trapFault
        VARIABLES   { trapTag }
        DESCRIPTION
            "Loss of VITC Cleared on Input7"
    ::= 1252
    
    faultlossOfVITCInput7True TRAP-TYPE
        ENTERPRISE  trapFault
        VARIABLES   { trapTag }
        DESCRIPTION
            "Loss of VITC Alert on Input7"
    ::= 1253

-- end of lossOfVITC Input7 trap

-- beginning of lossOfVITC Input8 trap

    faultlossOfVITCInput8False TRAP-TYPE
        ENTERPRISE  trapFault
        VARIABLES   { trapTag }
        DESCRIPTION
            "Loss of VITC Cleared on Input8"
    ::= 1254
    
    faultlossOfVITCInput8True TRAP-TYPE
        ENTERPRISE  trapFault
        VARIABLES   { trapTag }
        DESCRIPTION
            "Loss of VITC Alert on Input8"
    ::= 1255

-- end of lossOfVITC Input8 trap

-- beginning of lossOfSID Input1 trap

    faultlossOfSIDInput1False TRAP-TYPE
        ENTERPRISE  trapFault
        VARIABLES   { trapTag }
        DESCRIPTION
            "Loss of SID Cleared on Input1"
    ::= 1256
    
    faultlossOfSIDInput1True TRAP-TYPE
        ENTERPRISE  trapFault
        VARIABLES   { trapTag }
        DESCRIPTION
            "Loss of SID Alert on Input1"
    ::= 1257

-- end of lossOfSID Input1 trap

-- beginning of lossOfSID Input2 trap

    faultlossOfSIDInput2False TRAP-TYPE
        ENTERPRISE  trapFault
        VARIABLES   { trapTag }
        DESCRIPTION
            "Loss of SID Cleared on Input2"
    ::= 1258
    
    faultlossOfSIDInput2True TRAP-TYPE
        ENTERPRISE  trapFault
        VARIABLES   { trapTag }
        DESCRIPTION
            "Loss of SID Alert on Input2"
    ::= 1259

-- end of lossOfSID Input2 trap

-- beginning of lossOfSID Input3 trap

    faultlossOfSIDInput3False TRAP-TYPE
        ENTERPRISE  trapFault
        VARIABLES   { trapTag }
        DESCRIPTION
            "Loss of SID Cleared on Input3"
    ::= 1260
    
    faultlossOfSIDInput3True TRAP-TYPE
        ENTERPRISE  trapFault
        VARIABLES   { trapTag }
        DESCRIPTION
            "Loss of SID Alert on Input3"
    ::= 1261

-- end of lossOfSID Input3 trap

-- beginning of lossOfSID Input4 trap

    faultlossOfSIDInput4False TRAP-TYPE
        ENTERPRISE  trapFault
        VARIABLES   { trapTag }
        DESCRIPTION
            "Loss of SID Cleared on Input4"
    ::= 1262
    
    faultlossOfSIDInput4True TRAP-TYPE
        ENTERPRISE  trapFault
        VARIABLES   { trapTag }
        DESCRIPTION
            "Loss of SID Alert on Input4"
    ::= 1263

-- end of lossOfSID Input4 trap

-- beginning of lossOfSID Input5 trap

    faultlossOfSIDInput5False TRAP-TYPE
        ENTERPRISE  trapFault
        VARIABLES   { trapTag }
        DESCRIPTION
            "Loss of SID Cleared on Input5"
    ::= 1264
    
    faultlossOfSIDInput5True TRAP-TYPE
        ENTERPRISE  trapFault
        VARIABLES   { trapTag }
        DESCRIPTION
            "Loss of SID Alert on Input5"
    ::= 1265

-- end of lossOfSID Input5 trap

-- beginning of lossOfSID Input6 trap

    faultlossOfSIDInput6False TRAP-TYPE
        ENTERPRISE  trapFault
        VARIABLES   { trapTag }
        DESCRIPTION
            "Loss of SID Cleared on Input6"
    ::= 1266
    
    faultlossOfSIDInput6True TRAP-TYPE
        ENTERPRISE  trapFault
        VARIABLES   { trapTag }
        DESCRIPTION
            "Loss of SID Alert on Input6"
    ::= 1267

-- end of lossOfSID Input6 trap

-- beginning of lossOfSID Input7 trap

    faultlossOfSIDInput7False TRAP-TYPE
        ENTERPRISE  trapFault
        VARIABLES   { trapTag }
        DESCRIPTION
            "Loss of SID Cleared on Input7"
    ::= 1268
    
    faultlossOfSIDInput7True TRAP-TYPE
        ENTERPRISE  trapFault
        VARIABLES   { trapTag }
        DESCRIPTION
            "Loss of SID Alert on Input7"
    ::= 1269

-- end of lossOfSID Input7 trap

-- beginning of lossOfSID Input8 trap

    faultlossOfSIDInput8False TRAP-TYPE
        ENTERPRISE  trapFault
        VARIABLES   { trapTag }
        DESCRIPTION
            "Loss of SID Cleared on Input8"
    ::= 1270
    
    faultlossOfSIDInput8True TRAP-TYPE
        ENTERPRISE  trapFault
        VARIABLES   { trapTag }
        DESCRIPTION
            "Loss of SID Alert on Input8"
    ::= 1271

-- end of lossOfSID Input8 trap

-- beginning of lossOfPR Input1 trap

    faultlossOfPRInput1False TRAP-TYPE
        ENTERPRISE  trapFault
        VARIABLES   { trapTag }
        DESCRIPTION
            "Loss of Program Rating Cleared on Input1"
    ::= 1272
    
    faultlossOfPRInput1True TRAP-TYPE
        ENTERPRISE  trapFault
        VARIABLES   { trapTag }
        DESCRIPTION
            "Loss of Program Rating Alert on Input1"
    ::= 1273

-- end of lossOfPR Input1 trap

-- beginning of lossOfPR Input2 trap

    faultlossOfPRInput2False TRAP-TYPE
        ENTERPRISE  trapFault
        VARIABLES   { trapTag }
        DESCRIPTION
            "Loss of Program Rating Cleared on Input2"
    ::= 1274
    
    faultlossOfPRInput2True TRAP-TYPE
        ENTERPRISE  trapFault
        VARIABLES   { trapTag }
        DESCRIPTION
            "Loss of Program Rating Alert on Input2"
    ::= 1275

-- end of lossOfPR Input2 trap

-- beginning of lossOfPR Input3 trap

    faultlossOfPRInput3False TRAP-TYPE
        ENTERPRISE  trapFault
        VARIABLES   { trapTag }
        DESCRIPTION
            "Loss of Program Rating Cleared on Input3"
    ::= 1276
    
    faultlossOfPRInput3True TRAP-TYPE
        ENTERPRISE  trapFault
        VARIABLES   { trapTag }
        DESCRIPTION
            "Loss of Program Rating Alert on Input3"
    ::= 1277

-- end of lossOfPR Input3 trap

-- beginning of lossOfPR Input4 trap

    faultlossOfPRInput4False TRAP-TYPE
        ENTERPRISE  trapFault
        VARIABLES   { trapTag }
        DESCRIPTION
            "Loss of Program Rating Cleared on Input4"
    ::= 1278
    
    faultlossOfPRInput4True TRAP-TYPE
        ENTERPRISE  trapFault
        VARIABLES   { trapTag }
        DESCRIPTION
            "Loss of Program Rating Alert on Input4"
    ::= 1279

-- end of lossOfPR Input4 trap

-- beginning of lossOfPR Input5 trap

    faultlossOfPRInput5False TRAP-TYPE
        ENTERPRISE  trapFault
        VARIABLES   { trapTag }
        DESCRIPTION
            "Loss of Program Rating Cleared on Input5"
    ::= 1280
    
    faultlossOfPRInput5True TRAP-TYPE
        ENTERPRISE  trapFault
        VARIABLES   { trapTag }
        DESCRIPTION
            "Loss of Program Rating Alert on Input5"
    ::= 1281

-- end of lossOfPR Input5 trap

-- beginning of lossOfPR Input6 trap

    faultlossOfPRInput6False TRAP-TYPE
        ENTERPRISE  trapFault
        VARIABLES   { trapTag }
        DESCRIPTION
            "Loss of Program Rating Cleared on Input6"
    ::= 1282
    
    faultlossOfPRInput6True TRAP-TYPE
        ENTERPRISE  trapFault
        VARIABLES   { trapTag }
        DESCRIPTION
            "Loss of Program Rating Alert on Input6"
    ::= 1283

-- end of lossOfPR Input6 trap

-- beginning of lossOfPR Input7 trap

    faultlossOfPRInput7False TRAP-TYPE
        ENTERPRISE  trapFault
        VARIABLES   { trapTag }
        DESCRIPTION
            "Loss of Program Rating Cleared on Input7"
    ::= 1284
    
    faultlossOfPRInput7True TRAP-TYPE
        ENTERPRISE  trapFault
        VARIABLES   { trapTag }
        DESCRIPTION
            "Loss of Program Rating Alert on Input7"
    ::= 1285

-- end of lossOfPR Input7 trap

-- beginning of lossOfPR Input8 trap

    faultlossOfPRInput8False TRAP-TYPE
        ENTERPRISE  trapFault
        VARIABLES   { trapTag }
        DESCRIPTION
            "Loss of Program Rating Cleared on Input8"
    ::= 1286
    
    faultlossOfPRInput8True TRAP-TYPE
        ENTERPRISE  trapFault
        VARIABLES   { trapTag }
        DESCRIPTION
            "Loss of Program Rating Alert on Input8"
    ::= 1287

-- end of lossOfPR Input8 trap

-- beginning of lossOfCC1 Input1 trap

    faultlossOfCC1Input1False TRAP-TYPE
        ENTERPRISE  trapFault
        VARIABLES   { trapTag }
        DESCRIPTION
            "Loss of Closed Caption 1 Cleared on Input1"
    ::= 1288
    
    faultlossOfCC1Input1True TRAP-TYPE
        ENTERPRISE  trapFault
        VARIABLES   { trapTag }
        DESCRIPTION
            "Loss of Closed Caption 1 Alert on Input1"
    ::= 1289

-- end of lossOfCC1 Input1 trap

-- beginning of lossOfCC1 Input2 trap

    faultlossOfCC1Input2False TRAP-TYPE
        ENTERPRISE  trapFault
        VARIABLES   { trapTag }
        DESCRIPTION
            "Loss of Closed Caption 1 Cleared on Input2"
    ::= 1290
    
    faultlossOfCC1Input2True TRAP-TYPE
        ENTERPRISE  trapFault
        VARIABLES   { trapTag }
        DESCRIPTION
            "Loss of Closed Caption 1 Alert on Input2"
    ::= 1291

-- end of lossOfCC1 Input2 trap

-- beginning of lossOfCC1 Input3 trap

    faultlossOfCC1Input3False TRAP-TYPE
        ENTERPRISE  trapFault
        VARIABLES   { trapTag }
        DESCRIPTION
            "Loss of Closed Caption 1 Cleared on Input3"
    ::= 1292
    
    faultlossOfCC1Input3True TRAP-TYPE
        ENTERPRISE  trapFault
        VARIABLES   { trapTag }
        DESCRIPTION
            "Loss of Closed Caption 1 Alert on Input3"
    ::= 1293

-- end of lossOfCC1 Input3 trap

-- beginning of lossOfCC1 Input4 trap

    faultlossOfCC1Input4False TRAP-TYPE
        ENTERPRISE  trapFault
        VARIABLES   { trapTag }
        DESCRIPTION
            "Loss of Closed Caption 1 Cleared on Input4"
    ::= 1294
    
    faultlossOfCC1Input4True TRAP-TYPE
        ENTERPRISE  trapFault
        VARIABLES   { trapTag }
        DESCRIPTION
            "Loss of Closed Caption 1 Alert on Input4"
    ::= 1295

-- end of lossOfCC1 Input4 trap

-- beginning of lossOfCC1 Input5 trap

    faultlossOfCC1Input5False TRAP-TYPE
        ENTERPRISE  trapFault
        VARIABLES   { trapTag }
        DESCRIPTION
            "Loss of Closed Caption 1 Cleared on Input5"
    ::= 1296
    
    faultlossOfCC1Input5True TRAP-TYPE
        ENTERPRISE  trapFault
        VARIABLES   { trapTag }
        DESCRIPTION
            "Loss of Closed Caption 1 Alert on Input5"
    ::= 1297

-- end of lossOfCC1 Input5 trap

-- beginning of lossOfCC1 Input6 trap

    faultlossOfCC1Input6False TRAP-TYPE
        ENTERPRISE  trapFault
        VARIABLES   { trapTag }
        DESCRIPTION
            "Loss of Closed Caption 1 Cleared on Input6"
    ::= 1298
    
    faultlossOfCC1Input6True TRAP-TYPE
        ENTERPRISE  trapFault
        VARIABLES   { trapTag }
        DESCRIPTION
            "Loss of Closed Caption 1 Alert on Input6"
    ::= 1299

-- end of lossOfCC1 Input6 trap

-- beginning of lossOfCC1 Input7 trap

    faultlossOfCC1Input7False TRAP-TYPE
        ENTERPRISE  trapFault
        VARIABLES   { trapTag }
        DESCRIPTION
            "Loss of Closed Caption 1 Cleared on Input7"
    ::= 1300
    
    faultlossOfCC1Input7True TRAP-TYPE
        ENTERPRISE  trapFault
        VARIABLES   { trapTag }
        DESCRIPTION
            "Loss of Closed Caption 1 Alert on Input7"
    ::= 1301

-- end of lossOfCC1 Input7 trap

-- beginning of lossOfCC1 Input8 trap

    faultlossOfCC1Input8False TRAP-TYPE
        ENTERPRISE  trapFault
        VARIABLES   { trapTag }
        DESCRIPTION
            "Loss of Closed Caption 1 Cleared on Input8"
    ::= 1302
    
    faultlossOfCC1Input8True TRAP-TYPE
        ENTERPRISE  trapFault
        VARIABLES   { trapTag }
        DESCRIPTION
            "Loss of Closed Caption 1 Alert on Input8"
    ::= 1303

-- end of lossOfCC1 Input8 trap

-- beginning of lossOfCC2 Input1 trap

    faultlossOfCC2Input1False TRAP-TYPE
        ENTERPRISE  trapFault
        VARIABLES   { trapTag }
        DESCRIPTION
            "Loss of Closed Caption 2 Cleared on Input1"
    ::= 1304
    
    faultlossOfCC2Input1True TRAP-TYPE
        ENTERPRISE  trapFault
        VARIABLES   { trapTag }
        DESCRIPTION
            "Loss of Closed Caption 2 Alert on Input1"
    ::= 1305

-- end of lossOfCC2 Input1 trap

-- beginning of lossOfCC2 Input2 trap

    faultlossOfCC2Input2False TRAP-TYPE
        ENTERPRISE  trapFault
        VARIABLES   { trapTag }
        DESCRIPTION
            "Loss of Closed Caption 2 Cleared on Input2"
    ::= 1306
    
    faultlossOfCC2Input2True TRAP-TYPE
        ENTERPRISE  trapFault
        VARIABLES   { trapTag }
        DESCRIPTION
            "Loss of Closed Caption 2 Alert on Input2"
    ::= 1307

-- end of lossOfCC2 Input2 trap

-- beginning of lossOfCC2 Input3 trap

    faultlossOfCC2Input3False TRAP-TYPE
        ENTERPRISE  trapFault
        VARIABLES   { trapTag }
        DESCRIPTION
            "Loss of Closed Caption 2 Cleared on Input3"
    ::= 1308
    
    faultlossOfCC2Input3True TRAP-TYPE
        ENTERPRISE  trapFault
        VARIABLES   { trapTag }
        DESCRIPTION
            "Loss of Closed Caption 2 Alert on Input3"
    ::= 1309

-- end of lossOfCC2 Input3 trap

-- beginning of lossOfCC2 Input4 trap

    faultlossOfCC2Input4False TRAP-TYPE
        ENTERPRISE  trapFault
        VARIABLES   { trapTag }
        DESCRIPTION
            "Loss of Closed Caption 2 Cleared on Input4"
    ::= 1310
    
    faultlossOfCC2Input4True TRAP-TYPE
        ENTERPRISE  trapFault
        VARIABLES   { trapTag }
        DESCRIPTION
            "Loss of Closed Caption 2 Alert on Input4"
    ::= 1311

-- end of lossOfCC2 Input4 trap

-- beginning of lossOfCC2 Input5 trap

    faultlossOfCC2Input5False TRAP-TYPE
        ENTERPRISE  trapFault
        VARIABLES   { trapTag }
        DESCRIPTION
            "Loss of Closed Caption 2 Cleared on Input5"
    ::= 1312
    
    faultlossOfCC2Input5True TRAP-TYPE
        ENTERPRISE  trapFault
        VARIABLES   { trapTag }
        DESCRIPTION
            "Loss of Closed Caption 2 Alert on Input5"
    ::= 1313

-- end of lossOfCC2 Input5 trap

-- beginning of lossOfCC2 Input6 trap

    faultlossOfCC2Input6False TRAP-TYPE
        ENTERPRISE  trapFault
        VARIABLES   { trapTag }
        DESCRIPTION
            "Loss of Closed Caption 2 Cleared on Input6"
    ::= 1314
    
    faultlossOfCC2Input6True TRAP-TYPE
        ENTERPRISE  trapFault
        VARIABLES   { trapTag }
        DESCRIPTION
            "Loss of Closed Caption 2 Alert on Input6"
    ::= 1315

-- end of lossOfCC2 Input6 trap

-- beginning of lossOfCC2 Input7 trap

    faultlossOfCC2Input7False TRAP-TYPE
        ENTERPRISE  trapFault
        VARIABLES   { trapTag }
        DESCRIPTION
            "Loss of Closed Caption 2 Cleared on Input7"
    ::= 1316
    
    faultlossOfCC2Input7True TRAP-TYPE
        ENTERPRISE  trapFault
        VARIABLES   { trapTag }
        DESCRIPTION
            "Loss of Closed Caption 2 Alert on Input7"
    ::= 1317

-- end of lossOfCC2 Input7 trap

-- beginning of lossOfCC2 Input8 trap

    faultlossOfCC2Input8False TRAP-TYPE
        ENTERPRISE  trapFault
        VARIABLES   { trapTag }
        DESCRIPTION
            "Loss of Closed Caption 2 Cleared on Input8"
    ::= 1318
    
    faultlossOfCC2Input8True TRAP-TYPE
        ENTERPRISE  trapFault
        VARIABLES   { trapTag }
        DESCRIPTION
            "Loss of Closed Caption 2 Alert on Input8"
    ::= 1319

-- end of lossOfCC2 Input8 trap

-- beginning of lossOfCC3 Input1 trap

    faultlossOfCC3Input1False TRAP-TYPE
        ENTERPRISE  trapFault
        VARIABLES   { trapTag }
        DESCRIPTION
            "Loss of Closed Caption 3 Cleared on Input1"
    ::= 1320
    
    faultlossOfCC3Input1True TRAP-TYPE
        ENTERPRISE  trapFault
        VARIABLES   { trapTag }
        DESCRIPTION
            "Loss of Closed Caption 3 Alert on Input1"
    ::= 1321

-- end of lossOfCC3 Input1 trap

-- beginning of lossOfCC3 Input2 trap

    faultlossOfCC3Input2False TRAP-TYPE
        ENTERPRISE  trapFault
        VARIABLES   { trapTag }
        DESCRIPTION
            "Loss of Closed Caption 3 Cleared on Input2"
    ::= 1322
    
    faultlossOfCC3Input2True TRAP-TYPE
        ENTERPRISE  trapFault
        VARIABLES   { trapTag }
        DESCRIPTION
            "Loss of Closed Caption 3 Alert on Input2"
    ::= 1323

-- end of lossOfCC3 Input2 trap

-- beginning of lossOfCC3 Input3 trap

    faultlossOfCC3Input3False TRAP-TYPE
        ENTERPRISE  trapFault
        VARIABLES   { trapTag }
        DESCRIPTION
            "Loss of Closed Caption 3 Cleared on Input3"
    ::= 1324
    
    faultlossOfCC3Input3True TRAP-TYPE
        ENTERPRISE  trapFault
        VARIABLES   { trapTag }
        DESCRIPTION
            "Loss of Closed Caption 3 Alert on Input3"
    ::= 1325

-- end of lossOfCC3 Input3 trap

-- beginning of lossOfCC3 Input4 trap

    faultlossOfCC3Input4False TRAP-TYPE
        ENTERPRISE  trapFault
        VARIABLES   { trapTag }
        DESCRIPTION
            "Loss of Closed Caption 3 Cleared on Input4"
    ::= 1326
    
    faultlossOfCC3Input4True TRAP-TYPE
        ENTERPRISE  trapFault
        VARIABLES   { trapTag }
        DESCRIPTION
            "Loss of Closed Caption 3 Alert on Input4"
    ::= 1327

-- end of lossOfCC3 Input4 trap

-- beginning of lossOfCC3 Input5 trap

    faultlossOfCC3Input5False TRAP-TYPE
        ENTERPRISE  trapFault
        VARIABLES   { trapTag }
        DESCRIPTION
            "Loss of Closed Caption 3 Cleared on Input5"
    ::= 1328
    
    faultlossOfCC3Input5True TRAP-TYPE
        ENTERPRISE  trapFault
        VARIABLES   { trapTag }
        DESCRIPTION
            "Loss of Closed Caption 3 Alert on Input5"
    ::= 1329

-- end of lossOfCC3 Input5 trap

-- beginning of lossOfCC3 Input6 trap

    faultlossOfCC3Input6False TRAP-TYPE
        ENTERPRISE  trapFault
        VARIABLES   { trapTag }
        DESCRIPTION
            "Loss of Closed Caption 3 Cleared on Input6"
    ::= 1330
    
    faultlossOfCC3Input6True TRAP-TYPE
        ENTERPRISE  trapFault
        VARIABLES   { trapTag }
        DESCRIPTION
            "Loss of Closed Caption 3 Alert on Input6"
    ::= 1331

-- end of lossOfCC3 Input6 trap

-- beginning of lossOfCC3 Input7 trap

    faultlossOfCC3Input7False TRAP-TYPE
        ENTERPRISE  trapFault
        VARIABLES   { trapTag }
        DESCRIPTION
            "Loss of Closed Caption 3 Cleared on Input7"
    ::= 1332
    
    faultlossOfCC3Input7True TRAP-TYPE
        ENTERPRISE  trapFault
        VARIABLES   { trapTag }
        DESCRIPTION
            "Loss of Closed Caption 3 Alert on Input7"
    ::= 1333

-- end of lossOfCC3 Input7 trap

-- beginning of lossOfCC3 Input8 trap

    faultlossOfCC3Input8False TRAP-TYPE
        ENTERPRISE  trapFault
        VARIABLES   { trapTag }
        DESCRIPTION
            "Loss of Closed Caption 3 Cleared on Input8"
    ::= 1334
    
    faultlossOfCC3Input8True TRAP-TYPE
        ENTERPRISE  trapFault
        VARIABLES   { trapTag }
        DESCRIPTION
            "Loss of Closed Caption 3 Alert on Input8"
    ::= 1335

-- end of lossOfCC3 Input8 trap

-- beginning of lossOfCC4 Input1 trap

    faultlossOfCC4Input1False TRAP-TYPE
        ENTERPRISE  trapFault
        VARIABLES   { trapTag }
        DESCRIPTION
            "Loss of Closed Caption 4 Cleared on Input1"
    ::= 1336
    
    faultlossOfCC4Input1True TRAP-TYPE
        ENTERPRISE  trapFault
        VARIABLES   { trapTag }
        DESCRIPTION
            "Loss of Closed Caption 4 Alert on Input1"
    ::= 1337

-- end of lossOfCC4 Input1 trap

-- beginning of lossOfCC4 Input2 trap

    faultlossOfCC4Input2False TRAP-TYPE
        ENTERPRISE  trapFault
        VARIABLES   { trapTag }
        DESCRIPTION
            "Loss of Closed Caption 4 Cleared on Input2"
    ::= 1338
    
    faultlossOfCC4Input2True TRAP-TYPE
        ENTERPRISE  trapFault
        VARIABLES   { trapTag }
        DESCRIPTION
            "Loss of Closed Caption 4 Alert on Input2"
    ::= 1339

-- end of lossOfCC4 Input2 trap

-- beginning of lossOfCC4 Input3 trap

    faultlossOfCC4Input3False TRAP-TYPE
        ENTERPRISE  trapFault
        VARIABLES   { trapTag }
        DESCRIPTION
            "Loss of Closed Caption 4 Cleared on Input3"
    ::= 1340
    
    faultlossOfCC4Input3True TRAP-TYPE
        ENTERPRISE  trapFault
        VARIABLES   { trapTag }
        DESCRIPTION
            "Loss of Closed Caption 4 Alert on Input3"
    ::= 1341

-- end of lossOfCC4 Input3 trap

-- beginning of lossOfCC4 Input4 trap

    faultlossOfCC4Input4False TRAP-TYPE
        ENTERPRISE  trapFault
        VARIABLES   { trapTag }
        DESCRIPTION
            "Loss of Closed Caption 4 Cleared on Input4"
    ::= 1342
    
    faultlossOfCC4Input4True TRAP-TYPE
        ENTERPRISE  trapFault
        VARIABLES   { trapTag }
        DESCRIPTION
            "Loss of Closed Caption 4 Alert on Input4"
    ::= 1343

-- end of lossOfCC4 Input4 trap

-- beginning of lossOfCC4 Input5 trap

    faultlossOfCC4Input5False TRAP-TYPE
        ENTERPRISE  trapFault
        VARIABLES   { trapTag }
        DESCRIPTION
            "Loss of Closed Caption 4 Cleared on Input5"
    ::= 1344
    
    faultlossOfCC4Input5True TRAP-TYPE
        ENTERPRISE  trapFault
        VARIABLES   { trapTag }
        DESCRIPTION
            "Loss of Closed Caption 4 Alert on Input5"
    ::= 1345

-- end of lossOfCC4 Input5 trap

-- beginning of lossOfCC4 Input6 trap

    faultlossOfCC4Input6False TRAP-TYPE
        ENTERPRISE  trapFault
        VARIABLES   { trapTag }
        DESCRIPTION
            "Loss of Closed Caption 4 Cleared on Input6"
    ::= 1346
    
    faultlossOfCC4Input6True TRAP-TYPE
        ENTERPRISE  trapFault
        VARIABLES   { trapTag }
        DESCRIPTION
            "Loss of Closed Caption 4 Alert on Input6"
    ::= 1347

-- end of lossOfCC4 Input6 trap

-- beginning of lossOfCC4 Input7 trap

    faultlossOfCC4Input7False TRAP-TYPE
        ENTERPRISE  trapFault
        VARIABLES   { trapTag }
        DESCRIPTION
            "Loss of Closed Caption 4 Cleared on Input7"
    ::= 1348
    
    faultlossOfCC4Input7True TRAP-TYPE
        ENTERPRISE  trapFault
        VARIABLES   { trapTag }
        DESCRIPTION
            "Loss of Closed Caption 4 Alert on Input7"
    ::= 1349

-- end of lossOfCC4 Input7 trap

-- beginning of lossOfCC4 Input8 trap

    faultlossOfCC4Input8False TRAP-TYPE
        ENTERPRISE  trapFault
        VARIABLES   { trapTag }
        DESCRIPTION
            "Loss of Closed Caption 4 Cleared on Input8"
    ::= 1350
    
    faultlossOfCC4Input8True TRAP-TYPE
        ENTERPRISE  trapFault
        VARIABLES   { trapTag }
        DESCRIPTION
            "Loss of Closed Caption 4 Alert on Input8"
    ::= 1351

-- end of lossOfCC4 Input8 trap

-- beginning of lossOfText1 Input1 trap

    faultlossOfText1Input1False TRAP-TYPE
        ENTERPRISE  trapFault
        VARIABLES   { trapTag }
        DESCRIPTION
            "Loss of Text 1 Cleared on Input1"
    ::= 1352
    
    faultlossOfText1Input1True TRAP-TYPE
        ENTERPRISE  trapFault
        VARIABLES   { trapTag }
        DESCRIPTION
            "Loss of Text 1 Alert on Input1"
    ::= 1353

-- end of lossOfText1 Input1 trap

-- beginning of lossOfText1 Input2 trap

    faultlossOfText1Input2False TRAP-TYPE
        ENTERPRISE  trapFault
        VARIABLES   { trapTag }
        DESCRIPTION
            "Loss of Text 1 Cleared on Input2"
    ::= 1354
    
    faultlossOfText1Input2True TRAP-TYPE
        ENTERPRISE  trapFault
        VARIABLES   { trapTag }
        DESCRIPTION
            "Loss of Text 1 Alert on Input2"
    ::= 1355

-- end of lossOfText1 Input2 trap

-- beginning of lossOfText1 Input3 trap

    faultlossOfText1Input3False TRAP-TYPE
        ENTERPRISE  trapFault
        VARIABLES   { trapTag }
        DESCRIPTION
            "Loss of Text 1 Cleared on Input3"
    ::= 1356
    
    faultlossOfText1Input3True TRAP-TYPE
        ENTERPRISE  trapFault
        VARIABLES   { trapTag }
        DESCRIPTION
            "Loss of Text 1 Alert on Input3"
    ::= 1357

-- end of lossOfText1 Input3 trap

-- beginning of lossOfText1 Input4 trap

    faultlossOfText1Input4False TRAP-TYPE
        ENTERPRISE  trapFault
        VARIABLES   { trapTag }
        DESCRIPTION
            "Loss of Text 1 Cleared on Input4"
    ::= 1358
    
    faultlossOfText1Input4True TRAP-TYPE
        ENTERPRISE  trapFault
        VARIABLES   { trapTag }
        DESCRIPTION
            "Loss of Text 1 Alert on Input4"
    ::= 1359

-- end of lossOfText1 Input4 trap

-- beginning of lossOfText1 Input5 trap

    faultlossOfText1Input5False TRAP-TYPE
        ENTERPRISE  trapFault
        VARIABLES   { trapTag }
        DESCRIPTION
            "Loss of Text 1 Cleared on Input5"
    ::= 1360
    
    faultlossOfText1Input5True TRAP-TYPE
        ENTERPRISE  trapFault
        VARIABLES   { trapTag }
        DESCRIPTION
            "Loss of Text 1 Alert on Input5"
    ::= 1361

-- end of lossOfText1 Input5 trap

-- beginning of lossOfText1 Input6 trap

    faultlossOfText1Input6False TRAP-TYPE
        ENTERPRISE  trapFault
        VARIABLES   { trapTag }
        DESCRIPTION
            "Loss of Text 1 Cleared on Input6"
    ::= 1362
    
    faultlossOfText1Input6True TRAP-TYPE
        ENTERPRISE  trapFault
        VARIABLES   { trapTag }
        DESCRIPTION
            "Loss of Text 1 Alert on Input6"
    ::= 1363

-- end of lossOfText1 Input6 trap

-- beginning of lossOfText1 Input7 trap

    faultlossOfText1Input7False TRAP-TYPE
        ENTERPRISE  trapFault
        VARIABLES   { trapTag }
        DESCRIPTION
            "Loss of Text 1 Cleared on Input7"
    ::= 1364
    
    faultlossOfText1Input7True TRAP-TYPE
        ENTERPRISE  trapFault
        VARIABLES   { trapTag }
        DESCRIPTION
            "Loss of Text 1 Alert on Input7"
    ::= 1365

-- end of lossOfText1 Input7 trap

-- beginning of lossOfText1 Input8 trap

    faultlossOfText1Input8False TRAP-TYPE
        ENTERPRISE  trapFault
        VARIABLES   { trapTag }
        DESCRIPTION
            "Loss of Text 1 Cleared on Input8"
    ::= 1366
    
    faultlossOfText1Input8True TRAP-TYPE
        ENTERPRISE  trapFault
        VARIABLES   { trapTag }
        DESCRIPTION
            "Loss of Text 1 Alert on Input8"
    ::= 1367

-- end of lossOfText1 Input8 trap

-- beginning of lossOfText2 Input1 trap

    faultlossOfText2Input1False TRAP-TYPE
        ENTERPRISE  trapFault
        VARIABLES   { trapTag }
        DESCRIPTION
            "Loss of Text 2 Cleared on Input1"
    ::= 1368
    
    faultlossOfText2Input1True TRAP-TYPE
        ENTERPRISE  trapFault
        VARIABLES   { trapTag }
        DESCRIPTION
            "Loss of Text 2 Alert on Input1"
    ::= 1369

-- end of lossOfText2 Input1 trap

-- beginning of lossOfText2 Input2 trap

    faultlossOfText2Input2False TRAP-TYPE
        ENTERPRISE  trapFault
        VARIABLES   { trapTag }
        DESCRIPTION
            "Loss of Text 2 Cleared on Input2"
    ::= 1370
    
    faultlossOfText2Input2True TRAP-TYPE
        ENTERPRISE  trapFault
        VARIABLES   { trapTag }
        DESCRIPTION
            "Loss of Text 2 Alert on Input2"
    ::= 1371

-- end of lossOfText2 Input2 trap

-- beginning of lossOfText2 Input3 trap

    faultlossOfText2Input3False TRAP-TYPE
        ENTERPRISE  trapFault
        VARIABLES   { trapTag }
        DESCRIPTION
            "Loss of Text 2 Cleared on Input3"
    ::= 1372
    
    faultlossOfText2Input3True TRAP-TYPE
        ENTERPRISE  trapFault
        VARIABLES   { trapTag }
        DESCRIPTION
            "Loss of Text 2 Alert on Input3"
    ::= 1373

-- end of lossOfText2 Input3 trap

-- beginning of lossOfText2 Input4 trap

    faultlossOfText2Input4False TRAP-TYPE
        ENTERPRISE  trapFault
        VARIABLES   { trapTag }
        DESCRIPTION
            "Loss of Text 2 Cleared on Input4"
    ::= 1374
    
    faultlossOfText2Input4True TRAP-TYPE
        ENTERPRISE  trapFault
        VARIABLES   { trapTag }
        DESCRIPTION
            "Loss of Text 2 Alert on Input4"
    ::= 1375

-- end of lossOfText2 Input4 trap

-- beginning of lossOfText2 Input5 trap

    faultlossOfText2Input5False TRAP-TYPE
        ENTERPRISE  trapFault
        VARIABLES   { trapTag }
        DESCRIPTION
            "Loss of Text 2 Cleared on Input5"
    ::= 1376
    
    faultlossOfText2Input5True TRAP-TYPE
        ENTERPRISE  trapFault
        VARIABLES   { trapTag }
        DESCRIPTION
            "Loss of Text 2 Alert on Input5"
    ::= 1377

-- end of lossOfText2 Input5 trap

-- beginning of lossOfText2 Input6 trap

    faultlossOfText2Input6False TRAP-TYPE
        ENTERPRISE  trapFault
        VARIABLES   { trapTag }
        DESCRIPTION
            "Loss of Text 2 Cleared on Input6"
    ::= 1378
    
    faultlossOfText2Input6True TRAP-TYPE
        ENTERPRISE  trapFault
        VARIABLES   { trapTag }
        DESCRIPTION
            "Loss of Text 2 Alert on Input6"
    ::= 1379

-- end of lossOfText2 Input6 trap

-- beginning of lossOfText2 Input7 trap

    faultlossOfText2Input7False TRAP-TYPE
        ENTERPRISE  trapFault
        VARIABLES   { trapTag }
        DESCRIPTION
            "Loss of Text 2 Cleared on Input7"
    ::= 1380
    
    faultlossOfText2Input7True TRAP-TYPE
        ENTERPRISE  trapFault
        VARIABLES   { trapTag }
        DESCRIPTION
            "Loss of Text 2 Alert on Input7"
    ::= 1381

-- end of lossOfText2 Input7 trap

-- beginning of lossOfText2 Input8 trap

    faultlossOfText2Input8False TRAP-TYPE
        ENTERPRISE  trapFault
        VARIABLES   { trapTag }
        DESCRIPTION
            "Loss of Text 2 Cleared on Input8"
    ::= 1382
    
    faultlossOfText2Input8True TRAP-TYPE
        ENTERPRISE  trapFault
        VARIABLES   { trapTag }
        DESCRIPTION
            "Loss of Text 2 Alert on Input8"
    ::= 1383

-- end of lossOfText2 Input8 trap

-- beginning of lossOfText3 Input1 trap

    faultlossOfText3Input1False TRAP-TYPE
        ENTERPRISE  trapFault
        VARIABLES   { trapTag }
        DESCRIPTION
            "Loss of Text 3 Cleared on Input1"
    ::= 1384
    
    faultlossOfText3Input1True TRAP-TYPE
        ENTERPRISE  trapFault
        VARIABLES   { trapTag }
        DESCRIPTION
            "Loss of Text 3 Alert on Input1"
    ::= 1385

-- end of lossOfText3 Input1 trap

-- beginning of lossOfText3 Input2 trap

    faultlossOfText3Input2False TRAP-TYPE
        ENTERPRISE  trapFault
        VARIABLES   { trapTag }
        DESCRIPTION
            "Loss of Text 3 Cleared on Input2"
    ::= 1386
    
    faultlossOfText3Input2True TRAP-TYPE
        ENTERPRISE  trapFault
        VARIABLES   { trapTag }
        DESCRIPTION
            "Loss of Text 3 Alert on Input2"
    ::= 1387

-- end of lossOfText3 Input2 trap

-- beginning of lossOfText3 Input3 trap

    faultlossOfText3Input3False TRAP-TYPE
        ENTERPRISE  trapFault
        VARIABLES   { trapTag }
        DESCRIPTION
            "Loss of Text 3 Cleared on Input3"
    ::= 1388
    
    faultlossOfText3Input3True TRAP-TYPE
        ENTERPRISE  trapFault
        VARIABLES   { trapTag }
        DESCRIPTION
            "Loss of Text 3 Alert on Input3"
    ::= 1389

-- end of lossOfText3 Input3 trap

-- beginning of lossOfText3 Input4 trap

    faultlossOfText3Input4False TRAP-TYPE
        ENTERPRISE  trapFault
        VARIABLES   { trapTag }
        DESCRIPTION
            "Loss of Text 3 Cleared on Input4"
    ::= 1390
    
    faultlossOfText3Input4True TRAP-TYPE
        ENTERPRISE  trapFault
        VARIABLES   { trapTag }
        DESCRIPTION
            "Loss of Text 3 Alert on Input4"
    ::= 1391

-- end of lossOfText3 Input4 trap

-- beginning of lossOfText3 Input5 trap

    faultlossOfText3Input5False TRAP-TYPE
        ENTERPRISE  trapFault
        VARIABLES   { trapTag }
        DESCRIPTION
            "Loss of Text 3 Cleared on Input5"
    ::= 1392
    
    faultlossOfText3Input5True TRAP-TYPE
        ENTERPRISE  trapFault
        VARIABLES   { trapTag }
        DESCRIPTION
            "Loss of Text 3 Alert on Input5"
    ::= 1393

-- end of lossOfText3 Input5 trap

-- beginning of lossOfText3 Input6 trap

    faultlossOfText3Input6False TRAP-TYPE
        ENTERPRISE  trapFault
        VARIABLES   { trapTag }
        DESCRIPTION
            "Loss of Text 3 Cleared on Input6"
    ::= 1394
    
    faultlossOfText3Input6True TRAP-TYPE
        ENTERPRISE  trapFault
        VARIABLES   { trapTag }
        DESCRIPTION
            "Loss of Text 3 Alert on Input6"
    ::= 1395

-- end of lossOfText3 Input6 trap

-- beginning of lossOfText3 Input7 trap

    faultlossOfText3Input7False TRAP-TYPE
        ENTERPRISE  trapFault
        VARIABLES   { trapTag }
        DESCRIPTION
            "Loss of Text 3 Cleared on Input7"
    ::= 1396
    
    faultlossOfText3Input7True TRAP-TYPE
        ENTERPRISE  trapFault
        VARIABLES   { trapTag }
        DESCRIPTION
            "Loss of Text 3 Alert on Input7"
    ::= 1397

-- end of lossOfText3 Input7 trap

-- beginning of lossOfText3 Input8 trap

    faultlossOfText3Input8False TRAP-TYPE
        ENTERPRISE  trapFault
        VARIABLES   { trapTag }
        DESCRIPTION
            "Loss of Text 3 Cleared on Input8"
    ::= 1398
    
    faultlossOfText3Input8True TRAP-TYPE
        ENTERPRISE  trapFault
        VARIABLES   { trapTag }
        DESCRIPTION
            "Loss of Text 3 Alert on Input8"
    ::= 1399

-- end of lossOfText3 Input8 trap

-- beginning of lossOfText4 Input1 trap

    faultlossOfText4Input1False TRAP-TYPE
        ENTERPRISE  trapFault
        VARIABLES   { trapTag }
        DESCRIPTION
            "Loss of Text 4 Cleared on Input1"
    ::= 1400
    
    faultlossOfText4Input1True TRAP-TYPE
        ENTERPRISE  trapFault
        VARIABLES   { trapTag }
        DESCRIPTION
            "Loss of Text 4 Alert on Input1"
    ::= 1401

-- end of lossOfText4 Input1 trap

-- beginning of lossOfText4 Input2 trap

    faultlossOfText4Input2False TRAP-TYPE
        ENTERPRISE  trapFault
        VARIABLES   { trapTag }
        DESCRIPTION
            "Loss of Text 4 Cleared on Input2"
    ::= 1402
    
    faultlossOfText4Input2True TRAP-TYPE
        ENTERPRISE  trapFault
        VARIABLES   { trapTag }
        DESCRIPTION
            "Loss of Text 4 Alert on Input2"
    ::= 1403

-- end of lossOfText4 Input2 trap

-- beginning of lossOfText4 Input3 trap

    faultlossOfText4Input3False TRAP-TYPE
        ENTERPRISE  trapFault
        VARIABLES   { trapTag }
        DESCRIPTION
            "Loss of Text 4 Cleared on Input3"
    ::= 1404
    
    faultlossOfText4Input3True TRAP-TYPE
        ENTERPRISE  trapFault
        VARIABLES   { trapTag }
        DESCRIPTION
            "Loss of Text 4 Alert on Input3"
    ::= 1405

-- end of lossOfText4 Input3 trap

-- beginning of lossOfText4 Input4 trap

    faultlossOfText4Input4False TRAP-TYPE
        ENTERPRISE  trapFault
        VARIABLES   { trapTag }
        DESCRIPTION
            "Loss of Text 4 Cleared on Input4"
    ::= 1406
    
    faultlossOfText4Input4True TRAP-TYPE
        ENTERPRISE  trapFault
        VARIABLES   { trapTag }
        DESCRIPTION
            "Loss of Text 4 Alert on Input4"
    ::= 1407

-- end of lossOfText4 Input4 trap

-- beginning of lossOfText4 Input5 trap

    faultlossOfText4Input5False TRAP-TYPE
        ENTERPRISE  trapFault
        VARIABLES   { trapTag }
        DESCRIPTION
            "Loss of Text 4 Cleared on Input5"
    ::= 1408
    
    faultlossOfText4Input5True TRAP-TYPE
        ENTERPRISE  trapFault
        VARIABLES   { trapTag }
        DESCRIPTION
            "Loss of Text 4 Alert on Input5"
    ::= 1409

-- end of lossOfText4 Input5 trap

-- beginning of lossOfText4 Input6 trap

    faultlossOfText4Input6False TRAP-TYPE
        ENTERPRISE  trapFault
        VARIABLES   { trapTag }
        DESCRIPTION
            "Loss of Text 4 Cleared on Input6"
    ::= 1410
    
    faultlossOfText4Input6True TRAP-TYPE
        ENTERPRISE  trapFault
        VARIABLES   { trapTag }
        DESCRIPTION
            "Loss of Text 4 Alert on Input6"
    ::= 1411

-- end of lossOfText4 Input6 trap

-- beginning of lossOfText4 Input7 trap

    faultlossOfText4Input7False TRAP-TYPE
        ENTERPRISE  trapFault
        VARIABLES   { trapTag }
        DESCRIPTION
            "Loss of Text 4 Cleared on Input7"
    ::= 1412
    
    faultlossOfText4Input7True TRAP-TYPE
        ENTERPRISE  trapFault
        VARIABLES   { trapTag }
        DESCRIPTION
            "Loss of Text 4 Alert on Input7"
    ::= 1413

-- end of lossOfText4 Input7 trap

-- beginning of lossOfText4 Input8 trap

    faultlossOfText4Input8False TRAP-TYPE
        ENTERPRISE  trapFault
        VARIABLES   { trapTag }
        DESCRIPTION
            "Loss of Text 4 Cleared on Input8"
    ::= 1414
    
    faultlossOfText4Input8True TRAP-TYPE
        ENTERPRISE  trapFault
        VARIABLES   { trapTag }
        DESCRIPTION
            "Loss of Text 4 Alert on Input8"
    ::= 1415

-- end of lossOfText4 Input8 trap

-- beginning of lossOfXDS Input1 trap

    faultlossOfXDSInput1False TRAP-TYPE
        ENTERPRISE  trapFault
        VARIABLES   { trapTag }
        DESCRIPTION
            "Loss of Extended Data Services Cleared on Input1"
    ::= 1416
    
    faultlossOfXDSInput1True TRAP-TYPE
        ENTERPRISE  trapFault
        VARIABLES   { trapTag }
        DESCRIPTION
            "Loss of Extended Data Services Alert on Input1"
    ::= 1417

-- end of lossOfXDS Input1 trap

-- beginning of lossOfXDS Input2 trap

    faultlossOfXDSInput2False TRAP-TYPE
        ENTERPRISE  trapFault
        VARIABLES   { trapTag }
        DESCRIPTION
            "Loss of Extended Data Services Cleared on Input2"
    ::= 1418
    
    faultlossOfXDSInput2True TRAP-TYPE
        ENTERPRISE  trapFault
        VARIABLES   { trapTag }
        DESCRIPTION
            "Loss of Extended Data Services Alert on Input2"
    ::= 1419

-- end of lossOfXDS Input2 trap

-- beginning of lossOfXDS Input3 trap

    faultlossOfXDSInput3False TRAP-TYPE
        ENTERPRISE  trapFault
        VARIABLES   { trapTag }
        DESCRIPTION
            "Loss of Extended Data Services Cleared on Input3"
    ::= 1420
    
    faultlossOfXDSInput3True TRAP-TYPE
        ENTERPRISE  trapFault
        VARIABLES   { trapTag }
        DESCRIPTION
            "Loss of Extended Data Services Alert on Input3"
    ::= 1421

-- end of lossOfXDS Input3 trap

-- beginning of lossOfXDS Input4 trap

    faultlossOfXDSInput4False TRAP-TYPE
        ENTERPRISE  trapFault
        VARIABLES   { trapTag }
        DESCRIPTION
            "Loss of Extended Data Services Cleared on Input4"
    ::= 1422
    
    faultlossOfXDSInput4True TRAP-TYPE
        ENTERPRISE  trapFault
        VARIABLES   { trapTag }
        DESCRIPTION
            "Loss of Extended Data Services Alert on Input4"
    ::= 1423

-- end of lossOfXDS Input4 trap

-- beginning of lossOfXDS Input5 trap

    faultlossOfXDSInput5False TRAP-TYPE
        ENTERPRISE  trapFault
        VARIABLES   { trapTag }
        DESCRIPTION
            "Loss of Extended Data Services Cleared on Input5"
    ::= 1424
    
    faultlossOfXDSInput5True TRAP-TYPE
        ENTERPRISE  trapFault
        VARIABLES   { trapTag }
        DESCRIPTION
            "Loss of Extended Data Services Alert on Input5"
    ::= 1425

-- end of lossOfXDS Input5 trap

-- beginning of lossOfXDS Input6 trap

    faultlossOfXDSInput6False TRAP-TYPE
        ENTERPRISE  trapFault
        VARIABLES   { trapTag }
        DESCRIPTION
            "Loss of Extended Data Services Cleared on Input6"
    ::= 1426
    
    faultlossOfXDSInput6True TRAP-TYPE
        ENTERPRISE  trapFault
        VARIABLES   { trapTag }
        DESCRIPTION
            "Loss of Extended Data Services Alert on Input6"
    ::= 1427

-- end of lossOfXDS Input6 trap

-- beginning of lossOfXDS Input7 trap

    faultlossOfXDSInput7False TRAP-TYPE
        ENTERPRISE  trapFault
        VARIABLES   { trapTag }
        DESCRIPTION
            "Loss of Extended Data Services Cleared on Input7"
    ::= 1428
    
    faultlossOfXDSInput7True TRAP-TYPE
        ENTERPRISE  trapFault
        VARIABLES   { trapTag }
        DESCRIPTION
            "Loss of Extended Data Services Alert on Input7"
    ::= 1429

-- end of lossOfXDS Input7 trap

-- beginning of lossOfXDS Input8 trap

    faultlossOfXDSInput8False TRAP-TYPE
        ENTERPRISE  trapFault
        VARIABLES   { trapTag }
        DESCRIPTION
            "Loss of Extended Data Services Cleared on Input8"
    ::= 1430
    
    faultlossOfXDSInput8True TRAP-TYPE
        ENTERPRISE  trapFault
        VARIABLES   { trapTag }
        DESCRIPTION
            "Loss of Extended Data Services Alert on Input8"
    ::= 1431

-- end of lossOfXDS Input8 trap

-- beginning of lossOfCCWaveform Input1 trap

    faultlossOfCCWaveformInput1False TRAP-TYPE
        ENTERPRISE  trapFault
        VARIABLES   { trapTag }
        DESCRIPTION
            "Loss of CC Waveform Cleared on Input1"
    ::= 1432
    
    faultlossOfCCWaveformInput1True TRAP-TYPE
        ENTERPRISE  trapFault
        VARIABLES   { trapTag }
        DESCRIPTION
            "Loss of CC Waveform Alert on Input1"
    ::= 1433

-- end of lossOfCCWaveform Input1 trap

-- beginning of lossOfCCWaveform Input2 trap

    faultlossOfCCWaveformInput2False TRAP-TYPE
        ENTERPRISE  trapFault
        VARIABLES   { trapTag }
        DESCRIPTION
            "Loss of CC Waveform Cleared on Input2"
    ::= 1434
    
    faultlossOfCCWaveformInput2True TRAP-TYPE
        ENTERPRISE  trapFault
        VARIABLES   { trapTag }
        DESCRIPTION
            "Loss of CC Waveform Alert on Input2"
    ::= 1435

-- end of lossOfCCWaveform Input2 trap

-- beginning of lossOfCCWaveform Input3 trap

    faultlossOfCCWaveformInput3False TRAP-TYPE
        ENTERPRISE  trapFault
        VARIABLES   { trapTag }
        DESCRIPTION
            "Loss of CC Waveform Cleared on Input3"
    ::= 1436
    
    faultlossOfCCWaveformInput3True TRAP-TYPE
        ENTERPRISE  trapFault
        VARIABLES   { trapTag }
        DESCRIPTION
            "Loss of CC Waveform Alert on Input3"
    ::= 1437

-- end of lossOfCCWaveform Input3 trap

-- beginning of lossOfCCWaveform Input4 trap

    faultlossOfCCWaveformInput4False TRAP-TYPE
        ENTERPRISE  trapFault
        VARIABLES   { trapTag }
        DESCRIPTION
            "Loss of CC Waveform Cleared on Input4"
    ::= 1438
    
    faultlossOfCCWaveformInput4True TRAP-TYPE
        ENTERPRISE  trapFault
        VARIABLES   { trapTag }
        DESCRIPTION
            "Loss of CC Waveform Alert on Input4"
    ::= 1439

-- end of lossOfCCWaveform Input4 trap

-- beginning of lossOfCCWaveform Input5 trap

    faultlossOfCCWaveformInput5False TRAP-TYPE
        ENTERPRISE  trapFault
        VARIABLES   { trapTag }
        DESCRIPTION
            "Loss of CC Waveform Cleared on Input5"
    ::= 1440
    
    faultlossOfCCWaveformInput5True TRAP-TYPE
        ENTERPRISE  trapFault
        VARIABLES   { trapTag }
        DESCRIPTION
            "Loss of CC Waveform Alert on Input5"
    ::= 1441

-- end of lossOfCCWaveform Input5 trap

-- beginning of lossOfCCWaveform Input6 trap

    faultlossOfCCWaveformInput6False TRAP-TYPE
        ENTERPRISE  trapFault
        VARIABLES   { trapTag }
        DESCRIPTION
            "Loss of CC Waveform Cleared on Input6"
    ::= 1442
    
    faultlossOfCCWaveformInput6True TRAP-TYPE
        ENTERPRISE  trapFault
        VARIABLES   { trapTag }
        DESCRIPTION
            "Loss of CC Waveform Alert on Input6"
    ::= 1443

-- end of lossOfCCWaveform Input6 trap

-- beginning of lossOfCCWaveform Input7 trap

    faultlossOfCCWaveformInput7False TRAP-TYPE
        ENTERPRISE  trapFault
        VARIABLES   { trapTag }
        DESCRIPTION
            "Loss of CC Waveform Cleared on Input7"
    ::= 1444
    
    faultlossOfCCWaveformInput7True TRAP-TYPE
        ENTERPRISE  trapFault
        VARIABLES   { trapTag }
        DESCRIPTION
            "Loss of CC Waveform Alert on Input7"
    ::= 1445

-- end of lossOfCCWaveform Input7 trap

-- beginning of lossOfCCWaveform Input8 trap

    faultlossOfCCWaveformInput8False TRAP-TYPE
        ENTERPRISE  trapFault
        VARIABLES   { trapTag }
        DESCRIPTION
            "Loss of CC Waveform Cleared on Input8"
    ::= 1446
    
    faultlossOfCCWaveformInput8True TRAP-TYPE
        ENTERPRISE  trapFault
        VARIABLES   { trapTag }
        DESCRIPTION
            "Loss of CC Waveform Alert on Input8"
    ::= 1447

-- end of lossOfCCWaveform Input8 trap

-- beginning of lossOfVITCWaveform Input1 trap

    faultlossOfVITCWaveformInput1False TRAP-TYPE
        ENTERPRISE  trapFault
        VARIABLES   { trapTag }
        DESCRIPTION
            "Loss Of VITC Waveform Cleared on Input1"
    ::= 1448
    
    faultlossOfVITCWaveformInput1True TRAP-TYPE
        ENTERPRISE  trapFault
        VARIABLES   { trapTag }
        DESCRIPTION
            "Loss Of VITC Waveform Alert on Input1"
    ::= 1449

-- end of lossOfVITCWaveform Input1 trap

-- beginning of lossOfVITCWaveform Input2 trap

    faultlossOfVITCWaveformInput2False TRAP-TYPE
        ENTERPRISE  trapFault
        VARIABLES   { trapTag }
        DESCRIPTION
            "Loss Of VITC Waveform Cleared on Input2"
    ::= 1450
    
    faultlossOfVITCWaveformInput2True TRAP-TYPE
        ENTERPRISE  trapFault
        VARIABLES   { trapTag }
        DESCRIPTION
            "Loss Of VITC Waveform Alert on Input2"
    ::= 1451

-- end of lossOfVITCWaveform Input2 trap

-- beginning of lossOfVITCWaveform Input3 trap

    faultlossOfVITCWaveformInput3False TRAP-TYPE
        ENTERPRISE  trapFault
        VARIABLES   { trapTag }
        DESCRIPTION
            "Loss Of VITC Waveform Cleared on Input3"
    ::= 1452
    
    faultlossOfVITCWaveformInput3True TRAP-TYPE
        ENTERPRISE  trapFault
        VARIABLES   { trapTag }
        DESCRIPTION
            "Loss Of VITC Waveform Alert on Input3"
    ::= 1453

-- end of lossOfVITCWaveform Input3 trap

-- beginning of lossOfVITCWaveform Input4 trap

    faultlossOfVITCWaveformInput4False TRAP-TYPE
        ENTERPRISE  trapFault
        VARIABLES   { trapTag }
        DESCRIPTION
            "Loss Of VITC Waveform Cleared on Input4"
    ::= 1454
    
    faultlossOfVITCWaveformInput4True TRAP-TYPE
        ENTERPRISE  trapFault
        VARIABLES   { trapTag }
        DESCRIPTION
            "Loss Of VITC Waveform Alert on Input4"
    ::= 1455

-- end of lossOfVITCWaveform Input4 trap

-- beginning of lossOfVITCWaveform Input5 trap

    faultlossOfVITCWaveformInput5False TRAP-TYPE
        ENTERPRISE  trapFault
        VARIABLES   { trapTag }
        DESCRIPTION
            "Loss Of VITC Waveform Cleared on Input5"
    ::= 1456
    
    faultlossOfVITCWaveformInput5True TRAP-TYPE
        ENTERPRISE  trapFault
        VARIABLES   { trapTag }
        DESCRIPTION
            "Loss Of VITC Waveform Alert on Input5"
    ::= 1457

-- end of lossOfVITCWaveform Input5 trap

-- beginning of lossOfVITCWaveform Input6 trap

    faultlossOfVITCWaveformInput6False TRAP-TYPE
        ENTERPRISE  trapFault
        VARIABLES   { trapTag }
        DESCRIPTION
            "Loss Of VITC Waveform Cleared on Input6"
    ::= 1458
    
    faultlossOfVITCWaveformInput6True TRAP-TYPE
        ENTERPRISE  trapFault
        VARIABLES   { trapTag }
        DESCRIPTION
            "Loss Of VITC Waveform Alert on Input6"
    ::= 1459

-- end of lossOfVITCWaveform Input6 trap

-- beginning of lossOfVITCWaveform Input7 trap

    faultlossOfVITCWaveformInput7False TRAP-TYPE
        ENTERPRISE  trapFault
        VARIABLES   { trapTag }
        DESCRIPTION
            "Loss Of VITC Waveform Cleared on Input7"
    ::= 1460
    
    faultlossOfVITCWaveformInput7True TRAP-TYPE
        ENTERPRISE  trapFault
        VARIABLES   { trapTag }
        DESCRIPTION
            "Loss Of VITC Waveform Alert on Input7"
    ::= 1461

-- end of lossOfVITCWaveform Input7 trap

-- beginning of lossOfVITCWaveform Input8 trap

    faultlossOfVITCWaveformInput8False TRAP-TYPE
        ENTERPRISE  trapFault
        VARIABLES   { trapTag }
        DESCRIPTION
            "Loss Of VITC Waveform Cleared on Input8"
    ::= 1462
    
    faultlossOfVITCWaveformInput8True TRAP-TYPE
        ENTERPRISE  trapFault
        VARIABLES   { trapTag }
        DESCRIPTION
            "Loss Of VITC Waveform Alert on Input8"
    ::= 1463

-- end of lossOfVITCWaveform Input8 trap

-- beginning of changeOfPR Input1 trap

    faultchangeOfPRInput1False TRAP-TYPE
        ENTERPRISE  trapFault
        VARIABLES   { trapTag }
        DESCRIPTION
            "Change of Program Rating Cleared on Input1"
    ::= 1464
    
    faultchangeOfPRInput1True TRAP-TYPE
        ENTERPRISE  trapFault
        VARIABLES   { trapTag }
        DESCRIPTION
            "Change of Program Rating Alert on Input1"
    ::= 1465

-- end of changeOfPR Input1 trap

-- beginning of changeOfPR Input2 trap

    faultchangeOfPRInput2False TRAP-TYPE
        ENTERPRISE  trapFault
        VARIABLES   { trapTag }
        DESCRIPTION
            "Change of Program Rating Cleared on Input2"
    ::= 1466
    
    faultchangeOfPRInput2True TRAP-TYPE
        ENTERPRISE  trapFault
        VARIABLES   { trapTag }
        DESCRIPTION
            "Change of Program Rating Alert on Input2"
    ::= 1467

-- end of changeOfPR Input2 trap

-- beginning of changeOfPR Input3 trap

    faultchangeOfPRInput3False TRAP-TYPE
        ENTERPRISE  trapFault
        VARIABLES   { trapTag }
        DESCRIPTION
            "Change of Program Rating Cleared on Input3"
    ::= 1468
    
    faultchangeOfPRInput3True TRAP-TYPE
        ENTERPRISE  trapFault
        VARIABLES   { trapTag }
        DESCRIPTION
            "Change of Program Rating Alert on Input3"
    ::= 1469

-- end of changeOfPR Input3 trap

-- beginning of changeOfPR Input4 trap

    faultchangeOfPRInput4False TRAP-TYPE
        ENTERPRISE  trapFault
        VARIABLES   { trapTag }
        DESCRIPTION
            "Change of Program Rating Cleared on Input4"
    ::= 1470
    
    faultchangeOfPRInput4True TRAP-TYPE
        ENTERPRISE  trapFault
        VARIABLES   { trapTag }
        DESCRIPTION
            "Change of Program Rating Alert on Input4"
    ::= 1471

-- end of changeOfPR Input4 trap

-- beginning of changeOfPR Input5 trap

    faultchangeOfPRInput5False TRAP-TYPE
        ENTERPRISE  trapFault
        VARIABLES   { trapTag }
        DESCRIPTION
            "Change of Program Rating Cleared on Input5"
    ::= 1472
    
    faultchangeOfPRInput5True TRAP-TYPE
        ENTERPRISE  trapFault
        VARIABLES   { trapTag }
        DESCRIPTION
            "Change of Program Rating Alert on Input5"
    ::= 1473

-- end of changeOfPR Input5 trap

-- beginning of changeOfPR Input6 trap

    faultchangeOfPRInput6False TRAP-TYPE
        ENTERPRISE  trapFault
        VARIABLES   { trapTag }
        DESCRIPTION
            "Change of Program Rating Cleared on Input6"
    ::= 1474
    
    faultchangeOfPRInput6True TRAP-TYPE
        ENTERPRISE  trapFault
        VARIABLES   { trapTag }
        DESCRIPTION
            "Change of Program Rating Alert on Input6"
    ::= 1475

-- end of changeOfPR Input6 trap

-- beginning of changeOfPR Input7 trap

    faultchangeOfPRInput7False TRAP-TYPE
        ENTERPRISE  trapFault
        VARIABLES   { trapTag }
        DESCRIPTION
            "Change of Program Rating Cleared on Input7"
    ::= 1476
    
    faultchangeOfPRInput7True TRAP-TYPE
        ENTERPRISE  trapFault
        VARIABLES   { trapTag }
        DESCRIPTION
            "Change of Program Rating Alert on Input7"
    ::= 1477

-- end of changeOfPR Input7 trap

-- beginning of changeOfPR Input8 trap

    faultchangeOfPRInput8False TRAP-TYPE
        ENTERPRISE  trapFault
        VARIABLES   { trapTag }
        DESCRIPTION
            "Change of Program Rating Cleared on Input8"
    ::= 1478
    
    faultchangeOfPRInput8True TRAP-TYPE
        ENTERPRISE  trapFault
        VARIABLES   { trapTag }
        DESCRIPTION
            "Change of Program Rating Alert on Input8"
    ::= 1479

-- end of changeOfPR Input8 trap

-- beginning of lossOfWST Input1 trap

    faultlossOfWSTInput1False TRAP-TYPE
        ENTERPRISE  trapFault
        VARIABLES   { trapTag }
        DESCRIPTION
            "Loss of World Standard Teletext Cleared on Input1"
    ::= 1480
    
    faultlossOfWSTInput1True TRAP-TYPE
        ENTERPRISE  trapFault
        VARIABLES   { trapTag }
        DESCRIPTION
            "Loss of World Standard Teletext Alert on Input1"
    ::= 1481

-- end of lossOfWST Input1 trap

-- beginning of lossOfWST Input2 trap

    faultlossOfWSTInput2False TRAP-TYPE
        ENTERPRISE  trapFault
        VARIABLES   { trapTag }
        DESCRIPTION
            "Loss of World Standard Teletext Cleared on Input2"
    ::= 1482
    
    faultlossOfWSTInput2True TRAP-TYPE
        ENTERPRISE  trapFault
        VARIABLES   { trapTag }
        DESCRIPTION
            "Loss of World Standard Teletext Alert on Input2"
    ::= 1483

-- end of lossOfWST Input2 trap

-- beginning of lossOfWST Input3 trap

    faultlossOfWSTInput3False TRAP-TYPE
        ENTERPRISE  trapFault
        VARIABLES   { trapTag }
        DESCRIPTION
            "Loss of World Standard Teletext Cleared on Input3"
    ::= 1484
    
    faultlossOfWSTInput3True TRAP-TYPE
        ENTERPRISE  trapFault
        VARIABLES   { trapTag }
        DESCRIPTION
            "Loss of World Standard Teletext Alert on Input3"
    ::= 1485

-- end of lossOfWST Input3 trap

-- beginning of lossOfWST Input4 trap

    faultlossOfWSTInput4False TRAP-TYPE
        ENTERPRISE  trapFault
        VARIABLES   { trapTag }
        DESCRIPTION
            "Loss of World Standard Teletext Cleared on Input4"
    ::= 1486
    
    faultlossOfWSTInput4True TRAP-TYPE
        ENTERPRISE  trapFault
        VARIABLES   { trapTag }
        DESCRIPTION
            "Loss of World Standard Teletext Alert on Input4"
    ::= 1487

-- end of lossOfWST Input4 trap

-- beginning of lossOfWST Input5 trap

    faultlossOfWSTInput5False TRAP-TYPE
        ENTERPRISE  trapFault
        VARIABLES   { trapTag }
        DESCRIPTION
            "Loss of World Standard Teletext Cleared on Input5"
    ::= 1488
    
    faultlossOfWSTInput5True TRAP-TYPE
        ENTERPRISE  trapFault
        VARIABLES   { trapTag }
        DESCRIPTION
            "Loss of World Standard Teletext Alert on Input5"
    ::= 1489

-- end of lossOfWST Input5 trap

-- beginning of lossOfWST Input6 trap

    faultlossOfWSTInput6False TRAP-TYPE
        ENTERPRISE  trapFault
        VARIABLES   { trapTag }
        DESCRIPTION
            "Loss of World Standard Teletext Cleared on Input6"
    ::= 1490
    
    faultlossOfWSTInput6True TRAP-TYPE
        ENTERPRISE  trapFault
        VARIABLES   { trapTag }
        DESCRIPTION
            "Loss of World Standard Teletext Alert on Input6"
    ::= 1491

-- end of lossOfWST Input6 trap

-- beginning of lossOfWST Input7 trap

    faultlossOfWSTInput7False TRAP-TYPE
        ENTERPRISE  trapFault
        VARIABLES   { trapTag }
        DESCRIPTION
            "Loss of World Standard Teletext Cleared on Input7"
    ::= 1492
    
    faultlossOfWSTInput7True TRAP-TYPE
        ENTERPRISE  trapFault
        VARIABLES   { trapTag }
        DESCRIPTION
            "Loss of World Standard Teletext Alert on Input7"
    ::= 1493

-- end of lossOfWST Input7 trap

-- beginning of lossOfWST Input8 trap

    faultlossOfWSTInput8False TRAP-TYPE
        ENTERPRISE  trapFault
        VARIABLES   { trapTag }
        DESCRIPTION
            "Loss of World Standard Teletext Cleared on Input8"
    ::= 1494
    
    faultlossOfWSTInput8True TRAP-TYPE
        ENTERPRISE  trapFault
        VARIABLES   { trapTag }
        DESCRIPTION
            "Loss of World Standard Teletext Alert on Input8"
    ::= 1495

-- end of lossOfWST Input8 trap

-- beginning of futureUse3 Input1 trap

    faultfutureUse3Input1False TRAP-TYPE
        ENTERPRISE  trapFault
        VARIABLES   { trapTag }
        DESCRIPTION
            "FutureUse3 Cleared on Input1"
    ::= 1496
    
    faultfutureUse3Input1True TRAP-TYPE
        ENTERPRISE  trapFault
        VARIABLES   { trapTag }
        DESCRIPTION
            "FutureUse3 Alert on Input1"
    ::= 1497

-- end of futureUse3 Input1 trap

-- beginning of futureUse3 Input2 trap

    faultfutureUse3Input2False TRAP-TYPE
        ENTERPRISE  trapFault
        VARIABLES   { trapTag }
        DESCRIPTION
            "FutureUse3 Cleared on Input2"
    ::= 1498
    
    faultfutureUse3Input2True TRAP-TYPE
        ENTERPRISE  trapFault
        VARIABLES   { trapTag }
        DESCRIPTION
            "FutureUse3 Alert on Input2"
    ::= 1499

-- end of futureUse3 Input2 trap

-- beginning of futureUse3 Input3 trap

    faultfutureUse3Input3False TRAP-TYPE
        ENTERPRISE  trapFault
        VARIABLES   { trapTag }
        DESCRIPTION
            "FutureUse3 Cleared on Input3"
    ::= 1500
    
    faultfutureUse3Input3True TRAP-TYPE
        ENTERPRISE  trapFault
        VARIABLES   { trapTag }
        DESCRIPTION
            "FutureUse3 Alert on Input3"
    ::= 1501

-- end of futureUse3 Input3 trap

-- beginning of futureUse3 Input4 trap

    faultfutureUse3Input4False TRAP-TYPE
        ENTERPRISE  trapFault
        VARIABLES   { trapTag }
        DESCRIPTION
            "FutureUse3 Cleared on Input4"
    ::= 1502
    
    faultfutureUse3Input4True TRAP-TYPE
        ENTERPRISE  trapFault
        VARIABLES   { trapTag }
        DESCRIPTION
            "FutureUse3 Alert on Input4"
    ::= 1503

-- end of futureUse3 Input4 trap

-- beginning of futureUse3 Input5 trap

    faultfutureUse3Input5False TRAP-TYPE
        ENTERPRISE  trapFault
        VARIABLES   { trapTag }
        DESCRIPTION
            "FutureUse3 Cleared on Input5"
    ::= 1504
    
    faultfutureUse3Input5True TRAP-TYPE
        ENTERPRISE  trapFault
        VARIABLES   { trapTag }
        DESCRIPTION
            "FutureUse3 Alert on Input5"
    ::= 1505

-- end of futureUse3 Input5 trap

-- beginning of futureUse3 Input6 trap

    faultfutureUse3Input6False TRAP-TYPE
        ENTERPRISE  trapFault
        VARIABLES   { trapTag }
        DESCRIPTION
            "FutureUse3 Cleared on Input6"
    ::= 1506
    
    faultfutureUse3Input6True TRAP-TYPE
        ENTERPRISE  trapFault
        VARIABLES   { trapTag }
        DESCRIPTION
            "FutureUse3 Alert on Input6"
    ::= 1507

-- end of futureUse3 Input6 trap

-- beginning of futureUse3 Input7 trap

    faultfutureUse3Input7False TRAP-TYPE
        ENTERPRISE  trapFault
        VARIABLES   { trapTag }
        DESCRIPTION
            "FutureUse3 Cleared on Input7"
    ::= 1508
    
    faultfutureUse3Input7True TRAP-TYPE
        ENTERPRISE  trapFault
        VARIABLES   { trapTag }
        DESCRIPTION
            "FutureUse3 Alert on Input7"
    ::= 1509

-- end of futureUse3 Input7 trap

-- beginning of futureUse3 Input8 trap

    faultfutureUse3Input8False TRAP-TYPE
        ENTERPRISE  trapFault
        VARIABLES   { trapTag }
        DESCRIPTION
            "FutureUse3 Cleared on Input8"
    ::= 1510
    
    faultfutureUse3Input8True TRAP-TYPE
        ENTERPRISE  trapFault
        VARIABLES   { trapTag }
        DESCRIPTION
            "FutureUse3 Alert on Input8"
    ::= 1511

-- end of futureUse3 Input8 trap

-- beginning of lossOfAudioCH1 Input1 trap

    faultlossOfAudioCH1Input1False TRAP-TYPE
        ENTERPRISE  trapFault
        VARIABLES   { trapTag }
        DESCRIPTION
            "Audio Channel 1 Loss Cleared on Input1"
    ::= 1512
    
    faultlossOfAudioCH1Input1True TRAP-TYPE
        ENTERPRISE  trapFault
        VARIABLES   { trapTag }
        DESCRIPTION
            "Audio Channel 1 Loss Alert on Input1"
    ::= 1513

-- end of lossOfAudioCH1 Input1 trap

-- beginning of lossOfAudioCH1 Input2 trap

    faultlossOfAudioCH1Input2False TRAP-TYPE
        ENTERPRISE  trapFault
        VARIABLES   { trapTag }
        DESCRIPTION
            "Audio Channel 1 Loss Cleared on Input2"
    ::= 1514
    
    faultlossOfAudioCH1Input2True TRAP-TYPE
        ENTERPRISE  trapFault
        VARIABLES   { trapTag }
        DESCRIPTION
            "Audio Channel 1 Loss Alert on Input2"
    ::= 1515

-- end of lossOfAudioCH1 Input2 trap

-- beginning of lossOfAudioCH1 Input3 trap

    faultlossOfAudioCH1Input3False TRAP-TYPE
        ENTERPRISE  trapFault
        VARIABLES   { trapTag }
        DESCRIPTION
            "Audio Channel 1 Loss Cleared on Input3"
    ::= 1516
    
    faultlossOfAudioCH1Input3True TRAP-TYPE
        ENTERPRISE  trapFault
        VARIABLES   { trapTag }
        DESCRIPTION
            "Audio Channel 1 Loss Alert on Input3"
    ::= 1517

-- end of lossOfAudioCH1 Input3 trap

-- beginning of lossOfAudioCH1 Input4 trap

    faultlossOfAudioCH1Input4False TRAP-TYPE
        ENTERPRISE  trapFault
        VARIABLES   { trapTag }
        DESCRIPTION
            "Audio Channel 1 Loss Cleared on Input4"
    ::= 1518
    
    faultlossOfAudioCH1Input4True TRAP-TYPE
        ENTERPRISE  trapFault
        VARIABLES   { trapTag }
        DESCRIPTION
            "Audio Channel 1 Loss Alert on Input4"
    ::= 1519

-- end of lossOfAudioCH1 Input4 trap

-- beginning of lossOfAudioCH1 Input5 trap

    faultlossOfAudioCH1Input5False TRAP-TYPE
        ENTERPRISE  trapFault
        VARIABLES   { trapTag }
        DESCRIPTION
            "Audio Channel 1 Loss Cleared on Input5"
    ::= 1520
    
    faultlossOfAudioCH1Input5True TRAP-TYPE
        ENTERPRISE  trapFault
        VARIABLES   { trapTag }
        DESCRIPTION
            "Audio Channel 1 Loss Alert on Input5"
    ::= 1521

-- end of lossOfAudioCH1 Input5 trap

-- beginning of lossOfAudioCH1 Input6 trap

    faultlossOfAudioCH1Input6False TRAP-TYPE
        ENTERPRISE  trapFault
        VARIABLES   { trapTag }
        DESCRIPTION
            "Audio Channel 1 Loss Cleared on Input6"
    ::= 1522
    
    faultlossOfAudioCH1Input6True TRAP-TYPE
        ENTERPRISE  trapFault
        VARIABLES   { trapTag }
        DESCRIPTION
            "Audio Channel 1 Loss Alert on Input6"
    ::= 1523

-- end of lossOfAudioCH1 Input6 trap

-- beginning of lossOfAudioCH1 Input7 trap

    faultlossOfAudioCH1Input7False TRAP-TYPE
        ENTERPRISE  trapFault
        VARIABLES   { trapTag }
        DESCRIPTION
            "Audio Channel 1 Loss Cleared on Input7"
    ::= 1524
    
    faultlossOfAudioCH1Input7True TRAP-TYPE
        ENTERPRISE  trapFault
        VARIABLES   { trapTag }
        DESCRIPTION
            "Audio Channel 1 Loss Alert on Input7"
    ::= 1525

-- end of lossOfAudioCH1 Input7 trap

-- beginning of lossOfAudioCH1 Input8 trap

    faultlossOfAudioCH1Input8False TRAP-TYPE
        ENTERPRISE  trapFault
        VARIABLES   { trapTag }
        DESCRIPTION
            "Audio Channel 1 Loss Cleared on Input8"
    ::= 1526
    
    faultlossOfAudioCH1Input8True TRAP-TYPE
        ENTERPRISE  trapFault
        VARIABLES   { trapTag }
        DESCRIPTION
            "Audio Channel 1 Loss Alert on Input8"
    ::= 1527

-- end of lossOfAudioCH1 Input8 trap

-- beginning of lossOfAudioCH2 Input1 trap

    faultlossOfAudioCH2Input1False TRAP-TYPE
        ENTERPRISE  trapFault
        VARIABLES   { trapTag }
        DESCRIPTION
            "Audio Channel 2 Loss Cleared on Input1"
    ::= 1528
    
    faultlossOfAudioCH2Input1True TRAP-TYPE
        ENTERPRISE  trapFault
        VARIABLES   { trapTag }
        DESCRIPTION
            "Audio Channel 2 Loss Alert on Input1"
    ::= 1529

-- end of lossOfAudioCH2 Input1 trap

-- beginning of lossOfAudioCH2 Input2 trap

    faultlossOfAudioCH2Input2False TRAP-TYPE
        ENTERPRISE  trapFault
        VARIABLES   { trapTag }
        DESCRIPTION
            "Audio Channel 2 Loss Cleared on Input2"
    ::= 1530
    
    faultlossOfAudioCH2Input2True TRAP-TYPE
        ENTERPRISE  trapFault
        VARIABLES   { trapTag }
        DESCRIPTION
            "Audio Channel 2 Loss Alert on Input2"
    ::= 1531

-- end of lossOfAudioCH2 Input2 trap

-- beginning of lossOfAudioCH2 Input3 trap

    faultlossOfAudioCH2Input3False TRAP-TYPE
        ENTERPRISE  trapFault
        VARIABLES   { trapTag }
        DESCRIPTION
            "Audio Channel 2 Loss Cleared on Input3"
    ::= 1532
    
    faultlossOfAudioCH2Input3True TRAP-TYPE
        ENTERPRISE  trapFault
        VARIABLES   { trapTag }
        DESCRIPTION
            "Audio Channel 2 Loss Alert on Input3"
    ::= 1533

-- end of lossOfAudioCH2 Input3 trap

-- beginning of lossOfAudioCH2 Input4 trap

    faultlossOfAudioCH2Input4False TRAP-TYPE
        ENTERPRISE  trapFault
        VARIABLES   { trapTag }
        DESCRIPTION
            "Audio Channel 2 Loss Cleared on Input4"
    ::= 1534
    
    faultlossOfAudioCH2Input4True TRAP-TYPE
        ENTERPRISE  trapFault
        VARIABLES   { trapTag }
        DESCRIPTION
            "Audio Channel 2 Loss Alert on Input4"
    ::= 1535

-- end of lossOfAudioCH2 Input4 trap

-- beginning of lossOfAudioCH2 Input5 trap

    faultlossOfAudioCH2Input5False TRAP-TYPE
        ENTERPRISE  trapFault
        VARIABLES   { trapTag }
        DESCRIPTION
            "Audio Channel 2 Loss Cleared on Input5"
    ::= 1536
    
    faultlossOfAudioCH2Input5True TRAP-TYPE
        ENTERPRISE  trapFault
        VARIABLES   { trapTag }
        DESCRIPTION
            "Audio Channel 2 Loss Alert on Input5"
    ::= 1537

-- end of lossOfAudioCH2 Input5 trap

-- beginning of lossOfAudioCH2 Input6 trap

    faultlossOfAudioCH2Input6False TRAP-TYPE
        ENTERPRISE  trapFault
        VARIABLES   { trapTag }
        DESCRIPTION
            "Audio Channel 2 Loss Cleared on Input6"
    ::= 1538
    
    faultlossOfAudioCH2Input6True TRAP-TYPE
        ENTERPRISE  trapFault
        VARIABLES   { trapTag }
        DESCRIPTION
            "Audio Channel 2 Loss Alert on Input6"
    ::= 1539

-- end of lossOfAudioCH2 Input6 trap

-- beginning of lossOfAudioCH2 Input7 trap

    faultlossOfAudioCH2Input7False TRAP-TYPE
        ENTERPRISE  trapFault
        VARIABLES   { trapTag }
        DESCRIPTION
            "Audio Channel 2 Loss Cleared on Input7"
    ::= 1540
    
    faultlossOfAudioCH2Input7True TRAP-TYPE
        ENTERPRISE  trapFault
        VARIABLES   { trapTag }
        DESCRIPTION
            "Audio Channel 2 Loss Alert on Input7"
    ::= 1541

-- end of lossOfAudioCH2 Input7 trap

-- beginning of lossOfAudioCH2 Input8 trap

    faultlossOfAudioCH2Input8False TRAP-TYPE
        ENTERPRISE  trapFault
        VARIABLES   { trapTag }
        DESCRIPTION
            "Audio Channel 2 Loss Cleared on Input8"
    ::= 1542
    
    faultlossOfAudioCH2Input8True TRAP-TYPE
        ENTERPRISE  trapFault
        VARIABLES   { trapTag }
        DESCRIPTION
            "Audio Channel 2 Loss Alert on Input8"
    ::= 1543

-- end of lossOfAudioCH2 Input8 trap

-- beginning of lossOfAudioCH3 Input1 trap

    faultlossOfAudioCH3Input1False TRAP-TYPE
        ENTERPRISE  trapFault
        VARIABLES   { trapTag }
        DESCRIPTION
            "Audio Channel 3 Loss Cleared on Input1"
    ::= 1544
    
    faultlossOfAudioCH3Input1True TRAP-TYPE
        ENTERPRISE  trapFault
        VARIABLES   { trapTag }
        DESCRIPTION
            "Audio Channel 3 Loss Alert on Input1"
    ::= 1545

-- end of lossOfAudioCH3 Input1 trap

-- beginning of lossOfAudioCH3 Input2 trap

    faultlossOfAudioCH3Input2False TRAP-TYPE
        ENTERPRISE  trapFault
        VARIABLES   { trapTag }
        DESCRIPTION
            "Audio Channel 3 Loss Cleared on Input2"
    ::= 1546
    
    faultlossOfAudioCH3Input2True TRAP-TYPE
        ENTERPRISE  trapFault
        VARIABLES   { trapTag }
        DESCRIPTION
            "Audio Channel 3 Loss Alert on Input2"
    ::= 1547

-- end of lossOfAudioCH3 Input2 trap

-- beginning of lossOfAudioCH3 Input3 trap

    faultlossOfAudioCH3Input3False TRAP-TYPE
        ENTERPRISE  trapFault
        VARIABLES   { trapTag }
        DESCRIPTION
            "Audio Channel 3 Loss Cleared on Input3"
    ::= 1548
    
    faultlossOfAudioCH3Input3True TRAP-TYPE
        ENTERPRISE  trapFault
        VARIABLES   { trapTag }
        DESCRIPTION
            "Audio Channel 3 Loss Alert on Input3"
    ::= 1549

-- end of lossOfAudioCH3 Input3 trap

-- beginning of lossOfAudioCH3 Input4 trap

    faultlossOfAudioCH3Input4False TRAP-TYPE
        ENTERPRISE  trapFault
        VARIABLES   { trapTag }
        DESCRIPTION
            "Audio Channel 3 Loss Cleared on Input4"
    ::= 1550
    
    faultlossOfAudioCH3Input4True TRAP-TYPE
        ENTERPRISE  trapFault
        VARIABLES   { trapTag }
        DESCRIPTION
            "Audio Channel 3 Loss Alert on Input4"
    ::= 1551

-- end of lossOfAudioCH3 Input4 trap

-- beginning of lossOfAudioCH3 Input5 trap

    faultlossOfAudioCH3Input5False TRAP-TYPE
        ENTERPRISE  trapFault
        VARIABLES   { trapTag }
        DESCRIPTION
            "Audio Channel 3 Loss Cleared on Input5"
    ::= 1552
    
    faultlossOfAudioCH3Input5True TRAP-TYPE
        ENTERPRISE  trapFault
        VARIABLES   { trapTag }
        DESCRIPTION
            "Audio Channel 3 Loss Alert on Input5"
    ::= 1553

-- end of lossOfAudioCH3 Input5 trap

-- beginning of lossOfAudioCH3 Input6 trap

    faultlossOfAudioCH3Input6False TRAP-TYPE
        ENTERPRISE  trapFault
        VARIABLES   { trapTag }
        DESCRIPTION
            "Audio Channel 3 Loss Cleared on Input6"
    ::= 1554
    
    faultlossOfAudioCH3Input6True TRAP-TYPE
        ENTERPRISE  trapFault
        VARIABLES   { trapTag }
        DESCRIPTION
            "Audio Channel 3 Loss Alert on Input6"
    ::= 1555

-- end of lossOfAudioCH3 Input6 trap

-- beginning of lossOfAudioCH3 Input7 trap

    faultlossOfAudioCH3Input7False TRAP-TYPE
        ENTERPRISE  trapFault
        VARIABLES   { trapTag }
        DESCRIPTION
            "Audio Channel 3 Loss Cleared on Input7"
    ::= 1556
    
    faultlossOfAudioCH3Input7True TRAP-TYPE
        ENTERPRISE  trapFault
        VARIABLES   { trapTag }
        DESCRIPTION
            "Audio Channel 3 Loss Alert on Input7"
    ::= 1557

-- end of lossOfAudioCH3 Input7 trap

-- beginning of lossOfAudioCH3 Input8 trap

    faultlossOfAudioCH3Input8False TRAP-TYPE
        ENTERPRISE  trapFault
        VARIABLES   { trapTag }
        DESCRIPTION
            "Audio Channel 3 Loss Cleared on Input8"
    ::= 1558
    
    faultlossOfAudioCH3Input8True TRAP-TYPE
        ENTERPRISE  trapFault
        VARIABLES   { trapTag }
        DESCRIPTION
            "Audio Channel 3 Loss Alert on Input8"
    ::= 1559

-- end of lossOfAudioCH3 Input8 trap

-- beginning of lossOfAudioCH4 Input1 trap

    faultlossOfAudioCH4Input1False TRAP-TYPE
        ENTERPRISE  trapFault
        VARIABLES   { trapTag }
        DESCRIPTION
            "Audio Channel 4 Loss Cleared on Input1"
    ::= 1560
    
    faultlossOfAudioCH4Input1True TRAP-TYPE
        ENTERPRISE  trapFault
        VARIABLES   { trapTag }
        DESCRIPTION
            "Audio Channel 4 Loss Alert on Input1"
    ::= 1561

-- end of lossOfAudioCH4 Input1 trap

-- beginning of lossOfAudioCH4 Input2 trap

    faultlossOfAudioCH4Input2False TRAP-TYPE
        ENTERPRISE  trapFault
        VARIABLES   { trapTag }
        DESCRIPTION
            "Audio Channel 4 Loss Cleared on Input2"
    ::= 1562
    
    faultlossOfAudioCH4Input2True TRAP-TYPE
        ENTERPRISE  trapFault
        VARIABLES   { trapTag }
        DESCRIPTION
            "Audio Channel 4 Loss Alert on Input2"
    ::= 1563

-- end of lossOfAudioCH4 Input2 trap

-- beginning of lossOfAudioCH4 Input3 trap

    faultlossOfAudioCH4Input3False TRAP-TYPE
        ENTERPRISE  trapFault
        VARIABLES   { trapTag }
        DESCRIPTION
            "Audio Channel 4 Loss Cleared on Input3"
    ::= 1564
    
    faultlossOfAudioCH4Input3True TRAP-TYPE
        ENTERPRISE  trapFault
        VARIABLES   { trapTag }
        DESCRIPTION
            "Audio Channel 4 Loss Alert on Input3"
    ::= 1565

-- end of lossOfAudioCH4 Input3 trap

-- beginning of lossOfAudioCH4 Input4 trap

    faultlossOfAudioCH4Input4False TRAP-TYPE
        ENTERPRISE  trapFault
        VARIABLES   { trapTag }
        DESCRIPTION
            "Audio Channel 4 Loss Cleared on Input4"
    ::= 1566
    
    faultlossOfAudioCH4Input4True TRAP-TYPE
        ENTERPRISE  trapFault
        VARIABLES   { trapTag }
        DESCRIPTION
            "Audio Channel 4 Loss Alert on Input4"
    ::= 1567

-- end of lossOfAudioCH4 Input4 trap

-- beginning of lossOfAudioCH4 Input5 trap

    faultlossOfAudioCH4Input5False TRAP-TYPE
        ENTERPRISE  trapFault
        VARIABLES   { trapTag }
        DESCRIPTION
            "Audio Channel 4 Loss Cleared on Input5"
    ::= 1568
    
    faultlossOfAudioCH4Input5True TRAP-TYPE
        ENTERPRISE  trapFault
        VARIABLES   { trapTag }
        DESCRIPTION
            "Audio Channel 4 Loss Alert on Input5"
    ::= 1569

-- end of lossOfAudioCH4 Input5 trap

-- beginning of lossOfAudioCH4 Input6 trap

    faultlossOfAudioCH4Input6False TRAP-TYPE
        ENTERPRISE  trapFault
        VARIABLES   { trapTag }
        DESCRIPTION
            "Audio Channel 4 Loss Cleared on Input6"
    ::= 1570
    
    faultlossOfAudioCH4Input6True TRAP-TYPE
        ENTERPRISE  trapFault
        VARIABLES   { trapTag }
        DESCRIPTION
            "Audio Channel 4 Loss Alert on Input6"
    ::= 1571

-- end of lossOfAudioCH4 Input6 trap

-- beginning of lossOfAudioCH4 Input7 trap

    faultlossOfAudioCH4Input7False TRAP-TYPE
        ENTERPRISE  trapFault
        VARIABLES   { trapTag }
        DESCRIPTION
            "Audio Channel 4 Loss Cleared on Input7"
    ::= 1572
    
    faultlossOfAudioCH4Input7True TRAP-TYPE
        ENTERPRISE  trapFault
        VARIABLES   { trapTag }
        DESCRIPTION
            "Audio Channel 4 Loss Alert on Input7"
    ::= 1573

-- end of lossOfAudioCH4 Input7 trap

-- beginning of lossOfAudioCH4 Input8 trap

    faultlossOfAudioCH4Input8False TRAP-TYPE
        ENTERPRISE  trapFault
        VARIABLES   { trapTag }
        DESCRIPTION
            "Audio Channel 4 Loss Cleared on Input8"
    ::= 1574
    
    faultlossOfAudioCH4Input8True TRAP-TYPE
        ENTERPRISE  trapFault
        VARIABLES   { trapTag }
        DESCRIPTION
            "Audio Channel 4 Loss Alert on Input8"
    ::= 1575

-- end of lossOfAudioCH4 Input8 trap

-- beginning of lossOfAudioCH5 Input1 trap

    faultlossOfAudioCH5Input1False TRAP-TYPE
        ENTERPRISE  trapFault
        VARIABLES   { trapTag }
        DESCRIPTION
            "Audio Channel 5 Loss Cleared on Input1"
    ::= 1576
    
    faultlossOfAudioCH5Input1True TRAP-TYPE
        ENTERPRISE  trapFault
        VARIABLES   { trapTag }
        DESCRIPTION
            "Audio Channel 5 Loss Alert on Input1"
    ::= 1577

-- end of lossOfAudioCH5 Input1 trap

-- beginning of lossOfAudioCH5 Input2 trap

    faultlossOfAudioCH5Input2False TRAP-TYPE
        ENTERPRISE  trapFault
        VARIABLES   { trapTag }
        DESCRIPTION
            "Audio Channel 5 Loss Cleared on Input2"
    ::= 1578
    
    faultlossOfAudioCH5Input2True TRAP-TYPE
        ENTERPRISE  trapFault
        VARIABLES   { trapTag }
        DESCRIPTION
            "Audio Channel 5 Loss Alert on Input2"
    ::= 1579

-- end of lossOfAudioCH5 Input2 trap

-- beginning of lossOfAudioCH5 Input3 trap

    faultlossOfAudioCH5Input3False TRAP-TYPE
        ENTERPRISE  trapFault
        VARIABLES   { trapTag }
        DESCRIPTION
            "Audio Channel 5 Loss Cleared on Input3"
    ::= 1580
    
    faultlossOfAudioCH5Input3True TRAP-TYPE
        ENTERPRISE  trapFault
        VARIABLES   { trapTag }
        DESCRIPTION
            "Audio Channel 5 Loss Alert on Input3"
    ::= 1581

-- end of lossOfAudioCH5 Input3 trap

-- beginning of lossOfAudioCH5 Input4 trap

    faultlossOfAudioCH5Input4False TRAP-TYPE
        ENTERPRISE  trapFault
        VARIABLES   { trapTag }
        DESCRIPTION
            "Audio Channel 5 Loss Cleared on Input4"
    ::= 1582
    
    faultlossOfAudioCH5Input4True TRAP-TYPE
        ENTERPRISE  trapFault
        VARIABLES   { trapTag }
        DESCRIPTION
            "Audio Channel 5 Loss Alert on Input4"
    ::= 1583

-- end of lossOfAudioCH5 Input4 trap

-- beginning of lossOfAudioCH5 Input5 trap

    faultlossOfAudioCH5Input5False TRAP-TYPE
        ENTERPRISE  trapFault
        VARIABLES   { trapTag }
        DESCRIPTION
            "Audio Channel 5 Loss Cleared on Input5"
    ::= 1584
    
    faultlossOfAudioCH5Input5True TRAP-TYPE
        ENTERPRISE  trapFault
        VARIABLES   { trapTag }
        DESCRIPTION
            "Audio Channel 5 Loss Alert on Input5"
    ::= 1585

-- end of lossOfAudioCH5 Input5 trap

-- beginning of lossOfAudioCH5 Input6 trap

    faultlossOfAudioCH5Input6False TRAP-TYPE
        ENTERPRISE  trapFault
        VARIABLES   { trapTag }
        DESCRIPTION
            "Audio Channel 5 Loss Cleared on Input6"
    ::= 1586
    
    faultlossOfAudioCH5Input6True TRAP-TYPE
        ENTERPRISE  trapFault
        VARIABLES   { trapTag }
        DESCRIPTION
            "Audio Channel 5 Loss Alert on Input6"
    ::= 1587

-- end of lossOfAudioCH5 Input6 trap

-- beginning of lossOfAudioCH5 Input7 trap

    faultlossOfAudioCH5Input7False TRAP-TYPE
        ENTERPRISE  trapFault
        VARIABLES   { trapTag }
        DESCRIPTION
            "Audio Channel 5 Loss Cleared on Input7"
    ::= 1588
    
    faultlossOfAudioCH5Input7True TRAP-TYPE
        ENTERPRISE  trapFault
        VARIABLES   { trapTag }
        DESCRIPTION
            "Audio Channel 5 Loss Alert on Input7"
    ::= 1589

-- end of lossOfAudioCH5 Input7 trap

-- beginning of lossOfAudioCH5 Input8 trap

    faultlossOfAudioCH5Input8False TRAP-TYPE
        ENTERPRISE  trapFault
        VARIABLES   { trapTag }
        DESCRIPTION
            "Audio Channel 5 Loss Cleared on Input8"
    ::= 1590
    
    faultlossOfAudioCH5Input8True TRAP-TYPE
        ENTERPRISE  trapFault
        VARIABLES   { trapTag }
        DESCRIPTION
            "Audio Channel 5 Loss Alert on Input8"
    ::= 1591

-- end of lossOfAudioCH5 Input8 trap

-- beginning of lossOfAudioCH6 Input1 trap

    faultlossOfAudioCH6Input1False TRAP-TYPE
        ENTERPRISE  trapFault
        VARIABLES   { trapTag }
        DESCRIPTION
            "Audio Channel 6 Loss Cleared on Input1"
    ::= 1592
    
    faultlossOfAudioCH6Input1True TRAP-TYPE
        ENTERPRISE  trapFault
        VARIABLES   { trapTag }
        DESCRIPTION
            "Audio Channel 6 Loss Alert on Input1"
    ::= 1593

-- end of lossOfAudioCH6 Input1 trap

-- beginning of lossOfAudioCH6 Input2 trap

    faultlossOfAudioCH6Input2False TRAP-TYPE
        ENTERPRISE  trapFault
        VARIABLES   { trapTag }
        DESCRIPTION
            "Audio Channel 6 Loss Cleared on Input2"
    ::= 1594
    
    faultlossOfAudioCH6Input2True TRAP-TYPE
        ENTERPRISE  trapFault
        VARIABLES   { trapTag }
        DESCRIPTION
            "Audio Channel 6 Loss Alert on Input2"
    ::= 1595

-- end of lossOfAudioCH6 Input2 trap

-- beginning of lossOfAudioCH6 Input3 trap

    faultlossOfAudioCH6Input3False TRAP-TYPE
        ENTERPRISE  trapFault
        VARIABLES   { trapTag }
        DESCRIPTION
            "Audio Channel 6 Loss Cleared on Input3"
    ::= 1596
    
    faultlossOfAudioCH6Input3True TRAP-TYPE
        ENTERPRISE  trapFault
        VARIABLES   { trapTag }
        DESCRIPTION
            "Audio Channel 6 Loss Alert on Input3"
    ::= 1597

-- end of lossOfAudioCH6 Input3 trap

-- beginning of lossOfAudioCH6 Input4 trap

    faultlossOfAudioCH6Input4False TRAP-TYPE
        ENTERPRISE  trapFault
        VARIABLES   { trapTag }
        DESCRIPTION
            "Audio Channel 6 Loss Cleared on Input4"
    ::= 1598
    
    faultlossOfAudioCH6Input4True TRAP-TYPE
        ENTERPRISE  trapFault
        VARIABLES   { trapTag }
        DESCRIPTION
            "Audio Channel 6 Loss Alert on Input4"
    ::= 1599

-- end of lossOfAudioCH6 Input4 trap

-- beginning of lossOfAudioCH6 Input5 trap

    faultlossOfAudioCH6Input5False TRAP-TYPE
        ENTERPRISE  trapFault
        VARIABLES   { trapTag }
        DESCRIPTION
            "Audio Channel 6 Loss Cleared on Input5"
    ::= 1600
    
    faultlossOfAudioCH6Input5True TRAP-TYPE
        ENTERPRISE  trapFault
        VARIABLES   { trapTag }
        DESCRIPTION
            "Audio Channel 6 Loss Alert on Input5"
    ::= 1601

-- end of lossOfAudioCH6 Input5 trap

-- beginning of lossOfAudioCH6 Input6 trap

    faultlossOfAudioCH6Input6False TRAP-TYPE
        ENTERPRISE  trapFault
        VARIABLES   { trapTag }
        DESCRIPTION
            "Audio Channel 6 Loss Cleared on Input6"
    ::= 1602
    
    faultlossOfAudioCH6Input6True TRAP-TYPE
        ENTERPRISE  trapFault
        VARIABLES   { trapTag }
        DESCRIPTION
            "Audio Channel 6 Loss Alert on Input6"
    ::= 1603

-- end of lossOfAudioCH6 Input6 trap

-- beginning of lossOfAudioCH6 Input7 trap

    faultlossOfAudioCH6Input7False TRAP-TYPE
        ENTERPRISE  trapFault
        VARIABLES   { trapTag }
        DESCRIPTION
            "Audio Channel 6 Loss Cleared on Input7"
    ::= 1604
    
    faultlossOfAudioCH6Input7True TRAP-TYPE
        ENTERPRISE  trapFault
        VARIABLES   { trapTag }
        DESCRIPTION
            "Audio Channel 6 Loss Alert on Input7"
    ::= 1605

-- end of lossOfAudioCH6 Input7 trap

-- beginning of lossOfAudioCH6 Input8 trap

    faultlossOfAudioCH6Input8False TRAP-TYPE
        ENTERPRISE  trapFault
        VARIABLES   { trapTag }
        DESCRIPTION
            "Audio Channel 6 Loss Cleared on Input8"
    ::= 1606
    
    faultlossOfAudioCH6Input8True TRAP-TYPE
        ENTERPRISE  trapFault
        VARIABLES   { trapTag }
        DESCRIPTION
            "Audio Channel 6 Loss Alert on Input8"
    ::= 1607

-- end of lossOfAudioCH6 Input8 trap

-- beginning of lossOfAudioCH7 Input1 trap

    faultlossOfAudioCH7Input1False TRAP-TYPE
        ENTERPRISE  trapFault
        VARIABLES   { trapTag }
        DESCRIPTION
            "Audio Channel 7 Loss Cleared on Input1"
    ::= 1608
    
    faultlossOfAudioCH7Input1True TRAP-TYPE
        ENTERPRISE  trapFault
        VARIABLES   { trapTag }
        DESCRIPTION
            "Audio Channel 7 Loss Alert on Input1"
    ::= 1609

-- end of lossOfAudioCH7 Input1 trap

-- beginning of lossOfAudioCH7 Input2 trap

    faultlossOfAudioCH7Input2False TRAP-TYPE
        ENTERPRISE  trapFault
        VARIABLES   { trapTag }
        DESCRIPTION
            "Audio Channel 7 Loss Cleared on Input2"
    ::= 1610
    
    faultlossOfAudioCH7Input2True TRAP-TYPE
        ENTERPRISE  trapFault
        VARIABLES   { trapTag }
        DESCRIPTION
            "Audio Channel 7 Loss Alert on Input2"
    ::= 1611

-- end of lossOfAudioCH7 Input2 trap

-- beginning of lossOfAudioCH7 Input3 trap

    faultlossOfAudioCH7Input3False TRAP-TYPE
        ENTERPRISE  trapFault
        VARIABLES   { trapTag }
        DESCRIPTION
            "Audio Channel 7 Loss Cleared on Input3"
    ::= 1612
    
    faultlossOfAudioCH7Input3True TRAP-TYPE
        ENTERPRISE  trapFault
        VARIABLES   { trapTag }
        DESCRIPTION
            "Audio Channel 7 Loss Alert on Input3"
    ::= 1613

-- end of lossOfAudioCH7 Input3 trap

-- beginning of lossOfAudioCH7 Input4 trap

    faultlossOfAudioCH7Input4False TRAP-TYPE
        ENTERPRISE  trapFault
        VARIABLES   { trapTag }
        DESCRIPTION
            "Audio Channel 7 Loss Cleared on Input4"
    ::= 1614
    
    faultlossOfAudioCH7Input4True TRAP-TYPE
        ENTERPRISE  trapFault
        VARIABLES   { trapTag }
        DESCRIPTION
            "Audio Channel 7 Loss Alert on Input4"
    ::= 1615

-- end of lossOfAudioCH7 Input4 trap

-- beginning of lossOfAudioCH7 Input5 trap

    faultlossOfAudioCH7Input5False TRAP-TYPE
        ENTERPRISE  trapFault
        VARIABLES   { trapTag }
        DESCRIPTION
            "Audio Channel 7 Loss Cleared on Input5"
    ::= 1616
    
    faultlossOfAudioCH7Input5True TRAP-TYPE
        ENTERPRISE  trapFault
        VARIABLES   { trapTag }
        DESCRIPTION
            "Audio Channel 7 Loss Alert on Input5"
    ::= 1617

-- end of lossOfAudioCH7 Input5 trap

-- beginning of lossOfAudioCH7 Input6 trap

    faultlossOfAudioCH7Input6False TRAP-TYPE
        ENTERPRISE  trapFault
        VARIABLES   { trapTag }
        DESCRIPTION
            "Audio Channel 7 Loss Cleared on Input6"
    ::= 1618
    
    faultlossOfAudioCH7Input6True TRAP-TYPE
        ENTERPRISE  trapFault
        VARIABLES   { trapTag }
        DESCRIPTION
            "Audio Channel 7 Loss Alert on Input6"
    ::= 1619

-- end of lossOfAudioCH7 Input6 trap

-- beginning of lossOfAudioCH7 Input7 trap

    faultlossOfAudioCH7Input7False TRAP-TYPE
        ENTERPRISE  trapFault
        VARIABLES   { trapTag }
        DESCRIPTION
            "Audio Channel 7 Loss Cleared on Input7"
    ::= 1620
    
    faultlossOfAudioCH7Input7True TRAP-TYPE
        ENTERPRISE  trapFault
        VARIABLES   { trapTag }
        DESCRIPTION
            "Audio Channel 7 Loss Alert on Input7"
    ::= 1621

-- end of lossOfAudioCH7 Input7 trap

-- beginning of lossOfAudioCH7 Input8 trap

    faultlossOfAudioCH7Input8False TRAP-TYPE
        ENTERPRISE  trapFault
        VARIABLES   { trapTag }
        DESCRIPTION
            "Audio Channel 7 Loss Cleared on Input8"
    ::= 1622
    
    faultlossOfAudioCH7Input8True TRAP-TYPE
        ENTERPRISE  trapFault
        VARIABLES   { trapTag }
        DESCRIPTION
            "Audio Channel 7 Loss Alert on Input8"
    ::= 1623

-- end of lossOfAudioCH7 Input8 trap

-- beginning of lossOfAudioCH8 Input1 trap

    faultlossOfAudioCH8Input1False TRAP-TYPE
        ENTERPRISE  trapFault
        VARIABLES   { trapTag }
        DESCRIPTION
            "Audio Channel 8 Loss Cleared on Input1"
    ::= 1624
    
    faultlossOfAudioCH8Input1True TRAP-TYPE
        ENTERPRISE  trapFault
        VARIABLES   { trapTag }
        DESCRIPTION
            "Audio Channel 8 Loss Alert on Input1"
    ::= 1625

-- end of lossOfAudioCH8 Input1 trap

-- beginning of lossOfAudioCH8 Input2 trap

    faultlossOfAudioCH8Input2False TRAP-TYPE
        ENTERPRISE  trapFault
        VARIABLES   { trapTag }
        DESCRIPTION
            "Audio Channel 8 Loss Cleared on Input2"
    ::= 1626
    
    faultlossOfAudioCH8Input2True TRAP-TYPE
        ENTERPRISE  trapFault
        VARIABLES   { trapTag }
        DESCRIPTION
            "Audio Channel 8 Loss Alert on Input2"
    ::= 1627

-- end of lossOfAudioCH8 Input2 trap

-- beginning of lossOfAudioCH8 Input3 trap

    faultlossOfAudioCH8Input3False TRAP-TYPE
        ENTERPRISE  trapFault
        VARIABLES   { trapTag }
        DESCRIPTION
            "Audio Channel 8 Loss Cleared on Input3"
    ::= 1628
    
    faultlossOfAudioCH8Input3True TRAP-TYPE
        ENTERPRISE  trapFault
        VARIABLES   { trapTag }
        DESCRIPTION
            "Audio Channel 8 Loss Alert on Input3"
    ::= 1629

-- end of lossOfAudioCH8 Input3 trap

-- beginning of lossOfAudioCH8 Input4 trap

    faultlossOfAudioCH8Input4False TRAP-TYPE
        ENTERPRISE  trapFault
        VARIABLES   { trapTag }
        DESCRIPTION
            "Audio Channel 8 Loss Cleared on Input4"
    ::= 1630
    
    faultlossOfAudioCH8Input4True TRAP-TYPE
        ENTERPRISE  trapFault
        VARIABLES   { trapTag }
        DESCRIPTION
            "Audio Channel 8 Loss Alert on Input4"
    ::= 1631

-- end of lossOfAudioCH8 Input4 trap

-- beginning of lossOfAudioCH8 Input5 trap

    faultlossOfAudioCH8Input5False TRAP-TYPE
        ENTERPRISE  trapFault
        VARIABLES   { trapTag }
        DESCRIPTION
            "Audio Channel 8 Loss Cleared on Input5"
    ::= 1632
    
    faultlossOfAudioCH8Input5True TRAP-TYPE
        ENTERPRISE  trapFault
        VARIABLES   { trapTag }
        DESCRIPTION
            "Audio Channel 8 Loss Alert on Input5"
    ::= 1633

-- end of lossOfAudioCH8 Input5 trap

-- beginning of lossOfAudioCH8 Input6 trap

    faultlossOfAudioCH8Input6False TRAP-TYPE
        ENTERPRISE  trapFault
        VARIABLES   { trapTag }
        DESCRIPTION
            "Audio Channel 8 Loss Cleared on Input6"
    ::= 1634
    
    faultlossOfAudioCH8Input6True TRAP-TYPE
        ENTERPRISE  trapFault
        VARIABLES   { trapTag }
        DESCRIPTION
            "Audio Channel 8 Loss Alert on Input6"
    ::= 1635

-- end of lossOfAudioCH8 Input6 trap

-- beginning of lossOfAudioCH8 Input7 trap

    faultlossOfAudioCH8Input7False TRAP-TYPE
        ENTERPRISE  trapFault
        VARIABLES   { trapTag }
        DESCRIPTION
            "Audio Channel 8 Loss Cleared on Input7"
    ::= 1636
    
    faultlossOfAudioCH8Input7True TRAP-TYPE
        ENTERPRISE  trapFault
        VARIABLES   { trapTag }
        DESCRIPTION
            "Audio Channel 8 Loss Alert on Input7"
    ::= 1637

-- end of lossOfAudioCH8 Input7 trap

-- beginning of lossOfAudioCH8 Input8 trap

    faultlossOfAudioCH8Input8False TRAP-TYPE
        ENTERPRISE  trapFault
        VARIABLES   { trapTag }
        DESCRIPTION
            "Audio Channel 8 Loss Cleared on Input8"
    ::= 1638
    
    faultlossOfAudioCH8Input8True TRAP-TYPE
        ENTERPRISE  trapFault
        VARIABLES   { trapTag }
        DESCRIPTION
            "Audio Channel 8 Loss Alert on Input8"
    ::= 1639

-- end of lossOfAudioCH8 Input8 trap

-- beginning of audioCH1Silence Input1 trap

    faultaudioCH1SilenceInput1False TRAP-TYPE
        ENTERPRISE  trapFault
        VARIABLES   { trapTag }
        DESCRIPTION
            "Audio Channel 1 Silent Cleared on Input1"
    ::= 1640
    
    faultaudioCH1SilenceInput1True TRAP-TYPE
        ENTERPRISE  trapFault
        VARIABLES   { trapTag }
        DESCRIPTION
            "Audio Channel 1 Silent Alert on Input1"
    ::= 1641

-- end of audioCH1Silence Input1 trap

-- beginning of audioCH1Silence Input2 trap

    faultaudioCH1SilenceInput2False TRAP-TYPE
        ENTERPRISE  trapFault
        VARIABLES   { trapTag }
        DESCRIPTION
            "Audio Channel 1 Silent Cleared on Input2"
    ::= 1642
    
    faultaudioCH1SilenceInput2True TRAP-TYPE
        ENTERPRISE  trapFault
        VARIABLES   { trapTag }
        DESCRIPTION
            "Audio Channel 1 Silent Alert on Input2"
    ::= 1643

-- end of audioCH1Silence Input2 trap

-- beginning of audioCH1Silence Input3 trap

    faultaudioCH1SilenceInput3False TRAP-TYPE
        ENTERPRISE  trapFault
        VARIABLES   { trapTag }
        DESCRIPTION
            "Audio Channel 1 Silent Cleared on Input3"
    ::= 1644
    
    faultaudioCH1SilenceInput3True TRAP-TYPE
        ENTERPRISE  trapFault
        VARIABLES   { trapTag }
        DESCRIPTION
            "Audio Channel 1 Silent Alert on Input3"
    ::= 1645

-- end of audioCH1Silence Input3 trap

-- beginning of audioCH1Silence Input4 trap

    faultaudioCH1SilenceInput4False TRAP-TYPE
        ENTERPRISE  trapFault
        VARIABLES   { trapTag }
        DESCRIPTION
            "Audio Channel 1 Silent Cleared on Input4"
    ::= 1646
    
    faultaudioCH1SilenceInput4True TRAP-TYPE
        ENTERPRISE  trapFault
        VARIABLES   { trapTag }
        DESCRIPTION
            "Audio Channel 1 Silent Alert on Input4"
    ::= 1647

-- end of audioCH1Silence Input4 trap

-- beginning of audioCH1Silence Input5 trap

    faultaudioCH1SilenceInput5False TRAP-TYPE
        ENTERPRISE  trapFault
        VARIABLES   { trapTag }
        DESCRIPTION
            "Audio Channel 1 Silent Cleared on Input5"
    ::= 1648
    
    faultaudioCH1SilenceInput5True TRAP-TYPE
        ENTERPRISE  trapFault
        VARIABLES   { trapTag }
        DESCRIPTION
            "Audio Channel 1 Silent Alert on Input5"
    ::= 1649

-- end of audioCH1Silence Input5 trap

-- beginning of audioCH1Silence Input6 trap

    faultaudioCH1SilenceInput6False TRAP-TYPE
        ENTERPRISE  trapFault
        VARIABLES   { trapTag }
        DESCRIPTION
            "Audio Channel 1 Silent Cleared on Input6"
    ::= 1650
    
    faultaudioCH1SilenceInput6True TRAP-TYPE
        ENTERPRISE  trapFault
        VARIABLES   { trapTag }
        DESCRIPTION
            "Audio Channel 1 Silent Alert on Input6"
    ::= 1651

-- end of audioCH1Silence Input6 trap

-- beginning of audioCH1Silence Input7 trap

    faultaudioCH1SilenceInput7False TRAP-TYPE
        ENTERPRISE  trapFault
        VARIABLES   { trapTag }
        DESCRIPTION
            "Audio Channel 1 Silent Cleared on Input7"
    ::= 1652
    
    faultaudioCH1SilenceInput7True TRAP-TYPE
        ENTERPRISE  trapFault
        VARIABLES   { trapTag }
        DESCRIPTION
            "Audio Channel 1 Silent Alert on Input7"
    ::= 1653

-- end of audioCH1Silence Input7 trap

-- beginning of audioCH1Silence Input8 trap

    faultaudioCH1SilenceInput8False TRAP-TYPE
        ENTERPRISE  trapFault
        VARIABLES   { trapTag }
        DESCRIPTION
            "Audio Channel 1 Silent Cleared on Input8"
    ::= 1654
    
    faultaudioCH1SilenceInput8True TRAP-TYPE
        ENTERPRISE  trapFault
        VARIABLES   { trapTag }
        DESCRIPTION
            "Audio Channel 1 Silent Alert on Input8"
    ::= 1655

-- end of audioCH1Silence Input8 trap

-- beginning of audioCH2Silence Input1 trap

    faultaudioCH2SilenceInput1False TRAP-TYPE
        ENTERPRISE  trapFault
        VARIABLES   { trapTag }
        DESCRIPTION
            "Audio Channel 2 Silent Cleared on Input1"
    ::= 1656
    
    faultaudioCH2SilenceInput1True TRAP-TYPE
        ENTERPRISE  trapFault
        VARIABLES   { trapTag }
        DESCRIPTION
            "Audio Channel 2 Silent Alert on Input1"
    ::= 1657

-- end of audioCH2Silence Input1 trap

-- beginning of audioCH2Silence Input2 trap

    faultaudioCH2SilenceInput2False TRAP-TYPE
        ENTERPRISE  trapFault
        VARIABLES   { trapTag }
        DESCRIPTION
            "Audio Channel 2 Silent Cleared on Input2"
    ::= 1658
    
    faultaudioCH2SilenceInput2True TRAP-TYPE
        ENTERPRISE  trapFault
        VARIABLES   { trapTag }
        DESCRIPTION
            "Audio Channel 2 Silent Alert on Input2"
    ::= 1659

-- end of audioCH2Silence Input2 trap

-- beginning of audioCH2Silence Input3 trap

    faultaudioCH2SilenceInput3False TRAP-TYPE
        ENTERPRISE  trapFault
        VARIABLES   { trapTag }
        DESCRIPTION
            "Audio Channel 2 Silent Cleared on Input3"
    ::= 1660
    
    faultaudioCH2SilenceInput3True TRAP-TYPE
        ENTERPRISE  trapFault
        VARIABLES   { trapTag }
        DESCRIPTION
            "Audio Channel 2 Silent Alert on Input3"
    ::= 1661

-- end of audioCH2Silence Input3 trap

-- beginning of audioCH2Silence Input4 trap

    faultaudioCH2SilenceInput4False TRAP-TYPE
        ENTERPRISE  trapFault
        VARIABLES   { trapTag }
        DESCRIPTION
            "Audio Channel 2 Silent Cleared on Input4"
    ::= 1662
    
    faultaudioCH2SilenceInput4True TRAP-TYPE
        ENTERPRISE  trapFault
        VARIABLES   { trapTag }
        DESCRIPTION
            "Audio Channel 2 Silent Alert on Input4"
    ::= 1663

-- end of audioCH2Silence Input4 trap

-- beginning of audioCH2Silence Input5 trap

    faultaudioCH2SilenceInput5False TRAP-TYPE
        ENTERPRISE  trapFault
        VARIABLES   { trapTag }
        DESCRIPTION
            "Audio Channel 2 Silent Cleared on Input5"
    ::= 1664
    
    faultaudioCH2SilenceInput5True TRAP-TYPE
        ENTERPRISE  trapFault
        VARIABLES   { trapTag }
        DESCRIPTION
            "Audio Channel 2 Silent Alert on Input5"
    ::= 1665

-- end of audioCH2Silence Input5 trap

-- beginning of audioCH2Silence Input6 trap

    faultaudioCH2SilenceInput6False TRAP-TYPE
        ENTERPRISE  trapFault
        VARIABLES   { trapTag }
        DESCRIPTION
            "Audio Channel 2 Silent Cleared on Input6"
    ::= 1666
    
    faultaudioCH2SilenceInput6True TRAP-TYPE
        ENTERPRISE  trapFault
        VARIABLES   { trapTag }
        DESCRIPTION
            "Audio Channel 2 Silent Alert on Input6"
    ::= 1667

-- end of audioCH2Silence Input6 trap

-- beginning of audioCH2Silence Input7 trap

    faultaudioCH2SilenceInput7False TRAP-TYPE
        ENTERPRISE  trapFault
        VARIABLES   { trapTag }
        DESCRIPTION
            "Audio Channel 2 Silent Cleared on Input7"
    ::= 1668
    
    faultaudioCH2SilenceInput7True TRAP-TYPE
        ENTERPRISE  trapFault
        VARIABLES   { trapTag }
        DESCRIPTION
            "Audio Channel 2 Silent Alert on Input7"
    ::= 1669

-- end of audioCH2Silence Input7 trap

-- beginning of audioCH2Silence Input8 trap

    faultaudioCH2SilenceInput8False TRAP-TYPE
        ENTERPRISE  trapFault
        VARIABLES   { trapTag }
        DESCRIPTION
            "Audio Channel 2 Silent Cleared on Input8"
    ::= 1670
    
    faultaudioCH2SilenceInput8True TRAP-TYPE
        ENTERPRISE  trapFault
        VARIABLES   { trapTag }
        DESCRIPTION
            "Audio Channel 2 Silent Alert on Input8"
    ::= 1671

-- end of audioCH2Silence Input8 trap

-- beginning of audioCH3Silence Input1 trap

    faultaudioCH3SilenceInput1False TRAP-TYPE
        ENTERPRISE  trapFault
        VARIABLES   { trapTag }
        DESCRIPTION
            "Audio Channel 3 Silent Cleared on Input1"
    ::= 1672
    
    faultaudioCH3SilenceInput1True TRAP-TYPE
        ENTERPRISE  trapFault
        VARIABLES   { trapTag }
        DESCRIPTION
            "Audio Channel 3 Silent Alert on Input1"
    ::= 1673

-- end of audioCH3Silence Input1 trap

-- beginning of audioCH3Silence Input2 trap

    faultaudioCH3SilenceInput2False TRAP-TYPE
        ENTERPRISE  trapFault
        VARIABLES   { trapTag }
        DESCRIPTION
            "Audio Channel 3 Silent Cleared on Input2"
    ::= 1674
    
    faultaudioCH3SilenceInput2True TRAP-TYPE
        ENTERPRISE  trapFault
        VARIABLES   { trapTag }
        DESCRIPTION
            "Audio Channel 3 Silent Alert on Input2"
    ::= 1675

-- end of audioCH3Silence Input2 trap

-- beginning of audioCH3Silence Input3 trap

    faultaudioCH3SilenceInput3False TRAP-TYPE
        ENTERPRISE  trapFault
        VARIABLES   { trapTag }
        DESCRIPTION
            "Audio Channel 3 Silent Cleared on Input3"
    ::= 1676
    
    faultaudioCH3SilenceInput3True TRAP-TYPE
        ENTERPRISE  trapFault
        VARIABLES   { trapTag }
        DESCRIPTION
            "Audio Channel 3 Silent Alert on Input3"
    ::= 1677

-- end of audioCH3Silence Input3 trap

-- beginning of audioCH3Silence Input4 trap

    faultaudioCH3SilenceInput4False TRAP-TYPE
        ENTERPRISE  trapFault
        VARIABLES   { trapTag }
        DESCRIPTION
            "Audio Channel 3 Silent Cleared on Input4"
    ::= 1678
    
    faultaudioCH3SilenceInput4True TRAP-TYPE
        ENTERPRISE  trapFault
        VARIABLES   { trapTag }
        DESCRIPTION
            "Audio Channel 3 Silent Alert on Input4"
    ::= 1679

-- end of audioCH3Silence Input4 trap

-- beginning of audioCH3Silence Input5 trap

    faultaudioCH3SilenceInput5False TRAP-TYPE
        ENTERPRISE  trapFault
        VARIABLES   { trapTag }
        DESCRIPTION
            "Audio Channel 3 Silent Cleared on Input5"
    ::= 1680
    
    faultaudioCH3SilenceInput5True TRAP-TYPE
        ENTERPRISE  trapFault
        VARIABLES   { trapTag }
        DESCRIPTION
            "Audio Channel 3 Silent Alert on Input5"
    ::= 1681

-- end of audioCH3Silence Input5 trap

-- beginning of audioCH3Silence Input6 trap

    faultaudioCH3SilenceInput6False TRAP-TYPE
        ENTERPRISE  trapFault
        VARIABLES   { trapTag }
        DESCRIPTION
            "Audio Channel 3 Silent Cleared on Input6"
    ::= 1682
    
    faultaudioCH3SilenceInput6True TRAP-TYPE
        ENTERPRISE  trapFault
        VARIABLES   { trapTag }
        DESCRIPTION
            "Audio Channel 3 Silent Alert on Input6"
    ::= 1683

-- end of audioCH3Silence Input6 trap

-- beginning of audioCH3Silence Input7 trap

    faultaudioCH3SilenceInput7False TRAP-TYPE
        ENTERPRISE  trapFault
        VARIABLES   { trapTag }
        DESCRIPTION
            "Audio Channel 3 Silent Cleared on Input7"
    ::= 1684
    
    faultaudioCH3SilenceInput7True TRAP-TYPE
        ENTERPRISE  trapFault
        VARIABLES   { trapTag }
        DESCRIPTION
            "Audio Channel 3 Silent Alert on Input7"
    ::= 1685

-- end of audioCH3Silence Input7 trap

-- beginning of audioCH3Silence Input8 trap

    faultaudioCH3SilenceInput8False TRAP-TYPE
        ENTERPRISE  trapFault
        VARIABLES   { trapTag }
        DESCRIPTION
            "Audio Channel 3 Silent Cleared on Input8"
    ::= 1686
    
    faultaudioCH3SilenceInput8True TRAP-TYPE
        ENTERPRISE  trapFault
        VARIABLES   { trapTag }
        DESCRIPTION
            "Audio Channel 3 Silent Alert on Input8"
    ::= 1687

-- end of audioCH3Silence Input8 trap

-- beginning of audioCH4Silence Input1 trap

    faultaudioCH4SilenceInput1False TRAP-TYPE
        ENTERPRISE  trapFault
        VARIABLES   { trapTag }
        DESCRIPTION
            "Audio Channel 4 Silent Cleared on Input1"
    ::= 1688
    
    faultaudioCH4SilenceInput1True TRAP-TYPE
        ENTERPRISE  trapFault
        VARIABLES   { trapTag }
        DESCRIPTION
            "Audio Channel 4 Silent Alert on Input1"
    ::= 1689

-- end of audioCH4Silence Input1 trap

-- beginning of audioCH4Silence Input2 trap

    faultaudioCH4SilenceInput2False TRAP-TYPE
        ENTERPRISE  trapFault
        VARIABLES   { trapTag }
        DESCRIPTION
            "Audio Channel 4 Silent Cleared on Input2"
    ::= 1690
    
    faultaudioCH4SilenceInput2True TRAP-TYPE
        ENTERPRISE  trapFault
        VARIABLES   { trapTag }
        DESCRIPTION
            "Audio Channel 4 Silent Alert on Input2"
    ::= 1691

-- end of audioCH4Silence Input2 trap

-- beginning of audioCH4Silence Input3 trap

    faultaudioCH4SilenceInput3False TRAP-TYPE
        ENTERPRISE  trapFault
        VARIABLES   { trapTag }
        DESCRIPTION
            "Audio Channel 4 Silent Cleared on Input3"
    ::= 1692
    
    faultaudioCH4SilenceInput3True TRAP-TYPE
        ENTERPRISE  trapFault
        VARIABLES   { trapTag }
        DESCRIPTION
            "Audio Channel 4 Silent Alert on Input3"
    ::= 1693

-- end of audioCH4Silence Input3 trap

-- beginning of audioCH4Silence Input4 trap

    faultaudioCH4SilenceInput4False TRAP-TYPE
        ENTERPRISE  trapFault
        VARIABLES   { trapTag }
        DESCRIPTION
            "Audio Channel 4 Silent Cleared on Input4"
    ::= 1694
    
    faultaudioCH4SilenceInput4True TRAP-TYPE
        ENTERPRISE  trapFault
        VARIABLES   { trapTag }
        DESCRIPTION
            "Audio Channel 4 Silent Alert on Input4"
    ::= 1695

-- end of audioCH4Silence Input4 trap

-- beginning of audioCH4Silence Input5 trap

    faultaudioCH4SilenceInput5False TRAP-TYPE
        ENTERPRISE  trapFault
        VARIABLES   { trapTag }
        DESCRIPTION
            "Audio Channel 4 Silent Cleared on Input5"
    ::= 1696
    
    faultaudioCH4SilenceInput5True TRAP-TYPE
        ENTERPRISE  trapFault
        VARIABLES   { trapTag }
        DESCRIPTION
            "Audio Channel 4 Silent Alert on Input5"
    ::= 1697

-- end of audioCH4Silence Input5 trap

-- beginning of audioCH4Silence Input6 trap

    faultaudioCH4SilenceInput6False TRAP-TYPE
        ENTERPRISE  trapFault
        VARIABLES   { trapTag }
        DESCRIPTION
            "Audio Channel 4 Silent Cleared on Input6"
    ::= 1698
    
    faultaudioCH4SilenceInput6True TRAP-TYPE
        ENTERPRISE  trapFault
        VARIABLES   { trapTag }
        DESCRIPTION
            "Audio Channel 4 Silent Alert on Input6"
    ::= 1699

-- end of audioCH4Silence Input6 trap

-- beginning of audioCH4Silence Input7 trap

    faultaudioCH4SilenceInput7False TRAP-TYPE
        ENTERPRISE  trapFault
        VARIABLES   { trapTag }
        DESCRIPTION
            "Audio Channel 4 Silent Cleared on Input7"
    ::= 1700
    
    faultaudioCH4SilenceInput7True TRAP-TYPE
        ENTERPRISE  trapFault
        VARIABLES   { trapTag }
        DESCRIPTION
            "Audio Channel 4 Silent Alert on Input7"
    ::= 1701

-- end of audioCH4Silence Input7 trap

-- beginning of audioCH4Silence Input8 trap

    faultaudioCH4SilenceInput8False TRAP-TYPE
        ENTERPRISE  trapFault
        VARIABLES   { trapTag }
        DESCRIPTION
            "Audio Channel 4 Silent Cleared on Input8"
    ::= 1702
    
    faultaudioCH4SilenceInput8True TRAP-TYPE
        ENTERPRISE  trapFault
        VARIABLES   { trapTag }
        DESCRIPTION
            "Audio Channel 4 Silent Alert on Input8"
    ::= 1703

-- end of audioCH4Silence Input8 trap

-- beginning of audioCH5Silence Input1 trap

    faultaudioCH5SilenceInput1False TRAP-TYPE
        ENTERPRISE  trapFault
        VARIABLES   { trapTag }
        DESCRIPTION
            "Audio Channel 5 Silent Cleared on Input1"
    ::= 1704
    
    faultaudioCH5SilenceInput1True TRAP-TYPE
        ENTERPRISE  trapFault
        VARIABLES   { trapTag }
        DESCRIPTION
            "Audio Channel 5 Silent Alert on Input1"
    ::= 1705

-- end of audioCH5Silence Input1 trap

-- beginning of audioCH5Silence Input2 trap

    faultaudioCH5SilenceInput2False TRAP-TYPE
        ENTERPRISE  trapFault
        VARIABLES   { trapTag }
        DESCRIPTION
            "Audio Channel 5 Silent Cleared on Input2"
    ::= 1706
    
    faultaudioCH5SilenceInput2True TRAP-TYPE
        ENTERPRISE  trapFault
        VARIABLES   { trapTag }
        DESCRIPTION
            "Audio Channel 5 Silent Alert on Input2"
    ::= 1707

-- end of audioCH5Silence Input2 trap

-- beginning of audioCH5Silence Input3 trap

    faultaudioCH5SilenceInput3False TRAP-TYPE
        ENTERPRISE  trapFault
        VARIABLES   { trapTag }
        DESCRIPTION
            "Audio Channel 5 Silent Cleared on Input3"
    ::= 1708
    
    faultaudioCH5SilenceInput3True TRAP-TYPE
        ENTERPRISE  trapFault
        VARIABLES   { trapTag }
        DESCRIPTION
            "Audio Channel 5 Silent Alert on Input3"
    ::= 1709

-- end of audioCH5Silence Input3 trap

-- beginning of audioCH5Silence Input4 trap

    faultaudioCH5SilenceInput4False TRAP-TYPE
        ENTERPRISE  trapFault
        VARIABLES   { trapTag }
        DESCRIPTION
            "Audio Channel 5 Silent Cleared on Input4"
    ::= 1710
    
    faultaudioCH5SilenceInput4True TRAP-TYPE
        ENTERPRISE  trapFault
        VARIABLES   { trapTag }
        DESCRIPTION
            "Audio Channel 5 Silent Alert on Input4"
    ::= 1711

-- end of audioCH5Silence Input4 trap

-- beginning of audioCH5Silence Input5 trap

    faultaudioCH5SilenceInput5False TRAP-TYPE
        ENTERPRISE  trapFault
        VARIABLES   { trapTag }
        DESCRIPTION
            "Audio Channel 5 Silent Cleared on Input5"
    ::= 1712
    
    faultaudioCH5SilenceInput5True TRAP-TYPE
        ENTERPRISE  trapFault
        VARIABLES   { trapTag }
        DESCRIPTION
            "Audio Channel 5 Silent Alert on Input5"
    ::= 1713

-- end of audioCH5Silence Input5 trap

-- beginning of audioCH5Silence Input6 trap

    faultaudioCH5SilenceInput6False TRAP-TYPE
        ENTERPRISE  trapFault
        VARIABLES   { trapTag }
        DESCRIPTION
            "Audio Channel 5 Silent Cleared on Input6"
    ::= 1714
    
    faultaudioCH5SilenceInput6True TRAP-TYPE
        ENTERPRISE  trapFault
        VARIABLES   { trapTag }
        DESCRIPTION
            "Audio Channel 5 Silent Alert on Input6"
    ::= 1715

-- end of audioCH5Silence Input6 trap

-- beginning of audioCH5Silence Input7 trap

    faultaudioCH5SilenceInput7False TRAP-TYPE
        ENTERPRISE  trapFault
        VARIABLES   { trapTag }
        DESCRIPTION
            "Audio Channel 5 Silent Cleared on Input7"
    ::= 1716
    
    faultaudioCH5SilenceInput7True TRAP-TYPE
        ENTERPRISE  trapFault
        VARIABLES   { trapTag }
        DESCRIPTION
            "Audio Channel 5 Silent Alert on Input7"
    ::= 1717

-- end of audioCH5Silence Input7 trap

-- beginning of audioCH5Silence Input8 trap

    faultaudioCH5SilenceInput8False TRAP-TYPE
        ENTERPRISE  trapFault
        VARIABLES   { trapTag }
        DESCRIPTION
            "Audio Channel 5 Silent Cleared on Input8"
    ::= 1718
    
    faultaudioCH5SilenceInput8True TRAP-TYPE
        ENTERPRISE  trapFault
        VARIABLES   { trapTag }
        DESCRIPTION
            "Audio Channel 5 Silent Alert on Input8"
    ::= 1719

-- end of audioCH5Silence Input8 trap

-- beginning of audioCH6Silence Input1 trap

    faultaudioCH6SilenceInput1False TRAP-TYPE
        ENTERPRISE  trapFault
        VARIABLES   { trapTag }
        DESCRIPTION
            "Audio Channel 6 Silent Cleared on Input1"
    ::= 1720
    
    faultaudioCH6SilenceInput1True TRAP-TYPE
        ENTERPRISE  trapFault
        VARIABLES   { trapTag }
        DESCRIPTION
            "Audio Channel 6 Silent Alert on Input1"
    ::= 1721

-- end of audioCH6Silence Input1 trap

-- beginning of audioCH6Silence Input2 trap

    faultaudioCH6SilenceInput2False TRAP-TYPE
        ENTERPRISE  trapFault
        VARIABLES   { trapTag }
        DESCRIPTION
            "Audio Channel 6 Silent Cleared on Input2"
    ::= 1722
    
    faultaudioCH6SilenceInput2True TRAP-TYPE
        ENTERPRISE  trapFault
        VARIABLES   { trapTag }
        DESCRIPTION
            "Audio Channel 6 Silent Alert on Input2"
    ::= 1723

-- end of audioCH6Silence Input2 trap

-- beginning of audioCH6Silence Input3 trap

    faultaudioCH6SilenceInput3False TRAP-TYPE
        ENTERPRISE  trapFault
        VARIABLES   { trapTag }
        DESCRIPTION
            "Audio Channel 6 Silent Cleared on Input3"
    ::= 1724
    
    faultaudioCH6SilenceInput3True TRAP-TYPE
        ENTERPRISE  trapFault
        VARIABLES   { trapTag }
        DESCRIPTION
            "Audio Channel 6 Silent Alert on Input3"
    ::= 1725

-- end of audioCH6Silence Input3 trap

-- beginning of audioCH6Silence Input4 trap

    faultaudioCH6SilenceInput4False TRAP-TYPE
        ENTERPRISE  trapFault
        VARIABLES   { trapTag }
        DESCRIPTION
            "Audio Channel 6 Silent Cleared on Input4"
    ::= 1726
    
    faultaudioCH6SilenceInput4True TRAP-TYPE
        ENTERPRISE  trapFault
        VARIABLES   { trapTag }
        DESCRIPTION
            "Audio Channel 6 Silent Alert on Input4"
    ::= 1727

-- end of audioCH6Silence Input4 trap

-- beginning of audioCH6Silence Input5 trap

    faultaudioCH6SilenceInput5False TRAP-TYPE
        ENTERPRISE  trapFault
        VARIABLES   { trapTag }
        DESCRIPTION
            "Audio Channel 6 Silent Cleared on Input5"
    ::= 1728
    
    faultaudioCH6SilenceInput5True TRAP-TYPE
        ENTERPRISE  trapFault
        VARIABLES   { trapTag }
        DESCRIPTION
            "Audio Channel 6 Silent Alert on Input5"
    ::= 1729

-- end of audioCH6Silence Input5 trap

-- beginning of audioCH6Silence Input6 trap

    faultaudioCH6SilenceInput6False TRAP-TYPE
        ENTERPRISE  trapFault
        VARIABLES   { trapTag }
        DESCRIPTION
            "Audio Channel 6 Silent Cleared on Input6"
    ::= 1730
    
    faultaudioCH6SilenceInput6True TRAP-TYPE
        ENTERPRISE  trapFault
        VARIABLES   { trapTag }
        DESCRIPTION
            "Audio Channel 6 Silent Alert on Input6"
    ::= 1731

-- end of audioCH6Silence Input6 trap

-- beginning of audioCH6Silence Input7 trap

    faultaudioCH6SilenceInput7False TRAP-TYPE
        ENTERPRISE  trapFault
        VARIABLES   { trapTag }
        DESCRIPTION
            "Audio Channel 6 Silent Cleared on Input7"
    ::= 1732
    
    faultaudioCH6SilenceInput7True TRAP-TYPE
        ENTERPRISE  trapFault
        VARIABLES   { trapTag }
        DESCRIPTION
            "Audio Channel 6 Silent Alert on Input7"
    ::= 1733

-- end of audioCH6Silence Input7 trap

-- beginning of audioCH6Silence Input8 trap

    faultaudioCH6SilenceInput8False TRAP-TYPE
        ENTERPRISE  trapFault
        VARIABLES   { trapTag }
        DESCRIPTION
            "Audio Channel 6 Silent Cleared on Input8"
    ::= 1734
    
    faultaudioCH6SilenceInput8True TRAP-TYPE
        ENTERPRISE  trapFault
        VARIABLES   { trapTag }
        DESCRIPTION
            "Audio Channel 6 Silent Alert on Input8"
    ::= 1735

-- end of audioCH6Silence Input8 trap

-- beginning of audioCH7Silence Input1 trap

    faultaudioCH7SilenceInput1False TRAP-TYPE
        ENTERPRISE  trapFault
        VARIABLES   { trapTag }
        DESCRIPTION
            "Audio Channel 7 Silent Cleared on Input1"
    ::= 1736
    
    faultaudioCH7SilenceInput1True TRAP-TYPE
        ENTERPRISE  trapFault
        VARIABLES   { trapTag }
        DESCRIPTION
            "Audio Channel 7 Silent Alert on Input1"
    ::= 1737

-- end of audioCH7Silence Input1 trap

-- beginning of audioCH7Silence Input2 trap

    faultaudioCH7SilenceInput2False TRAP-TYPE
        ENTERPRISE  trapFault
        VARIABLES   { trapTag }
        DESCRIPTION
            "Audio Channel 7 Silent Cleared on Input2"
    ::= 1738
    
    faultaudioCH7SilenceInput2True TRAP-TYPE
        ENTERPRISE  trapFault
        VARIABLES   { trapTag }
        DESCRIPTION
            "Audio Channel 7 Silent Alert on Input2"
    ::= 1739

-- end of audioCH7Silence Input2 trap

-- beginning of audioCH7Silence Input3 trap

    faultaudioCH7SilenceInput3False TRAP-TYPE
        ENTERPRISE  trapFault
        VARIABLES   { trapTag }
        DESCRIPTION
            "Audio Channel 7 Silent Cleared on Input3"
    ::= 1740
    
    faultaudioCH7SilenceInput3True TRAP-TYPE
        ENTERPRISE  trapFault
        VARIABLES   { trapTag }
        DESCRIPTION
            "Audio Channel 7 Silent Alert on Input3"
    ::= 1741

-- end of audioCH7Silence Input3 trap

-- beginning of audioCH7Silence Input4 trap

    faultaudioCH7SilenceInput4False TRAP-TYPE
        ENTERPRISE  trapFault
        VARIABLES   { trapTag }
        DESCRIPTION
            "Audio Channel 7 Silent Cleared on Input4"
    ::= 1742
    
    faultaudioCH7SilenceInput4True TRAP-TYPE
        ENTERPRISE  trapFault
        VARIABLES   { trapTag }
        DESCRIPTION
            "Audio Channel 7 Silent Alert on Input4"
    ::= 1743

-- end of audioCH7Silence Input4 trap

-- beginning of audioCH7Silence Input5 trap

    faultaudioCH7SilenceInput5False TRAP-TYPE
        ENTERPRISE  trapFault
        VARIABLES   { trapTag }
        DESCRIPTION
            "Audio Channel 7 Silent Cleared on Input5"
    ::= 1744
    
    faultaudioCH7SilenceInput5True TRAP-TYPE
        ENTERPRISE  trapFault
        VARIABLES   { trapTag }
        DESCRIPTION
            "Audio Channel 7 Silent Alert on Input5"
    ::= 1745

-- end of audioCH7Silence Input5 trap

-- beginning of audioCH7Silence Input6 trap

    faultaudioCH7SilenceInput6False TRAP-TYPE
        ENTERPRISE  trapFault
        VARIABLES   { trapTag }
        DESCRIPTION
            "Audio Channel 7 Silent Cleared on Input6"
    ::= 1746
    
    faultaudioCH7SilenceInput6True TRAP-TYPE
        ENTERPRISE  trapFault
        VARIABLES   { trapTag }
        DESCRIPTION
            "Audio Channel 7 Silent Alert on Input6"
    ::= 1747

-- end of audioCH7Silence Input6 trap

-- beginning of audioCH7Silence Input7 trap

    faultaudioCH7SilenceInput7False TRAP-TYPE
        ENTERPRISE  trapFault
        VARIABLES   { trapTag }
        DESCRIPTION
            "Audio Channel 7 Silent Cleared on Input7"
    ::= 1748
    
    faultaudioCH7SilenceInput7True TRAP-TYPE
        ENTERPRISE  trapFault
        VARIABLES   { trapTag }
        DESCRIPTION
            "Audio Channel 7 Silent Alert on Input7"
    ::= 1749

-- end of audioCH7Silence Input7 trap

-- beginning of audioCH7Silence Input8 trap

    faultaudioCH7SilenceInput8False TRAP-TYPE
        ENTERPRISE  trapFault
        VARIABLES   { trapTag }
        DESCRIPTION
            "Audio Channel 7 Silent Cleared on Input8"
    ::= 1750
    
    faultaudioCH7SilenceInput8True TRAP-TYPE
        ENTERPRISE  trapFault
        VARIABLES   { trapTag }
        DESCRIPTION
            "Audio Channel 7 Silent Alert on Input8"
    ::= 1751

-- end of audioCH7Silence Input8 trap

-- beginning of audioCH8Silence Input1 trap

    faultaudioCH8SilenceInput1False TRAP-TYPE
        ENTERPRISE  trapFault
        VARIABLES   { trapTag }
        DESCRIPTION
            "Audio Channel 8 Silent Cleared on Input1"
    ::= 1752
    
    faultaudioCH8SilenceInput1True TRAP-TYPE
        ENTERPRISE  trapFault
        VARIABLES   { trapTag }
        DESCRIPTION
            "Audio Channel 8 Silent Alert on Input1"
    ::= 1753

-- end of audioCH8Silence Input1 trap

-- beginning of audioCH8Silence Input2 trap

    faultaudioCH8SilenceInput2False TRAP-TYPE
        ENTERPRISE  trapFault
        VARIABLES   { trapTag }
        DESCRIPTION
            "Audio Channel 8 Silent Cleared on Input2"
    ::= 1754
    
    faultaudioCH8SilenceInput2True TRAP-TYPE
        ENTERPRISE  trapFault
        VARIABLES   { trapTag }
        DESCRIPTION
            "Audio Channel 8 Silent Alert on Input2"
    ::= 1755

-- end of audioCH8Silence Input2 trap

-- beginning of audioCH8Silence Input3 trap

    faultaudioCH8SilenceInput3False TRAP-TYPE
        ENTERPRISE  trapFault
        VARIABLES   { trapTag }
        DESCRIPTION
            "Audio Channel 8 Silent Cleared on Input3"
    ::= 1756
    
    faultaudioCH8SilenceInput3True TRAP-TYPE
        ENTERPRISE  trapFault
        VARIABLES   { trapTag }
        DESCRIPTION
            "Audio Channel 8 Silent Alert on Input3"
    ::= 1757

-- end of audioCH8Silence Input3 trap

-- beginning of audioCH8Silence Input4 trap

    faultaudioCH8SilenceInput4False TRAP-TYPE
        ENTERPRISE  trapFault
        VARIABLES   { trapTag }
        DESCRIPTION
            "Audio Channel 8 Silent Cleared on Input4"
    ::= 1758
    
    faultaudioCH8SilenceInput4True TRAP-TYPE
        ENTERPRISE  trapFault
        VARIABLES   { trapTag }
        DESCRIPTION
            "Audio Channel 8 Silent Alert on Input4"
    ::= 1759

-- end of audioCH8Silence Input4 trap

-- beginning of audioCH8Silence Input5 trap

    faultaudioCH8SilenceInput5False TRAP-TYPE
        ENTERPRISE  trapFault
        VARIABLES   { trapTag }
        DESCRIPTION
            "Audio Channel 8 Silent Cleared on Input5"
    ::= 1760
    
    faultaudioCH8SilenceInput5True TRAP-TYPE
        ENTERPRISE  trapFault
        VARIABLES   { trapTag }
        DESCRIPTION
            "Audio Channel 8 Silent Alert on Input5"
    ::= 1761

-- end of audioCH8Silence Input5 trap

-- beginning of audioCH8Silence Input6 trap

    faultaudioCH8SilenceInput6False TRAP-TYPE
        ENTERPRISE  trapFault
        VARIABLES   { trapTag }
        DESCRIPTION
            "Audio Channel 8 Silent Cleared on Input6"
    ::= 1762
    
    faultaudioCH8SilenceInput6True TRAP-TYPE
        ENTERPRISE  trapFault
        VARIABLES   { trapTag }
        DESCRIPTION
            "Audio Channel 8 Silent Alert on Input6"
    ::= 1763

-- end of audioCH8Silence Input6 trap

-- beginning of audioCH8Silence Input7 trap

    faultaudioCH8SilenceInput7False TRAP-TYPE
        ENTERPRISE  trapFault
        VARIABLES   { trapTag }
        DESCRIPTION
            "Audio Channel 8 Silent Cleared on Input7"
    ::= 1764
    
    faultaudioCH8SilenceInput7True TRAP-TYPE
        ENTERPRISE  trapFault
        VARIABLES   { trapTag }
        DESCRIPTION
            "Audio Channel 8 Silent Alert on Input7"
    ::= 1765

-- end of audioCH8Silence Input7 trap

-- beginning of audioCH8Silence Input8 trap

    faultaudioCH8SilenceInput8False TRAP-TYPE
        ENTERPRISE  trapFault
        VARIABLES   { trapTag }
        DESCRIPTION
            "Audio Channel 8 Silent Cleared on Input8"
    ::= 1766
    
    faultaudioCH8SilenceInput8True TRAP-TYPE
        ENTERPRISE  trapFault
        VARIABLES   { trapTag }
        DESCRIPTION
            "Audio Channel 8 Silent Alert on Input8"
    ::= 1767

-- end of audioCH8Silence Input8 trap

-- beginning of audioCH1Over Input1 trap

    faultaudioCH1OverInput1False TRAP-TYPE
        ENTERPRISE  trapFault
        VARIABLES   { trapTag }
        DESCRIPTION
            "Audio Channel 1 Over Cleared on Input1"
    ::= 1768
    
    faultaudioCH1OverInput1True TRAP-TYPE
        ENTERPRISE  trapFault
        VARIABLES   { trapTag }
        DESCRIPTION
            "Audio Channel 1 Over Alert on Input1"
    ::= 1769

-- end of audioCH1Over Input1 trap

-- beginning of audioCH1Over Input2 trap

    faultaudioCH1OverInput2False TRAP-TYPE
        ENTERPRISE  trapFault
        VARIABLES   { trapTag }
        DESCRIPTION
            "Audio Channel 1 Over Cleared on Input2"
    ::= 1770
    
    faultaudioCH1OverInput2True TRAP-TYPE
        ENTERPRISE  trapFault
        VARIABLES   { trapTag }
        DESCRIPTION
            "Audio Channel 1 Over Alert on Input2"
    ::= 1771

-- end of audioCH1Over Input2 trap

-- beginning of audioCH1Over Input3 trap

    faultaudioCH1OverInput3False TRAP-TYPE
        ENTERPRISE  trapFault
        VARIABLES   { trapTag }
        DESCRIPTION
            "Audio Channel 1 Over Cleared on Input3"
    ::= 1772
    
    faultaudioCH1OverInput3True TRAP-TYPE
        ENTERPRISE  trapFault
        VARIABLES   { trapTag }
        DESCRIPTION
            "Audio Channel 1 Over Alert on Input3"
    ::= 1773

-- end of audioCH1Over Input3 trap

-- beginning of audioCH1Over Input4 trap

    faultaudioCH1OverInput4False TRAP-TYPE
        ENTERPRISE  trapFault
        VARIABLES   { trapTag }
        DESCRIPTION
            "Audio Channel 1 Over Cleared on Input4"
    ::= 1774
    
    faultaudioCH1OverInput4True TRAP-TYPE
        ENTERPRISE  trapFault
        VARIABLES   { trapTag }
        DESCRIPTION
            "Audio Channel 1 Over Alert on Input4"
    ::= 1775

-- end of audioCH1Over Input4 trap

-- beginning of audioCH1Over Input5 trap

    faultaudioCH1OverInput5False TRAP-TYPE
        ENTERPRISE  trapFault
        VARIABLES   { trapTag }
        DESCRIPTION
            "Audio Channel 1 Over Cleared on Input5"
    ::= 1776
    
    faultaudioCH1OverInput5True TRAP-TYPE
        ENTERPRISE  trapFault
        VARIABLES   { trapTag }
        DESCRIPTION
            "Audio Channel 1 Over Alert on Input5"
    ::= 1777

-- end of audioCH1Over Input5 trap

-- beginning of audioCH1Over Input6 trap

    faultaudioCH1OverInput6False TRAP-TYPE
        ENTERPRISE  trapFault
        VARIABLES   { trapTag }
        DESCRIPTION
            "Audio Channel 1 Over Cleared on Input6"
    ::= 1778
    
    faultaudioCH1OverInput6True TRAP-TYPE
        ENTERPRISE  trapFault
        VARIABLES   { trapTag }
        DESCRIPTION
            "Audio Channel 1 Over Alert on Input6"
    ::= 1779

-- end of audioCH1Over Input6 trap

-- beginning of audioCH1Over Input7 trap

    faultaudioCH1OverInput7False TRAP-TYPE
        ENTERPRISE  trapFault
        VARIABLES   { trapTag }
        DESCRIPTION
            "Audio Channel 1 Over Cleared on Input7"
    ::= 1780
    
    faultaudioCH1OverInput7True TRAP-TYPE
        ENTERPRISE  trapFault
        VARIABLES   { trapTag }
        DESCRIPTION
            "Audio Channel 1 Over Alert on Input7"
    ::= 1781

-- end of audioCH1Over Input7 trap

-- beginning of audioCH1Over Input8 trap

    faultaudioCH1OverInput8False TRAP-TYPE
        ENTERPRISE  trapFault
        VARIABLES   { trapTag }
        DESCRIPTION
            "Audio Channel 1 Over Cleared on Input8"
    ::= 1782
    
    faultaudioCH1OverInput8True TRAP-TYPE
        ENTERPRISE  trapFault
        VARIABLES   { trapTag }
        DESCRIPTION
            "Audio Channel 1 Over Alert on Input8"
    ::= 1783

-- end of audioCH1Over Input8 trap

-- beginning of audioCH2Over Input1 trap

    faultaudioCH2OverInput1False TRAP-TYPE
        ENTERPRISE  trapFault
        VARIABLES   { trapTag }
        DESCRIPTION
            "Audio Channel 2 Over Cleared on Input1"
    ::= 1784
    
    faultaudioCH2OverInput1True TRAP-TYPE
        ENTERPRISE  trapFault
        VARIABLES   { trapTag }
        DESCRIPTION
            "Audio Channel 2 Over Alert on Input1"
    ::= 1785

-- end of audioCH2Over Input1 trap

-- beginning of audioCH2Over Input2 trap

    faultaudioCH2OverInput2False TRAP-TYPE
        ENTERPRISE  trapFault
        VARIABLES   { trapTag }
        DESCRIPTION
            "Audio Channel 2 Over Cleared on Input2"
    ::= 1786
    
    faultaudioCH2OverInput2True TRAP-TYPE
        ENTERPRISE  trapFault
        VARIABLES   { trapTag }
        DESCRIPTION
            "Audio Channel 2 Over Alert on Input2"
    ::= 1787

-- end of audioCH2Over Input2 trap

-- beginning of audioCH2Over Input3 trap

    faultaudioCH2OverInput3False TRAP-TYPE
        ENTERPRISE  trapFault
        VARIABLES   { trapTag }
        DESCRIPTION
            "Audio Channel 2 Over Cleared on Input3"
    ::= 1788
    
    faultaudioCH2OverInput3True TRAP-TYPE
        ENTERPRISE  trapFault
        VARIABLES   { trapTag }
        DESCRIPTION
            "Audio Channel 2 Over Alert on Input3"
    ::= 1789

-- end of audioCH2Over Input3 trap

-- beginning of audioCH2Over Input4 trap

    faultaudioCH2OverInput4False TRAP-TYPE
        ENTERPRISE  trapFault
        VARIABLES   { trapTag }
        DESCRIPTION
            "Audio Channel 2 Over Cleared on Input4"
    ::= 1790
    
    faultaudioCH2OverInput4True TRAP-TYPE
        ENTERPRISE  trapFault
        VARIABLES   { trapTag }
        DESCRIPTION
            "Audio Channel 2 Over Alert on Input4"
    ::= 1791

-- end of audioCH2Over Input4 trap

-- beginning of audioCH2Over Input5 trap

    faultaudioCH2OverInput5False TRAP-TYPE
        ENTERPRISE  trapFault
        VARIABLES   { trapTag }
        DESCRIPTION
            "Audio Channel 2 Over Cleared on Input5"
    ::= 1792
    
    faultaudioCH2OverInput5True TRAP-TYPE
        ENTERPRISE  trapFault
        VARIABLES   { trapTag }
        DESCRIPTION
            "Audio Channel 2 Over Alert on Input5"
    ::= 1793

-- end of audioCH2Over Input5 trap

-- beginning of audioCH2Over Input6 trap

    faultaudioCH2OverInput6False TRAP-TYPE
        ENTERPRISE  trapFault
        VARIABLES   { trapTag }
        DESCRIPTION
            "Audio Channel 2 Over Cleared on Input6"
    ::= 1794
    
    faultaudioCH2OverInput6True TRAP-TYPE
        ENTERPRISE  trapFault
        VARIABLES   { trapTag }
        DESCRIPTION
            "Audio Channel 2 Over Alert on Input6"
    ::= 1795

-- end of audioCH2Over Input6 trap

-- beginning of audioCH2Over Input7 trap

    faultaudioCH2OverInput7False TRAP-TYPE
        ENTERPRISE  trapFault
        VARIABLES   { trapTag }
        DESCRIPTION
            "Audio Channel 2 Over Cleared on Input7"
    ::= 1796
    
    faultaudioCH2OverInput7True TRAP-TYPE
        ENTERPRISE  trapFault
        VARIABLES   { trapTag }
        DESCRIPTION
            "Audio Channel 2 Over Alert on Input7"
    ::= 1797

-- end of audioCH2Over Input7 trap

-- beginning of audioCH2Over Input8 trap

    faultaudioCH2OverInput8False TRAP-TYPE
        ENTERPRISE  trapFault
        VARIABLES   { trapTag }
        DESCRIPTION
            "Audio Channel 2 Over Cleared on Input8"
    ::= 1798
    
    faultaudioCH2OverInput8True TRAP-TYPE
        ENTERPRISE  trapFault
        VARIABLES   { trapTag }
        DESCRIPTION
            "Audio Channel 2 Over Alert on Input8"
    ::= 1799

-- end of audioCH2Over Input8 trap

-- beginning of audioCH3Over Input1 trap

    faultaudioCH3OverInput1False TRAP-TYPE
        ENTERPRISE  trapFault
        VARIABLES   { trapTag }
        DESCRIPTION
            "Audio Channel 3 Over Cleared on Input1"
    ::= 1800
    
    faultaudioCH3OverInput1True TRAP-TYPE
        ENTERPRISE  trapFault
        VARIABLES   { trapTag }
        DESCRIPTION
            "Audio Channel 3 Over Alert on Input1"
    ::= 1801

-- end of audioCH3Over Input1 trap

-- beginning of audioCH3Over Input2 trap

    faultaudioCH3OverInput2False TRAP-TYPE
        ENTERPRISE  trapFault
        VARIABLES   { trapTag }
        DESCRIPTION
            "Audio Channel 3 Over Cleared on Input2"
    ::= 1802
    
    faultaudioCH3OverInput2True TRAP-TYPE
        ENTERPRISE  trapFault
        VARIABLES   { trapTag }
        DESCRIPTION
            "Audio Channel 3 Over Alert on Input2"
    ::= 1803

-- end of audioCH3Over Input2 trap

-- beginning of audioCH3Over Input3 trap

    faultaudioCH3OverInput3False TRAP-TYPE
        ENTERPRISE  trapFault
        VARIABLES   { trapTag }
        DESCRIPTION
            "Audio Channel 3 Over Cleared on Input3"
    ::= 1804
    
    faultaudioCH3OverInput3True TRAP-TYPE
        ENTERPRISE  trapFault
        VARIABLES   { trapTag }
        DESCRIPTION
            "Audio Channel 3 Over Alert on Input3"
    ::= 1805

-- end of audioCH3Over Input3 trap

-- beginning of audioCH3Over Input4 trap

    faultaudioCH3OverInput4False TRAP-TYPE
        ENTERPRISE  trapFault
        VARIABLES   { trapTag }
        DESCRIPTION
            "Audio Channel 3 Over Cleared on Input4"
    ::= 1806
    
    faultaudioCH3OverInput4True TRAP-TYPE
        ENTERPRISE  trapFault
        VARIABLES   { trapTag }
        DESCRIPTION
            "Audio Channel 3 Over Alert on Input4"
    ::= 1807

-- end of audioCH3Over Input4 trap

-- beginning of audioCH3Over Input5 trap

    faultaudioCH3OverInput5False TRAP-TYPE
        ENTERPRISE  trapFault
        VARIABLES   { trapTag }
        DESCRIPTION
            "Audio Channel 3 Over Cleared on Input5"
    ::= 1808
    
    faultaudioCH3OverInput5True TRAP-TYPE
        ENTERPRISE  trapFault
        VARIABLES   { trapTag }
        DESCRIPTION
            "Audio Channel 3 Over Alert on Input5"
    ::= 1809

-- end of audioCH3Over Input5 trap

-- beginning of audioCH3Over Input6 trap

    faultaudioCH3OverInput6False TRAP-TYPE
        ENTERPRISE  trapFault
        VARIABLES   { trapTag }
        DESCRIPTION
            "Audio Channel 3 Over Cleared on Input6"
    ::= 1810
    
    faultaudioCH3OverInput6True TRAP-TYPE
        ENTERPRISE  trapFault
        VARIABLES   { trapTag }
        DESCRIPTION
            "Audio Channel 3 Over Alert on Input6"
    ::= 1811

-- end of audioCH3Over Input6 trap

-- beginning of audioCH3Over Input7 trap

    faultaudioCH3OverInput7False TRAP-TYPE
        ENTERPRISE  trapFault
        VARIABLES   { trapTag }
        DESCRIPTION
            "Audio Channel 3 Over Cleared on Input7"
    ::= 1812
    
    faultaudioCH3OverInput7True TRAP-TYPE
        ENTERPRISE  trapFault
        VARIABLES   { trapTag }
        DESCRIPTION
            "Audio Channel 3 Over Alert on Input7"
    ::= 1813

-- end of audioCH3Over Input7 trap

-- beginning of audioCH3Over Input8 trap

    faultaudioCH3OverInput8False TRAP-TYPE
        ENTERPRISE  trapFault
        VARIABLES   { trapTag }
        DESCRIPTION
            "Audio Channel 3 Over Cleared on Input8"
    ::= 1814
    
    faultaudioCH3OverInput8True TRAP-TYPE
        ENTERPRISE  trapFault
        VARIABLES   { trapTag }
        DESCRIPTION
            "Audio Channel 3 Over Alert on Input8"
    ::= 1815

-- end of audioCH3Over Input8 trap

-- beginning of audioCH4Over Input1 trap

    faultaudioCH4OverInput1False TRAP-TYPE
        ENTERPRISE  trapFault
        VARIABLES   { trapTag }
        DESCRIPTION
            "Audio Channel 4 Over Cleared on Input1"
    ::= 1816
    
    faultaudioCH4OverInput1True TRAP-TYPE
        ENTERPRISE  trapFault
        VARIABLES   { trapTag }
        DESCRIPTION
            "Audio Channel 4 Over Alert on Input1"
    ::= 1817

-- end of audioCH4Over Input1 trap

-- beginning of audioCH4Over Input2 trap

    faultaudioCH4OverInput2False TRAP-TYPE
        ENTERPRISE  trapFault
        VARIABLES   { trapTag }
        DESCRIPTION
            "Audio Channel 4 Over Cleared on Input2"
    ::= 1818
    
    faultaudioCH4OverInput2True TRAP-TYPE
        ENTERPRISE  trapFault
        VARIABLES   { trapTag }
        DESCRIPTION
            "Audio Channel 4 Over Alert on Input2"
    ::= 1819

-- end of audioCH4Over Input2 trap

-- beginning of audioCH4Over Input3 trap

    faultaudioCH4OverInput3False TRAP-TYPE
        ENTERPRISE  trapFault
        VARIABLES   { trapTag }
        DESCRIPTION
            "Audio Channel 4 Over Cleared on Input3"
    ::= 1820
    
    faultaudioCH4OverInput3True TRAP-TYPE
        ENTERPRISE  trapFault
        VARIABLES   { trapTag }
        DESCRIPTION
            "Audio Channel 4 Over Alert on Input3"
    ::= 1821

-- end of audioCH4Over Input3 trap

-- beginning of audioCH4Over Input4 trap

    faultaudioCH4OverInput4False TRAP-TYPE
        ENTERPRISE  trapFault
        VARIABLES   { trapTag }
        DESCRIPTION
            "Audio Channel 4 Over Cleared on Input4"
    ::= 1822
    
    faultaudioCH4OverInput4True TRAP-TYPE
        ENTERPRISE  trapFault
        VARIABLES   { trapTag }
        DESCRIPTION
            "Audio Channel 4 Over Alert on Input4"
    ::= 1823

-- end of audioCH4Over Input4 trap

-- beginning of audioCH4Over Input5 trap

    faultaudioCH4OverInput5False TRAP-TYPE
        ENTERPRISE  trapFault
        VARIABLES   { trapTag }
        DESCRIPTION
            "Audio Channel 4 Over Cleared on Input5"
    ::= 1824
    
    faultaudioCH4OverInput5True TRAP-TYPE
        ENTERPRISE  trapFault
        VARIABLES   { trapTag }
        DESCRIPTION
            "Audio Channel 4 Over Alert on Input5"
    ::= 1825

-- end of audioCH4Over Input5 trap

-- beginning of audioCH4Over Input6 trap

    faultaudioCH4OverInput6False TRAP-TYPE
        ENTERPRISE  trapFault
        VARIABLES   { trapTag }
        DESCRIPTION
            "Audio Channel 4 Over Cleared on Input6"
    ::= 1826
    
    faultaudioCH4OverInput6True TRAP-TYPE
        ENTERPRISE  trapFault
        VARIABLES   { trapTag }
        DESCRIPTION
            "Audio Channel 4 Over Alert on Input6"
    ::= 1827

-- end of audioCH4Over Input6 trap

-- beginning of audioCH4Over Input7 trap

    faultaudioCH4OverInput7False TRAP-TYPE
        ENTERPRISE  trapFault
        VARIABLES   { trapTag }
        DESCRIPTION
            "Audio Channel 4 Over Cleared on Input7"
    ::= 1828
    
    faultaudioCH4OverInput7True TRAP-TYPE
        ENTERPRISE  trapFault
        VARIABLES   { trapTag }
        DESCRIPTION
            "Audio Channel 4 Over Alert on Input7"
    ::= 1829

-- end of audioCH4Over Input7 trap

-- beginning of audioCH4Over Input8 trap

    faultaudioCH4OverInput8False TRAP-TYPE
        ENTERPRISE  trapFault
        VARIABLES   { trapTag }
        DESCRIPTION
            "Audio Channel 4 Over Cleared on Input8"
    ::= 1830
    
    faultaudioCH4OverInput8True TRAP-TYPE
        ENTERPRISE  trapFault
        VARIABLES   { trapTag }
        DESCRIPTION
            "Audio Channel 4 Over Alert on Input8"
    ::= 1831

-- end of audioCH4Over Input8 trap

-- beginning of audioCH5Over Input1 trap

    faultaudioCH5OverInput1False TRAP-TYPE
        ENTERPRISE  trapFault
        VARIABLES   { trapTag }
        DESCRIPTION
            "Audio Channel 5 Over Cleared on Input1"
    ::= 1832
    
    faultaudioCH5OverInput1True TRAP-TYPE
        ENTERPRISE  trapFault
        VARIABLES   { trapTag }
        DESCRIPTION
            "Audio Channel 5 Over Alert on Input1"
    ::= 1833

-- end of audioCH5Over Input1 trap

-- beginning of audioCH5Over Input2 trap

    faultaudioCH5OverInput2False TRAP-TYPE
        ENTERPRISE  trapFault
        VARIABLES   { trapTag }
        DESCRIPTION
            "Audio Channel 5 Over Cleared on Input2"
    ::= 1834
    
    faultaudioCH5OverInput2True TRAP-TYPE
        ENTERPRISE  trapFault
        VARIABLES   { trapTag }
        DESCRIPTION
            "Audio Channel 5 Over Alert on Input2"
    ::= 1835

-- end of audioCH5Over Input2 trap

-- beginning of audioCH5Over Input3 trap

    faultaudioCH5OverInput3False TRAP-TYPE
        ENTERPRISE  trapFault
        VARIABLES   { trapTag }
        DESCRIPTION
            "Audio Channel 5 Over Cleared on Input3"
    ::= 1836
    
    faultaudioCH5OverInput3True TRAP-TYPE
        ENTERPRISE  trapFault
        VARIABLES   { trapTag }
        DESCRIPTION
            "Audio Channel 5 Over Alert on Input3"
    ::= 1837

-- end of audioCH5Over Input3 trap

-- beginning of audioCH5Over Input4 trap

    faultaudioCH5OverInput4False TRAP-TYPE
        ENTERPRISE  trapFault
        VARIABLES   { trapTag }
        DESCRIPTION
            "Audio Channel 5 Over Cleared on Input4"
    ::= 1838
    
    faultaudioCH5OverInput4True TRAP-TYPE
        ENTERPRISE  trapFault
        VARIABLES   { trapTag }
        DESCRIPTION
            "Audio Channel 5 Over Alert on Input4"
    ::= 1839

-- end of audioCH5Over Input4 trap

-- beginning of audioCH5Over Input5 trap

    faultaudioCH5OverInput5False TRAP-TYPE
        ENTERPRISE  trapFault
        VARIABLES   { trapTag }
        DESCRIPTION
            "Audio Channel 5 Over Cleared on Input5"
    ::= 1840
    
    faultaudioCH5OverInput5True TRAP-TYPE
        ENTERPRISE  trapFault
        VARIABLES   { trapTag }
        DESCRIPTION
            "Audio Channel 5 Over Alert on Input5"
    ::= 1841

-- end of audioCH5Over Input5 trap

-- beginning of audioCH5Over Input6 trap

    faultaudioCH5OverInput6False TRAP-TYPE
        ENTERPRISE  trapFault
        VARIABLES   { trapTag }
        DESCRIPTION
            "Audio Channel 5 Over Cleared on Input6"
    ::= 1842
    
    faultaudioCH5OverInput6True TRAP-TYPE
        ENTERPRISE  trapFault
        VARIABLES   { trapTag }
        DESCRIPTION
            "Audio Channel 5 Over Alert on Input6"
    ::= 1843

-- end of audioCH5Over Input6 trap

-- beginning of audioCH5Over Input7 trap

    faultaudioCH5OverInput7False TRAP-TYPE
        ENTERPRISE  trapFault
        VARIABLES   { trapTag }
        DESCRIPTION
            "Audio Channel 5 Over Cleared on Input7"
    ::= 1844
    
    faultaudioCH5OverInput7True TRAP-TYPE
        ENTERPRISE  trapFault
        VARIABLES   { trapTag }
        DESCRIPTION
            "Audio Channel 5 Over Alert on Input7"
    ::= 1845

-- end of audioCH5Over Input7 trap

-- beginning of audioCH5Over Input8 trap

    faultaudioCH5OverInput8False TRAP-TYPE
        ENTERPRISE  trapFault
        VARIABLES   { trapTag }
        DESCRIPTION
            "Audio Channel 5 Over Cleared on Input8"
    ::= 1846
    
    faultaudioCH5OverInput8True TRAP-TYPE
        ENTERPRISE  trapFault
        VARIABLES   { trapTag }
        DESCRIPTION
            "Audio Channel 5 Over Alert on Input8"
    ::= 1847

-- end of audioCH5Over Input8 trap

-- beginning of audioCH6Over Input1 trap

    faultaudioCH6OverInput1False TRAP-TYPE
        ENTERPRISE  trapFault
        VARIABLES   { trapTag }
        DESCRIPTION
            "Audio Channel 6 Over Cleared on Input1"
    ::= 1848
    
    faultaudioCH6OverInput1True TRAP-TYPE
        ENTERPRISE  trapFault
        VARIABLES   { trapTag }
        DESCRIPTION
            "Audio Channel 6 Over Alert on Input1"
    ::= 1849

-- end of audioCH6Over Input1 trap

-- beginning of audioCH6Over Input2 trap

    faultaudioCH6OverInput2False TRAP-TYPE
        ENTERPRISE  trapFault
        VARIABLES   { trapTag }
        DESCRIPTION
            "Audio Channel 6 Over Cleared on Input2"
    ::= 1850
    
    faultaudioCH6OverInput2True TRAP-TYPE
        ENTERPRISE  trapFault
        VARIABLES   { trapTag }
        DESCRIPTION
            "Audio Channel 6 Over Alert on Input2"
    ::= 1851

-- end of audioCH6Over Input2 trap

-- beginning of audioCH6Over Input3 trap

    faultaudioCH6OverInput3False TRAP-TYPE
        ENTERPRISE  trapFault
        VARIABLES   { trapTag }
        DESCRIPTION
            "Audio Channel 6 Over Cleared on Input3"
    ::= 1852
    
    faultaudioCH6OverInput3True TRAP-TYPE
        ENTERPRISE  trapFault
        VARIABLES   { trapTag }
        DESCRIPTION
            "Audio Channel 6 Over Alert on Input3"
    ::= 1853

-- end of audioCH6Over Input3 trap

-- beginning of audioCH6Over Input4 trap

    faultaudioCH6OverInput4False TRAP-TYPE
        ENTERPRISE  trapFault
        VARIABLES   { trapTag }
        DESCRIPTION
            "Audio Channel 6 Over Cleared on Input4"
    ::= 1854
    
    faultaudioCH6OverInput4True TRAP-TYPE
        ENTERPRISE  trapFault
        VARIABLES   { trapTag }
        DESCRIPTION
            "Audio Channel 6 Over Alert on Input4"
    ::= 1855

-- end of audioCH6Over Input4 trap

-- beginning of audioCH6Over Input5 trap

    faultaudioCH6OverInput5False TRAP-TYPE
        ENTERPRISE  trapFault
        VARIABLES   { trapTag }
        DESCRIPTION
            "Audio Channel 6 Over Cleared on Input5"
    ::= 1856
    
    faultaudioCH6OverInput5True TRAP-TYPE
        ENTERPRISE  trapFault
        VARIABLES   { trapTag }
        DESCRIPTION
            "Audio Channel 6 Over Alert on Input5"
    ::= 1857

-- end of audioCH6Over Input5 trap

-- beginning of audioCH6Over Input6 trap

    faultaudioCH6OverInput6False TRAP-TYPE
        ENTERPRISE  trapFault
        VARIABLES   { trapTag }
        DESCRIPTION
            "Audio Channel 6 Over Cleared on Input6"
    ::= 1858
    
    faultaudioCH6OverInput6True TRAP-TYPE
        ENTERPRISE  trapFault
        VARIABLES   { trapTag }
        DESCRIPTION
            "Audio Channel 6 Over Alert on Input6"
    ::= 1859

-- end of audioCH6Over Input6 trap

-- beginning of audioCH6Over Input7 trap

    faultaudioCH6OverInput7False TRAP-TYPE
        ENTERPRISE  trapFault
        VARIABLES   { trapTag }
        DESCRIPTION
            "Audio Channel 6 Over Cleared on Input7"
    ::= 1860
    
    faultaudioCH6OverInput7True TRAP-TYPE
        ENTERPRISE  trapFault
        VARIABLES   { trapTag }
        DESCRIPTION
            "Audio Channel 6 Over Alert on Input7"
    ::= 1861

-- end of audioCH6Over Input7 trap

-- beginning of audioCH6Over Input8 trap

    faultaudioCH6OverInput8False TRAP-TYPE
        ENTERPRISE  trapFault
        VARIABLES   { trapTag }
        DESCRIPTION
            "Audio Channel 6 Over Cleared on Input8"
    ::= 1862
    
    faultaudioCH6OverInput8True TRAP-TYPE
        ENTERPRISE  trapFault
        VARIABLES   { trapTag }
        DESCRIPTION
            "Audio Channel 6 Over Alert on Input8"
    ::= 1863

-- end of audioCH6Over Input8 trap

-- beginning of audioCH7Over Input1 trap

    faultaudioCH7OverInput1False TRAP-TYPE
        ENTERPRISE  trapFault
        VARIABLES   { trapTag }
        DESCRIPTION
            "Audio Channel 7 Over Cleared on Input1"
    ::= 1864
    
    faultaudioCH7OverInput1True TRAP-TYPE
        ENTERPRISE  trapFault
        VARIABLES   { trapTag }
        DESCRIPTION
            "Audio Channel 7 Over Alert on Input1"
    ::= 1865

-- end of audioCH7Over Input1 trap

-- beginning of audioCH7Over Input2 trap

    faultaudioCH7OverInput2False TRAP-TYPE
        ENTERPRISE  trapFault
        VARIABLES   { trapTag }
        DESCRIPTION
            "Audio Channel 7 Over Cleared on Input2"
    ::= 1866
    
    faultaudioCH7OverInput2True TRAP-TYPE
        ENTERPRISE  trapFault
        VARIABLES   { trapTag }
        DESCRIPTION
            "Audio Channel 7 Over Alert on Input2"
    ::= 1867

-- end of audioCH7Over Input2 trap

-- beginning of audioCH7Over Input3 trap

    faultaudioCH7OverInput3False TRAP-TYPE
        ENTERPRISE  trapFault
        VARIABLES   { trapTag }
        DESCRIPTION
            "Audio Channel 7 Over Cleared on Input3"
    ::= 1868
    
    faultaudioCH7OverInput3True TRAP-TYPE
        ENTERPRISE  trapFault
        VARIABLES   { trapTag }
        DESCRIPTION
            "Audio Channel 7 Over Alert on Input3"
    ::= 1869

-- end of audioCH7Over Input3 trap

-- beginning of audioCH7Over Input4 trap

    faultaudioCH7OverInput4False TRAP-TYPE
        ENTERPRISE  trapFault
        VARIABLES   { trapTag }
        DESCRIPTION
            "Audio Channel 7 Over Cleared on Input4"
    ::= 1870
    
    faultaudioCH7OverInput4True TRAP-TYPE
        ENTERPRISE  trapFault
        VARIABLES   { trapTag }
        DESCRIPTION
            "Audio Channel 7 Over Alert on Input4"
    ::= 1871

-- end of audioCH7Over Input4 trap

-- beginning of audioCH7Over Input5 trap

    faultaudioCH7OverInput5False TRAP-TYPE
        ENTERPRISE  trapFault
        VARIABLES   { trapTag }
        DESCRIPTION
            "Audio Channel 7 Over Cleared on Input5"
    ::= 1872
    
    faultaudioCH7OverInput5True TRAP-TYPE
        ENTERPRISE  trapFault
        VARIABLES   { trapTag }
        DESCRIPTION
            "Audio Channel 7 Over Alert on Input5"
    ::= 1873

-- end of audioCH7Over Input5 trap

-- beginning of audioCH7Over Input6 trap

    faultaudioCH7OverInput6False TRAP-TYPE
        ENTERPRISE  trapFault
        VARIABLES   { trapTag }
        DESCRIPTION
            "Audio Channel 7 Over Cleared on Input6"
    ::= 1874
    
    faultaudioCH7OverInput6True TRAP-TYPE
        ENTERPRISE  trapFault
        VARIABLES   { trapTag }
        DESCRIPTION
            "Audio Channel 7 Over Alert on Input6"
    ::= 1875

-- end of audioCH7Over Input6 trap

-- beginning of audioCH7Over Input7 trap

    faultaudioCH7OverInput7False TRAP-TYPE
        ENTERPRISE  trapFault
        VARIABLES   { trapTag }
        DESCRIPTION
            "Audio Channel 7 Over Cleared on Input7"
    ::= 1876
    
    faultaudioCH7OverInput7True TRAP-TYPE
        ENTERPRISE  trapFault
        VARIABLES   { trapTag }
        DESCRIPTION
            "Audio Channel 7 Over Alert on Input7"
    ::= 1877

-- end of audioCH7Over Input7 trap

-- beginning of audioCH7Over Input8 trap

    faultaudioCH7OverInput8False TRAP-TYPE
        ENTERPRISE  trapFault
        VARIABLES   { trapTag }
        DESCRIPTION
            "Audio Channel 7 Over Cleared on Input8"
    ::= 1878
    
    faultaudioCH7OverInput8True TRAP-TYPE
        ENTERPRISE  trapFault
        VARIABLES   { trapTag }
        DESCRIPTION
            "Audio Channel 7 Over Alert on Input8"
    ::= 1879

-- end of audioCH7Over Input8 trap

-- beginning of audioCH8Over Input1 trap

    faultaudioCH8OverInput1False TRAP-TYPE
        ENTERPRISE  trapFault
        VARIABLES   { trapTag }
        DESCRIPTION
            "Audio Channel 8 Over Cleared on Input1"
    ::= 1880
    
    faultaudioCH8OverInput1True TRAP-TYPE
        ENTERPRISE  trapFault
        VARIABLES   { trapTag }
        DESCRIPTION
            "Audio Channel 8 Over Alert on Input1"
    ::= 1881

-- end of audioCH8Over Input1 trap

-- beginning of audioCH8Over Input2 trap

    faultaudioCH8OverInput2False TRAP-TYPE
        ENTERPRISE  trapFault
        VARIABLES   { trapTag }
        DESCRIPTION
            "Audio Channel 8 Over Cleared on Input2"
    ::= 1882
    
    faultaudioCH8OverInput2True TRAP-TYPE
        ENTERPRISE  trapFault
        VARIABLES   { trapTag }
        DESCRIPTION
            "Audio Channel 8 Over Alert on Input2"
    ::= 1883

-- end of audioCH8Over Input2 trap

-- beginning of audioCH8Over Input3 trap

    faultaudioCH8OverInput3False TRAP-TYPE
        ENTERPRISE  trapFault
        VARIABLES   { trapTag }
        DESCRIPTION
            "Audio Channel 8 Over Cleared on Input3"
    ::= 1884
    
    faultaudioCH8OverInput3True TRAP-TYPE
        ENTERPRISE  trapFault
        VARIABLES   { trapTag }
        DESCRIPTION
            "Audio Channel 8 Over Alert on Input3"
    ::= 1885

-- end of audioCH8Over Input3 trap

-- beginning of audioCH8Over Input4 trap

    faultaudioCH8OverInput4False TRAP-TYPE
        ENTERPRISE  trapFault
        VARIABLES   { trapTag }
        DESCRIPTION
            "Audio Channel 8 Over Cleared on Input4"
    ::= 1886
    
    faultaudioCH8OverInput4True TRAP-TYPE
        ENTERPRISE  trapFault
        VARIABLES   { trapTag }
        DESCRIPTION
            "Audio Channel 8 Over Alert on Input4"
    ::= 1887

-- end of audioCH8Over Input4 trap

-- beginning of audioCH8Over Input5 trap

    faultaudioCH8OverInput5False TRAP-TYPE
        ENTERPRISE  trapFault
        VARIABLES   { trapTag }
        DESCRIPTION
            "Audio Channel 8 Over Cleared on Input5"
    ::= 1888
    
    faultaudioCH8OverInput5True TRAP-TYPE
        ENTERPRISE  trapFault
        VARIABLES   { trapTag }
        DESCRIPTION
            "Audio Channel 8 Over Alert on Input5"
    ::= 1889

-- end of audioCH8Over Input5 trap

-- beginning of audioCH8Over Input6 trap

    faultaudioCH8OverInput6False TRAP-TYPE
        ENTERPRISE  trapFault
        VARIABLES   { trapTag }
        DESCRIPTION
            "Audio Channel 8 Over Cleared on Input6"
    ::= 1890
    
    faultaudioCH8OverInput6True TRAP-TYPE
        ENTERPRISE  trapFault
        VARIABLES   { trapTag }
        DESCRIPTION
            "Audio Channel 8 Over Alert on Input6"
    ::= 1891

-- end of audioCH8Over Input6 trap

-- beginning of audioCH8Over Input7 trap

    faultaudioCH8OverInput7False TRAP-TYPE
        ENTERPRISE  trapFault
        VARIABLES   { trapTag }
        DESCRIPTION
            "Audio Channel 8 Over Cleared on Input7"
    ::= 1892
    
    faultaudioCH8OverInput7True TRAP-TYPE
        ENTERPRISE  trapFault
        VARIABLES   { trapTag }
        DESCRIPTION
            "Audio Channel 8 Over Alert on Input7"
    ::= 1893

-- end of audioCH8Over Input7 trap

-- beginning of audioCH8Over Input8 trap

    faultaudioCH8OverInput8False TRAP-TYPE
        ENTERPRISE  trapFault
        VARIABLES   { trapTag }
        DESCRIPTION
            "Audio Channel 8 Over Cleared on Input8"
    ::= 1894
    
    faultaudioCH8OverInput8True TRAP-TYPE
        ENTERPRISE  trapFault
        VARIABLES   { trapTag }
        DESCRIPTION
            "Audio Channel 8 Over Alert on Input8"
    ::= 1895

-- end of audioCH8Over Input8 trap

-- beginning of phaseReversalLevel12 Input1 trap

    faultphaseReversalLevel12Input1False TRAP-TYPE
        ENTERPRISE  trapFault
        VARIABLES   { trapTag }
        DESCRIPTION
            "Audio Pair 1/2 Phase Reversed Cleared on Input1"
    ::= 1896
    
    faultphaseReversalLevel12Input1True TRAP-TYPE
        ENTERPRISE  trapFault
        VARIABLES   { trapTag }
        DESCRIPTION
            "Audio Pair 1/2 Phase Reversed Alert on Input1"
    ::= 1897

-- end of phaseReversalLevel12 Input1 trap

-- beginning of phaseReversalLevel12 Input2 trap

    faultphaseReversalLevel12Input2False TRAP-TYPE
        ENTERPRISE  trapFault
        VARIABLES   { trapTag }
        DESCRIPTION
            "Audio Pair 1/2 Phase Reversed Cleared on Input2"
    ::= 1898
    
    faultphaseReversalLevel12Input2True TRAP-TYPE
        ENTERPRISE  trapFault
        VARIABLES   { trapTag }
        DESCRIPTION
            "Audio Pair 1/2 Phase Reversed Alert on Input2"
    ::= 1899

-- end of phaseReversalLevel12 Input2 trap

-- beginning of phaseReversalLevel12 Input3 trap

    faultphaseReversalLevel12Input3False TRAP-TYPE
        ENTERPRISE  trapFault
        VARIABLES   { trapTag }
        DESCRIPTION
            "Audio Pair 1/2 Phase Reversed Cleared on Input3"
    ::= 1900
    
    faultphaseReversalLevel12Input3True TRAP-TYPE
        ENTERPRISE  trapFault
        VARIABLES   { trapTag }
        DESCRIPTION
            "Audio Pair 1/2 Phase Reversed Alert on Input3"
    ::= 1901

-- end of phaseReversalLevel12 Input3 trap

-- beginning of phaseReversalLevel12 Input4 trap

    faultphaseReversalLevel12Input4False TRAP-TYPE
        ENTERPRISE  trapFault
        VARIABLES   { trapTag }
        DESCRIPTION
            "Audio Pair 1/2 Phase Reversed Cleared on Input4"
    ::= 1902
    
    faultphaseReversalLevel12Input4True TRAP-TYPE
        ENTERPRISE  trapFault
        VARIABLES   { trapTag }
        DESCRIPTION
            "Audio Pair 1/2 Phase Reversed Alert on Input4"
    ::= 1903

-- end of phaseReversalLevel12 Input4 trap

-- beginning of phaseReversalLevel12 Input5 trap

    faultphaseReversalLevel12Input5False TRAP-TYPE
        ENTERPRISE  trapFault
        VARIABLES   { trapTag }
        DESCRIPTION
            "Audio Pair 1/2 Phase Reversed Cleared on Input5"
    ::= 1904
    
    faultphaseReversalLevel12Input5True TRAP-TYPE
        ENTERPRISE  trapFault
        VARIABLES   { trapTag }
        DESCRIPTION
            "Audio Pair 1/2 Phase Reversed Alert on Input5"
    ::= 1905

-- end of phaseReversalLevel12 Input5 trap

-- beginning of phaseReversalLevel12 Input6 trap

    faultphaseReversalLevel12Input6False TRAP-TYPE
        ENTERPRISE  trapFault
        VARIABLES   { trapTag }
        DESCRIPTION
            "Audio Pair 1/2 Phase Reversed Cleared on Input6"
    ::= 1906
    
    faultphaseReversalLevel12Input6True TRAP-TYPE
        ENTERPRISE  trapFault
        VARIABLES   { trapTag }
        DESCRIPTION
            "Audio Pair 1/2 Phase Reversed Alert on Input6"
    ::= 1907

-- end of phaseReversalLevel12 Input6 trap

-- beginning of phaseReversalLevel12 Input7 trap

    faultphaseReversalLevel12Input7False TRAP-TYPE
        ENTERPRISE  trapFault
        VARIABLES   { trapTag }
        DESCRIPTION
            "Audio Pair 1/2 Phase Reversed Cleared on Input7"
    ::= 1908
    
    faultphaseReversalLevel12Input7True TRAP-TYPE
        ENTERPRISE  trapFault
        VARIABLES   { trapTag }
        DESCRIPTION
            "Audio Pair 1/2 Phase Reversed Alert on Input7"
    ::= 1909

-- end of phaseReversalLevel12 Input7 trap

-- beginning of phaseReversalLevel12 Input8 trap

    faultphaseReversalLevel12Input8False TRAP-TYPE
        ENTERPRISE  trapFault
        VARIABLES   { trapTag }
        DESCRIPTION
            "Audio Pair 1/2 Phase Reversed Cleared on Input8"
    ::= 1910
    
    faultphaseReversalLevel12Input8True TRAP-TYPE
        ENTERPRISE  trapFault
        VARIABLES   { trapTag }
        DESCRIPTION
            "Audio Pair 1/2 Phase Reversed Alert on Input8"
    ::= 1911

-- end of phaseReversalLevel12 Input8 trap

-- beginning of phaseReversalLevel34 Input1 trap

    faultphaseReversalLevel34Input1False TRAP-TYPE
        ENTERPRISE  trapFault
        VARIABLES   { trapTag }
        DESCRIPTION
            "Audio Pair 3/4 Phase Reversed Cleared on Input1"
    ::= 1912
    
    faultphaseReversalLevel34Input1True TRAP-TYPE
        ENTERPRISE  trapFault
        VARIABLES   { trapTag }
        DESCRIPTION
            "Audio Pair 3/4 Phase Reversed Alert on Input1"
    ::= 1913

-- end of phaseReversalLevel34 Input1 trap

-- beginning of phaseReversalLevel34 Input2 trap

    faultphaseReversalLevel34Input2False TRAP-TYPE
        ENTERPRISE  trapFault
        VARIABLES   { trapTag }
        DESCRIPTION
            "Audio Pair 3/4 Phase Reversed Cleared on Input2"
    ::= 1914
    
    faultphaseReversalLevel34Input2True TRAP-TYPE
        ENTERPRISE  trapFault
        VARIABLES   { trapTag }
        DESCRIPTION
            "Audio Pair 3/4 Phase Reversed Alert on Input2"
    ::= 1915

-- end of phaseReversalLevel34 Input2 trap

-- beginning of phaseReversalLevel34 Input3 trap

    faultphaseReversalLevel34Input3False TRAP-TYPE
        ENTERPRISE  trapFault
        VARIABLES   { trapTag }
        DESCRIPTION
            "Audio Pair 3/4 Phase Reversed Cleared on Input3"
    ::= 1916
    
    faultphaseReversalLevel34Input3True TRAP-TYPE
        ENTERPRISE  trapFault
        VARIABLES   { trapTag }
        DESCRIPTION
            "Audio Pair 3/4 Phase Reversed Alert on Input3"
    ::= 1917

-- end of phaseReversalLevel34 Input3 trap

-- beginning of phaseReversalLevel34 Input4 trap

    faultphaseReversalLevel34Input4False TRAP-TYPE
        ENTERPRISE  trapFault
        VARIABLES   { trapTag }
        DESCRIPTION
            "Audio Pair 3/4 Phase Reversed Cleared on Input4"
    ::= 1918
    
    faultphaseReversalLevel34Input4True TRAP-TYPE
        ENTERPRISE  trapFault
        VARIABLES   { trapTag }
        DESCRIPTION
            "Audio Pair 3/4 Phase Reversed Alert on Input4"
    ::= 1919

-- end of phaseReversalLevel34 Input4 trap

-- beginning of phaseReversalLevel34 Input5 trap

    faultphaseReversalLevel34Input5False TRAP-TYPE
        ENTERPRISE  trapFault
        VARIABLES   { trapTag }
        DESCRIPTION
            "Audio Pair 3/4 Phase Reversed Cleared on Input5"
    ::= 1920
    
    faultphaseReversalLevel34Input5True TRAP-TYPE
        ENTERPRISE  trapFault
        VARIABLES   { trapTag }
        DESCRIPTION
            "Audio Pair 3/4 Phase Reversed Alert on Input5"
    ::= 1921

-- end of phaseReversalLevel34 Input5 trap

-- beginning of phaseReversalLevel34 Input6 trap

    faultphaseReversalLevel34Input6False TRAP-TYPE
        ENTERPRISE  trapFault
        VARIABLES   { trapTag }
        DESCRIPTION
            "Audio Pair 3/4 Phase Reversed Cleared on Input6"
    ::= 1922
    
    faultphaseReversalLevel34Input6True TRAP-TYPE
        ENTERPRISE  trapFault
        VARIABLES   { trapTag }
        DESCRIPTION
            "Audio Pair 3/4 Phase Reversed Alert on Input6"
    ::= 1923

-- end of phaseReversalLevel34 Input6 trap

-- beginning of phaseReversalLevel34 Input7 trap

    faultphaseReversalLevel34Input7False TRAP-TYPE
        ENTERPRISE  trapFault
        VARIABLES   { trapTag }
        DESCRIPTION
            "Audio Pair 3/4 Phase Reversed Cleared on Input7"
    ::= 1924
    
    faultphaseReversalLevel34Input7True TRAP-TYPE
        ENTERPRISE  trapFault
        VARIABLES   { trapTag }
        DESCRIPTION
            "Audio Pair 3/4 Phase Reversed Alert on Input7"
    ::= 1925

-- end of phaseReversalLevel34 Input7 trap

-- beginning of phaseReversalLevel34 Input8 trap

    faultphaseReversalLevel34Input8False TRAP-TYPE
        ENTERPRISE  trapFault
        VARIABLES   { trapTag }
        DESCRIPTION
            "Audio Pair 3/4 Phase Reversed Cleared on Input8"
    ::= 1926
    
    faultphaseReversalLevel34Input8True TRAP-TYPE
        ENTERPRISE  trapFault
        VARIABLES   { trapTag }
        DESCRIPTION
            "Audio Pair 3/4 Phase Reversed Alert on Input8"
    ::= 1927

-- end of phaseReversalLevel34 Input8 trap

-- beginning of phaseReversalLevel56 Input1 trap

    faultphaseReversalLevel56Input1False TRAP-TYPE
        ENTERPRISE  trapFault
        VARIABLES   { trapTag }
        DESCRIPTION
            "Audio Pair 5/6 Phase Reversed Cleared on Input1"
    ::= 1928
    
    faultphaseReversalLevel56Input1True TRAP-TYPE
        ENTERPRISE  trapFault
        VARIABLES   { trapTag }
        DESCRIPTION
            "Audio Pair 5/6 Phase Reversed Alert on Input1"
    ::= 1929

-- end of phaseReversalLevel56 Input1 trap

-- beginning of phaseReversalLevel56 Input2 trap

    faultphaseReversalLevel56Input2False TRAP-TYPE
        ENTERPRISE  trapFault
        VARIABLES   { trapTag }
        DESCRIPTION
            "Audio Pair 5/6 Phase Reversed Cleared on Input2"
    ::= 1930
    
    faultphaseReversalLevel56Input2True TRAP-TYPE
        ENTERPRISE  trapFault
        VARIABLES   { trapTag }
        DESCRIPTION
            "Audio Pair 5/6 Phase Reversed Alert on Input2"
    ::= 1931

-- end of phaseReversalLevel56 Input2 trap

-- beginning of phaseReversalLevel56 Input3 trap

    faultphaseReversalLevel56Input3False TRAP-TYPE
        ENTERPRISE  trapFault
        VARIABLES   { trapTag }
        DESCRIPTION
            "Audio Pair 5/6 Phase Reversed Cleared on Input3"
    ::= 1932
    
    faultphaseReversalLevel56Input3True TRAP-TYPE
        ENTERPRISE  trapFault
        VARIABLES   { trapTag }
        DESCRIPTION
            "Audio Pair 5/6 Phase Reversed Alert on Input3"
    ::= 1933

-- end of phaseReversalLevel56 Input3 trap

-- beginning of phaseReversalLevel56 Input4 trap

    faultphaseReversalLevel56Input4False TRAP-TYPE
        ENTERPRISE  trapFault
        VARIABLES   { trapTag }
        DESCRIPTION
            "Audio Pair 5/6 Phase Reversed Cleared on Input4"
    ::= 1934
    
    faultphaseReversalLevel56Input4True TRAP-TYPE
        ENTERPRISE  trapFault
        VARIABLES   { trapTag }
        DESCRIPTION
            "Audio Pair 5/6 Phase Reversed Alert on Input4"
    ::= 1935

-- end of phaseReversalLevel56 Input4 trap

-- beginning of phaseReversalLevel56 Input5 trap

    faultphaseReversalLevel56Input5False TRAP-TYPE
        ENTERPRISE  trapFault
        VARIABLES   { trapTag }
        DESCRIPTION
            "Audio Pair 5/6 Phase Reversed Cleared on Input5"
    ::= 1936
    
    faultphaseReversalLevel56Input5True TRAP-TYPE
        ENTERPRISE  trapFault
        VARIABLES   { trapTag }
        DESCRIPTION
            "Audio Pair 5/6 Phase Reversed Alert on Input5"
    ::= 1937

-- end of phaseReversalLevel56 Input5 trap

-- beginning of phaseReversalLevel56 Input6 trap

    faultphaseReversalLevel56Input6False TRAP-TYPE
        ENTERPRISE  trapFault
        VARIABLES   { trapTag }
        DESCRIPTION
            "Audio Pair 5/6 Phase Reversed Cleared on Input6"
    ::= 1938
    
    faultphaseReversalLevel56Input6True TRAP-TYPE
        ENTERPRISE  trapFault
        VARIABLES   { trapTag }
        DESCRIPTION
            "Audio Pair 5/6 Phase Reversed Alert on Input6"
    ::= 1939

-- end of phaseReversalLevel56 Input6 trap

-- beginning of phaseReversalLevel56 Input7 trap

    faultphaseReversalLevel56Input7False TRAP-TYPE
        ENTERPRISE  trapFault
        VARIABLES   { trapTag }
        DESCRIPTION
            "Audio Pair 5/6 Phase Reversed Cleared on Input7"
    ::= 1940
    
    faultphaseReversalLevel56Input7True TRAP-TYPE
        ENTERPRISE  trapFault
        VARIABLES   { trapTag }
        DESCRIPTION
            "Audio Pair 5/6 Phase Reversed Alert on Input7"
    ::= 1941

-- end of phaseReversalLevel56 Input7 trap

-- beginning of phaseReversalLevel56 Input8 trap

    faultphaseReversalLevel56Input8False TRAP-TYPE
        ENTERPRISE  trapFault
        VARIABLES   { trapTag }
        DESCRIPTION
            "Audio Pair 5/6 Phase Reversed Cleared on Input8"
    ::= 1942
    
    faultphaseReversalLevel56Input8True TRAP-TYPE
        ENTERPRISE  trapFault
        VARIABLES   { trapTag }
        DESCRIPTION
            "Audio Pair 5/6 Phase Reversed Alert on Input8"
    ::= 1943

-- end of phaseReversalLevel56 Input8 trap

-- beginning of phaseReversalLevel78 Input1 trap

    faultphaseReversalLevel78Input1False TRAP-TYPE
        ENTERPRISE  trapFault
        VARIABLES   { trapTag }
        DESCRIPTION
            "Audio Pair 7/8 Phase Reversed Cleared on Input1"
    ::= 1944
    
    faultphaseReversalLevel78Input1True TRAP-TYPE
        ENTERPRISE  trapFault
        VARIABLES   { trapTag }
        DESCRIPTION
            "Audio Pair 7/8 Phase Reversed Alert on Input1"
    ::= 1945

-- end of phaseReversalLevel78 Input1 trap

-- beginning of phaseReversalLevel78 Input2 trap

    faultphaseReversalLevel78Input2False TRAP-TYPE
        ENTERPRISE  trapFault
        VARIABLES   { trapTag }
        DESCRIPTION
            "Audio Pair 7/8 Phase Reversed Cleared on Input2"
    ::= 1946
    
    faultphaseReversalLevel78Input2True TRAP-TYPE
        ENTERPRISE  trapFault
        VARIABLES   { trapTag }
        DESCRIPTION
            "Audio Pair 7/8 Phase Reversed Alert on Input2"
    ::= 1947

-- end of phaseReversalLevel78 Input2 trap

-- beginning of phaseReversalLevel78 Input3 trap

    faultphaseReversalLevel78Input3False TRAP-TYPE
        ENTERPRISE  trapFault
        VARIABLES   { trapTag }
        DESCRIPTION
            "Audio Pair 7/8 Phase Reversed Cleared on Input3"
    ::= 1948
    
    faultphaseReversalLevel78Input3True TRAP-TYPE
        ENTERPRISE  trapFault
        VARIABLES   { trapTag }
        DESCRIPTION
            "Audio Pair 7/8 Phase Reversed Alert on Input3"
    ::= 1949

-- end of phaseReversalLevel78 Input3 trap

-- beginning of phaseReversalLevel78 Input4 trap

    faultphaseReversalLevel78Input4False TRAP-TYPE
        ENTERPRISE  trapFault
        VARIABLES   { trapTag }
        DESCRIPTION
            "Audio Pair 7/8 Phase Reversed Cleared on Input4"
    ::= 1950
    
    faultphaseReversalLevel78Input4True TRAP-TYPE
        ENTERPRISE  trapFault
        VARIABLES   { trapTag }
        DESCRIPTION
            "Audio Pair 7/8 Phase Reversed Alert on Input4"
    ::= 1951

-- end of phaseReversalLevel78 Input4 trap

-- beginning of phaseReversalLevel78 Input5 trap

    faultphaseReversalLevel78Input5False TRAP-TYPE
        ENTERPRISE  trapFault
        VARIABLES   { trapTag }
        DESCRIPTION
            "Audio Pair 7/8 Phase Reversed Cleared on Input5"
    ::= 1952
    
    faultphaseReversalLevel78Input5True TRAP-TYPE
        ENTERPRISE  trapFault
        VARIABLES   { trapTag }
        DESCRIPTION
            "Audio Pair 7/8 Phase Reversed Alert on Input5"
    ::= 1953

-- end of phaseReversalLevel78 Input5 trap

-- beginning of phaseReversalLevel78 Input6 trap

    faultphaseReversalLevel78Input6False TRAP-TYPE
        ENTERPRISE  trapFault
        VARIABLES   { trapTag }
        DESCRIPTION
            "Audio Pair 7/8 Phase Reversed Cleared on Input6"
    ::= 1954
    
    faultphaseReversalLevel78Input6True TRAP-TYPE
        ENTERPRISE  trapFault
        VARIABLES   { trapTag }
        DESCRIPTION
            "Audio Pair 7/8 Phase Reversed Alert on Input6"
    ::= 1955

-- end of phaseReversalLevel78 Input6 trap

-- beginning of phaseReversalLevel78 Input7 trap

    faultphaseReversalLevel78Input7False TRAP-TYPE
        ENTERPRISE  trapFault
        VARIABLES   { trapTag }
        DESCRIPTION
            "Audio Pair 7/8 Phase Reversed Cleared on Input7"
    ::= 1956
    
    faultphaseReversalLevel78Input7True TRAP-TYPE
        ENTERPRISE  trapFault
        VARIABLES   { trapTag }
        DESCRIPTION
            "Audio Pair 7/8 Phase Reversed Alert on Input7"
    ::= 1957

-- end of phaseReversalLevel78 Input7 trap

-- beginning of phaseReversalLevel78 Input8 trap

    faultphaseReversalLevel78Input8False TRAP-TYPE
        ENTERPRISE  trapFault
        VARIABLES   { trapTag }
        DESCRIPTION
            "Audio Pair 7/8 Phase Reversed Cleared on Input8"
    ::= 1958
    
    faultphaseReversalLevel78Input8True TRAP-TYPE
        ENTERPRISE  trapFault
        VARIABLES   { trapTag }
        DESCRIPTION
            "Audio Pair 7/8 Phase Reversed Alert on Input8"
    ::= 1959

-- end of phaseReversalLevel78 Input8 trap

-- beginning of audioMono12 Input1 trap

    faultaudioMono12Input1False TRAP-TYPE
        ENTERPRISE  trapFault
        VARIABLES   { trapTag }
        DESCRIPTION
            "Audio Pair 1/2 Mono Cleared on Input1"
    ::= 1960
    
    faultaudioMono12Input1True TRAP-TYPE
        ENTERPRISE  trapFault
        VARIABLES   { trapTag }
        DESCRIPTION
            "Audio Pair 1/2 Mono Alert on Input1"
    ::= 1961

-- end of audioMono12 Input1 trap

-- beginning of audioMono12 Input2 trap

    faultaudioMono12Input2False TRAP-TYPE
        ENTERPRISE  trapFault
        VARIABLES   { trapTag }
        DESCRIPTION
            "Audio Pair 1/2 Mono Cleared on Input2"
    ::= 1962
    
    faultaudioMono12Input2True TRAP-TYPE
        ENTERPRISE  trapFault
        VARIABLES   { trapTag }
        DESCRIPTION
            "Audio Pair 1/2 Mono Alert on Input2"
    ::= 1963

-- end of audioMono12 Input2 trap

-- beginning of audioMono12 Input3 trap

    faultaudioMono12Input3False TRAP-TYPE
        ENTERPRISE  trapFault
        VARIABLES   { trapTag }
        DESCRIPTION
            "Audio Pair 1/2 Mono Cleared on Input3"
    ::= 1964
    
    faultaudioMono12Input3True TRAP-TYPE
        ENTERPRISE  trapFault
        VARIABLES   { trapTag }
        DESCRIPTION
            "Audio Pair 1/2 Mono Alert on Input3"
    ::= 1965

-- end of audioMono12 Input3 trap

-- beginning of audioMono12 Input4 trap

    faultaudioMono12Input4False TRAP-TYPE
        ENTERPRISE  trapFault
        VARIABLES   { trapTag }
        DESCRIPTION
            "Audio Pair 1/2 Mono Cleared on Input4"
    ::= 1966
    
    faultaudioMono12Input4True TRAP-TYPE
        ENTERPRISE  trapFault
        VARIABLES   { trapTag }
        DESCRIPTION
            "Audio Pair 1/2 Mono Alert on Input4"
    ::= 1967

-- end of audioMono12 Input4 trap

-- beginning of audioMono12 Input5 trap

    faultaudioMono12Input5False TRAP-TYPE
        ENTERPRISE  trapFault
        VARIABLES   { trapTag }
        DESCRIPTION
            "Audio Pair 1/2 Mono Cleared on Input5"
    ::= 1968
    
    faultaudioMono12Input5True TRAP-TYPE
        ENTERPRISE  trapFault
        VARIABLES   { trapTag }
        DESCRIPTION
            "Audio Pair 1/2 Mono Alert on Input5"
    ::= 1969

-- end of audioMono12 Input5 trap

-- beginning of audioMono12 Input6 trap

    faultaudioMono12Input6False TRAP-TYPE
        ENTERPRISE  trapFault
        VARIABLES   { trapTag }
        DESCRIPTION
            "Audio Pair 1/2 Mono Cleared on Input6"
    ::= 1970
    
    faultaudioMono12Input6True TRAP-TYPE
        ENTERPRISE  trapFault
        VARIABLES   { trapTag }
        DESCRIPTION
            "Audio Pair 1/2 Mono Alert on Input6"
    ::= 1971

-- end of audioMono12 Input6 trap

-- beginning of audioMono12 Input7 trap

    faultaudioMono12Input7False TRAP-TYPE
        ENTERPRISE  trapFault
        VARIABLES   { trapTag }
        DESCRIPTION
            "Audio Pair 1/2 Mono Cleared on Input7"
    ::= 1972
    
    faultaudioMono12Input7True TRAP-TYPE
        ENTERPRISE  trapFault
        VARIABLES   { trapTag }
        DESCRIPTION
            "Audio Pair 1/2 Mono Alert on Input7"
    ::= 1973

-- end of audioMono12 Input7 trap

-- beginning of audioMono12 Input8 trap

    faultaudioMono12Input8False TRAP-TYPE
        ENTERPRISE  trapFault
        VARIABLES   { trapTag }
        DESCRIPTION
            "Audio Pair 1/2 Mono Cleared on Input8"
    ::= 1974
    
    faultaudioMono12Input8True TRAP-TYPE
        ENTERPRISE  trapFault
        VARIABLES   { trapTag }
        DESCRIPTION
            "Audio Pair 1/2 Mono Alert on Input8"
    ::= 1975

-- end of audioMono12 Input8 trap

-- beginning of audioMono34 Input1 trap

    faultaudioMono34Input1False TRAP-TYPE
        ENTERPRISE  trapFault
        VARIABLES   { trapTag }
        DESCRIPTION
            "Audio Pair 3/4 Mono Cleared on Input1"
    ::= 1976
    
    faultaudioMono34Input1True TRAP-TYPE
        ENTERPRISE  trapFault
        VARIABLES   { trapTag }
        DESCRIPTION
            "Audio Pair 3/4 Mono Alert on Input1"
    ::= 1977

-- end of audioMono34 Input1 trap

-- beginning of audioMono34 Input2 trap

    faultaudioMono34Input2False TRAP-TYPE
        ENTERPRISE  trapFault
        VARIABLES   { trapTag }
        DESCRIPTION
            "Audio Pair 3/4 Mono Cleared on Input2"
    ::= 1978
    
    faultaudioMono34Input2True TRAP-TYPE
        ENTERPRISE  trapFault
        VARIABLES   { trapTag }
        DESCRIPTION
            "Audio Pair 3/4 Mono Alert on Input2"
    ::= 1979

-- end of audioMono34 Input2 trap

-- beginning of audioMono34 Input3 trap

    faultaudioMono34Input3False TRAP-TYPE
        ENTERPRISE  trapFault
        VARIABLES   { trapTag }
        DESCRIPTION
            "Audio Pair 3/4 Mono Cleared on Input3"
    ::= 1980
    
    faultaudioMono34Input3True TRAP-TYPE
        ENTERPRISE  trapFault
        VARIABLES   { trapTag }
        DESCRIPTION
            "Audio Pair 3/4 Mono Alert on Input3"
    ::= 1981

-- end of audioMono34 Input3 trap

-- beginning of audioMono34 Input4 trap

    faultaudioMono34Input4False TRAP-TYPE
        ENTERPRISE  trapFault
        VARIABLES   { trapTag }
        DESCRIPTION
            "Audio Pair 3/4 Mono Cleared on Input4"
    ::= 1982
    
    faultaudioMono34Input4True TRAP-TYPE
        ENTERPRISE  trapFault
        VARIABLES   { trapTag }
        DESCRIPTION
            "Audio Pair 3/4 Mono Alert on Input4"
    ::= 1983

-- end of audioMono34 Input4 trap

-- beginning of audioMono34 Input5 trap

    faultaudioMono34Input5False TRAP-TYPE
        ENTERPRISE  trapFault
        VARIABLES   { trapTag }
        DESCRIPTION
            "Audio Pair 3/4 Mono Cleared on Input5"
    ::= 1984
    
    faultaudioMono34Input5True TRAP-TYPE
        ENTERPRISE  trapFault
        VARIABLES   { trapTag }
        DESCRIPTION
            "Audio Pair 3/4 Mono Alert on Input5"
    ::= 1985

-- end of audioMono34 Input5 trap

-- beginning of audioMono34 Input6 trap

    faultaudioMono34Input6False TRAP-TYPE
        ENTERPRISE  trapFault
        VARIABLES   { trapTag }
        DESCRIPTION
            "Audio Pair 3/4 Mono Cleared on Input6"
    ::= 1986
    
    faultaudioMono34Input6True TRAP-TYPE
        ENTERPRISE  trapFault
        VARIABLES   { trapTag }
        DESCRIPTION
            "Audio Pair 3/4 Mono Alert on Input6"
    ::= 1987

-- end of audioMono34 Input6 trap

-- beginning of audioMono34 Input7 trap

    faultaudioMono34Input7False TRAP-TYPE
        ENTERPRISE  trapFault
        VARIABLES   { trapTag }
        DESCRIPTION
            "Audio Pair 3/4 Mono Cleared on Input7"
    ::= 1988
    
    faultaudioMono34Input7True TRAP-TYPE
        ENTERPRISE  trapFault
        VARIABLES   { trapTag }
        DESCRIPTION
            "Audio Pair 3/4 Mono Alert on Input7"
    ::= 1989

-- end of audioMono34 Input7 trap

-- beginning of audioMono34 Input8 trap

    faultaudioMono34Input8False TRAP-TYPE
        ENTERPRISE  trapFault
        VARIABLES   { trapTag }
        DESCRIPTION
            "Audio Pair 3/4 Mono Cleared on Input8"
    ::= 1990
    
    faultaudioMono34Input8True TRAP-TYPE
        ENTERPRISE  trapFault
        VARIABLES   { trapTag }
        DESCRIPTION
            "Audio Pair 3/4 Mono Alert on Input8"
    ::= 1991

-- end of audioMono34 Input8 trap

-- beginning of audioMono56 Input1 trap

    faultaudioMono56Input1False TRAP-TYPE
        ENTERPRISE  trapFault
        VARIABLES   { trapTag }
        DESCRIPTION
            "Audio Pair 5/6 Mono Cleared on Input1"
    ::= 1992
    
    faultaudioMono56Input1True TRAP-TYPE
        ENTERPRISE  trapFault
        VARIABLES   { trapTag }
        DESCRIPTION
            "Audio Pair 5/6 Mono Alert on Input1"
    ::= 1993

-- end of audioMono56 Input1 trap

-- beginning of audioMono56 Input2 trap

    faultaudioMono56Input2False TRAP-TYPE
        ENTERPRISE  trapFault
        VARIABLES   { trapTag }
        DESCRIPTION
            "Audio Pair 5/6 Mono Cleared on Input2"
    ::= 1994
    
    faultaudioMono56Input2True TRAP-TYPE
        ENTERPRISE  trapFault
        VARIABLES   { trapTag }
        DESCRIPTION
            "Audio Pair 5/6 Mono Alert on Input2"
    ::= 1995

-- end of audioMono56 Input2 trap

-- beginning of audioMono56 Input3 trap

    faultaudioMono56Input3False TRAP-TYPE
        ENTERPRISE  trapFault
        VARIABLES   { trapTag }
        DESCRIPTION
            "Audio Pair 5/6 Mono Cleared on Input3"
    ::= 1996
    
    faultaudioMono56Input3True TRAP-TYPE
        ENTERPRISE  trapFault
        VARIABLES   { trapTag }
        DESCRIPTION
            "Audio Pair 5/6 Mono Alert on Input3"
    ::= 1997

-- end of audioMono56 Input3 trap

-- beginning of audioMono56 Input4 trap

    faultaudioMono56Input4False TRAP-TYPE
        ENTERPRISE  trapFault
        VARIABLES   { trapTag }
        DESCRIPTION
            "Audio Pair 5/6 Mono Cleared on Input4"
    ::= 1998
    
    faultaudioMono56Input4True TRAP-TYPE
        ENTERPRISE  trapFault
        VARIABLES   { trapTag }
        DESCRIPTION
            "Audio Pair 5/6 Mono Alert on Input4"
    ::= 1999

-- end of audioMono56 Input4 trap

-- beginning of audioMono56 Input5 trap

    faultaudioMono56Input5False TRAP-TYPE
        ENTERPRISE  trapFault
        VARIABLES   { trapTag }
        DESCRIPTION
            "Audio Pair 5/6 Mono Cleared on Input5"
    ::= 2000
    
    faultaudioMono56Input5True TRAP-TYPE
        ENTERPRISE  trapFault
        VARIABLES   { trapTag }
        DESCRIPTION
            "Audio Pair 5/6 Mono Alert on Input5"
    ::= 2001

-- end of audioMono56 Input5 trap

-- beginning of audioMono56 Input6 trap

    faultaudioMono56Input6False TRAP-TYPE
        ENTERPRISE  trapFault
        VARIABLES   { trapTag }
        DESCRIPTION
            "Audio Pair 5/6 Mono Cleared on Input6"
    ::= 2002
    
    faultaudioMono56Input6True TRAP-TYPE
        ENTERPRISE  trapFault
        VARIABLES   { trapTag }
        DESCRIPTION
            "Audio Pair 5/6 Mono Alert on Input6"
    ::= 2003

-- end of audioMono56 Input6 trap

-- beginning of audioMono56 Input7 trap

    faultaudioMono56Input7False TRAP-TYPE
        ENTERPRISE  trapFault
        VARIABLES   { trapTag }
        DESCRIPTION
            "Audio Pair 5/6 Mono Cleared on Input7"
    ::= 2004
    
    faultaudioMono56Input7True TRAP-TYPE
        ENTERPRISE  trapFault
        VARIABLES   { trapTag }
        DESCRIPTION
            "Audio Pair 5/6 Mono Alert on Input7"
    ::= 2005

-- end of audioMono56 Input7 trap

-- beginning of audioMono56 Input8 trap

    faultaudioMono56Input8False TRAP-TYPE
        ENTERPRISE  trapFault
        VARIABLES   { trapTag }
        DESCRIPTION
            "Audio Pair 5/6 Mono Cleared on Input8"
    ::= 2006
    
    faultaudioMono56Input8True TRAP-TYPE
        ENTERPRISE  trapFault
        VARIABLES   { trapTag }
        DESCRIPTION
            "Audio Pair 5/6 Mono Alert on Input8"
    ::= 2007

-- end of audioMono56 Input8 trap

-- beginning of audioMono78 Input1 trap

    faultaudioMono78Input1False TRAP-TYPE
        ENTERPRISE  trapFault
        VARIABLES   { trapTag }
        DESCRIPTION
            "Audio Pair 7/8 Mono Cleared on Input1"
    ::= 2008
    
    faultaudioMono78Input1True TRAP-TYPE
        ENTERPRISE  trapFault
        VARIABLES   { trapTag }
        DESCRIPTION
            "Audio Pair 7/8 Mono Alert on Input1"
    ::= 2009

-- end of audioMono78 Input1 trap

-- beginning of audioMono78 Input2 trap

    faultaudioMono78Input2False TRAP-TYPE
        ENTERPRISE  trapFault
        VARIABLES   { trapTag }
        DESCRIPTION
            "Audio Pair 7/8 Mono Cleared on Input2"
    ::= 2010
    
    faultaudioMono78Input2True TRAP-TYPE
        ENTERPRISE  trapFault
        VARIABLES   { trapTag }
        DESCRIPTION
            "Audio Pair 7/8 Mono Alert on Input2"
    ::= 2011

-- end of audioMono78 Input2 trap

-- beginning of audioMono78 Input3 trap

    faultaudioMono78Input3False TRAP-TYPE
        ENTERPRISE  trapFault
        VARIABLES   { trapTag }
        DESCRIPTION
            "Audio Pair 7/8 Mono Cleared on Input3"
    ::= 2012
    
    faultaudioMono78Input3True TRAP-TYPE
        ENTERPRISE  trapFault
        VARIABLES   { trapTag }
        DESCRIPTION
            "Audio Pair 7/8 Mono Alert on Input3"
    ::= 2013

-- end of audioMono78 Input3 trap

-- beginning of audioMono78 Input4 trap

    faultaudioMono78Input4False TRAP-TYPE
        ENTERPRISE  trapFault
        VARIABLES   { trapTag }
        DESCRIPTION
            "Audio Pair 7/8 Mono Cleared on Input4"
    ::= 2014
    
    faultaudioMono78Input4True TRAP-TYPE
        ENTERPRISE  trapFault
        VARIABLES   { trapTag }
        DESCRIPTION
            "Audio Pair 7/8 Mono Alert on Input4"
    ::= 2015

-- end of audioMono78 Input4 trap

-- beginning of audioMono78 Input5 trap

    faultaudioMono78Input5False TRAP-TYPE
        ENTERPRISE  trapFault
        VARIABLES   { trapTag }
        DESCRIPTION
            "Audio Pair 7/8 Mono Cleared on Input5"
    ::= 2016
    
    faultaudioMono78Input5True TRAP-TYPE
        ENTERPRISE  trapFault
        VARIABLES   { trapTag }
        DESCRIPTION
            "Audio Pair 7/8 Mono Alert on Input5"
    ::= 2017

-- end of audioMono78 Input5 trap

-- beginning of audioMono78 Input6 trap

    faultaudioMono78Input6False TRAP-TYPE
        ENTERPRISE  trapFault
        VARIABLES   { trapTag }
        DESCRIPTION
            "Audio Pair 7/8 Mono Cleared on Input6"
    ::= 2018
    
    faultaudioMono78Input6True TRAP-TYPE
        ENTERPRISE  trapFault
        VARIABLES   { trapTag }
        DESCRIPTION
            "Audio Pair 7/8 Mono Alert on Input6"
    ::= 2019

-- end of audioMono78 Input6 trap

-- beginning of audioMono78 Input7 trap

    faultaudioMono78Input7False TRAP-TYPE
        ENTERPRISE  trapFault
        VARIABLES   { trapTag }
        DESCRIPTION
            "Audio Pair 7/8 Mono Cleared on Input7"
    ::= 2020
    
    faultaudioMono78Input7True TRAP-TYPE
        ENTERPRISE  trapFault
        VARIABLES   { trapTag }
        DESCRIPTION
            "Audio Pair 7/8 Mono Alert on Input7"
    ::= 2021

-- end of audioMono78 Input7 trap

-- beginning of audioMono78 Input8 trap

    faultaudioMono78Input8False TRAP-TYPE
        ENTERPRISE  trapFault
        VARIABLES   { trapTag }
        DESCRIPTION
            "Audio Pair 7/8 Mono Cleared on Input8"
    ::= 2022
    
    faultaudioMono78Input8True TRAP-TYPE
        ENTERPRISE  trapFault
        VARIABLES   { trapTag }
        DESCRIPTION
            "Audio Pair 7/8 Mono Alert on Input8"
    ::= 2023

-- end of audioMono78 Input8 trap

-- beginning of lossOfNonPCMAudio12 Input1 trap

    faultlossOfNonPCMAudio12Input1False TRAP-TYPE
        ENTERPRISE  trapFault
        VARIABLES   { trapTag }
        DESCRIPTION
            "Audio Pair 1/2 Non-PCM Data Invalid Cleared on Input1"
    ::= 2024
    
    faultlossOfNonPCMAudio12Input1True TRAP-TYPE
        ENTERPRISE  trapFault
        VARIABLES   { trapTag }
        DESCRIPTION
            "Audio Pair 1/2 Non-PCM Data Invalid Alert on Input1"
    ::= 2025

-- end of lossOfNonPCMAudio12 Input1 trap

-- beginning of lossOfNonPCMAudio12 Input2 trap

    faultlossOfNonPCMAudio12Input2False TRAP-TYPE
        ENTERPRISE  trapFault
        VARIABLES   { trapTag }
        DESCRIPTION
            "Audio Pair 1/2 Non-PCM Data Invalid Cleared on Input2"
    ::= 2026
    
    faultlossOfNonPCMAudio12Input2True TRAP-TYPE
        ENTERPRISE  trapFault
        VARIABLES   { trapTag }
        DESCRIPTION
            "Audio Pair 1/2 Non-PCM Data Invalid Alert on Input2"
    ::= 2027

-- end of lossOfNonPCMAudio12 Input2 trap

-- beginning of lossOfNonPCMAudio12 Input3 trap

    faultlossOfNonPCMAudio12Input3False TRAP-TYPE
        ENTERPRISE  trapFault
        VARIABLES   { trapTag }
        DESCRIPTION
            "Audio Pair 1/2 Non-PCM Data Invalid Cleared on Input3"
    ::= 2028
    
    faultlossOfNonPCMAudio12Input3True TRAP-TYPE
        ENTERPRISE  trapFault
        VARIABLES   { trapTag }
        DESCRIPTION
            "Audio Pair 1/2 Non-PCM Data Invalid Alert on Input3"
    ::= 2029

-- end of lossOfNonPCMAudio12 Input3 trap

-- beginning of lossOfNonPCMAudio12 Input4 trap

    faultlossOfNonPCMAudio12Input4False TRAP-TYPE
        ENTERPRISE  trapFault
        VARIABLES   { trapTag }
        DESCRIPTION
            "Audio Pair 1/2 Non-PCM Data Invalid Cleared on Input4"
    ::= 2030
    
    faultlossOfNonPCMAudio12Input4True TRAP-TYPE
        ENTERPRISE  trapFault
        VARIABLES   { trapTag }
        DESCRIPTION
            "Audio Pair 1/2 Non-PCM Data Invalid Alert on Input4"
    ::= 2031

-- end of lossOfNonPCMAudio12 Input4 trap

-- beginning of lossOfNonPCMAudio12 Input5 trap

    faultlossOfNonPCMAudio12Input5False TRAP-TYPE
        ENTERPRISE  trapFault
        VARIABLES   { trapTag }
        DESCRIPTION
            "Audio Pair 1/2 Non-PCM Data Invalid Cleared on Input5"
    ::= 2032
    
    faultlossOfNonPCMAudio12Input5True TRAP-TYPE
        ENTERPRISE  trapFault
        VARIABLES   { trapTag }
        DESCRIPTION
            "Audio Pair 1/2 Non-PCM Data Invalid Alert on Input5"
    ::= 2033

-- end of lossOfNonPCMAudio12 Input5 trap

-- beginning of lossOfNonPCMAudio12 Input6 trap

    faultlossOfNonPCMAudio12Input6False TRAP-TYPE
        ENTERPRISE  trapFault
        VARIABLES   { trapTag }
        DESCRIPTION
            "Audio Pair 1/2 Non-PCM Data Invalid Cleared on Input6"
    ::= 2034
    
    faultlossOfNonPCMAudio12Input6True TRAP-TYPE
        ENTERPRISE  trapFault
        VARIABLES   { trapTag }
        DESCRIPTION
            "Audio Pair 1/2 Non-PCM Data Invalid Alert on Input6"
    ::= 2035

-- end of lossOfNonPCMAudio12 Input6 trap

-- beginning of lossOfNonPCMAudio12 Input7 trap

    faultlossOfNonPCMAudio12Input7False TRAP-TYPE
        ENTERPRISE  trapFault
        VARIABLES   { trapTag }
        DESCRIPTION
            "Audio Pair 1/2 Non-PCM Data Invalid Cleared on Input7"
    ::= 2036
    
    faultlossOfNonPCMAudio12Input7True TRAP-TYPE
        ENTERPRISE  trapFault
        VARIABLES   { trapTag }
        DESCRIPTION
            "Audio Pair 1/2 Non-PCM Data Invalid Alert on Input7"
    ::= 2037

-- end of lossOfNonPCMAudio12 Input7 trap

-- beginning of lossOfNonPCMAudio12 Input8 trap

    faultlossOfNonPCMAudio12Input8False TRAP-TYPE
        ENTERPRISE  trapFault
        VARIABLES   { trapTag }
        DESCRIPTION
            "Audio Pair 1/2 Non-PCM Data Invalid Cleared on Input8"
    ::= 2038
    
    faultlossOfNonPCMAudio12Input8True TRAP-TYPE
        ENTERPRISE  trapFault
        VARIABLES   { trapTag }
        DESCRIPTION
            "Audio Pair 1/2 Non-PCM Data Invalid Alert on Input8"
    ::= 2039

-- end of lossOfNonPCMAudio12 Input8 trap

-- beginning of lossOfNonPCMAudio34 Input1 trap

    faultlossOfNonPCMAudio34Input1False TRAP-TYPE
        ENTERPRISE  trapFault
        VARIABLES   { trapTag }
        DESCRIPTION
            "Audio Pair 3/4 Non-PCM Data Invalid Cleared on Input1"
    ::= 2040
    
    faultlossOfNonPCMAudio34Input1True TRAP-TYPE
        ENTERPRISE  trapFault
        VARIABLES   { trapTag }
        DESCRIPTION
            "Audio Pair 3/4 Non-PCM Data Invalid Alert on Input1"
    ::= 2041

-- end of lossOfNonPCMAudio34 Input1 trap

-- beginning of lossOfNonPCMAudio34 Input2 trap

    faultlossOfNonPCMAudio34Input2False TRAP-TYPE
        ENTERPRISE  trapFault
        VARIABLES   { trapTag }
        DESCRIPTION
            "Audio Pair 3/4 Non-PCM Data Invalid Cleared on Input2"
    ::= 2042
    
    faultlossOfNonPCMAudio34Input2True TRAP-TYPE
        ENTERPRISE  trapFault
        VARIABLES   { trapTag }
        DESCRIPTION
            "Audio Pair 3/4 Non-PCM Data Invalid Alert on Input2"
    ::= 2043

-- end of lossOfNonPCMAudio34 Input2 trap

-- beginning of lossOfNonPCMAudio34 Input3 trap

    faultlossOfNonPCMAudio34Input3False TRAP-TYPE
        ENTERPRISE  trapFault
        VARIABLES   { trapTag }
        DESCRIPTION
            "Audio Pair 3/4 Non-PCM Data Invalid Cleared on Input3"
    ::= 2044
    
    faultlossOfNonPCMAudio34Input3True TRAP-TYPE
        ENTERPRISE  trapFault
        VARIABLES   { trapTag }
        DESCRIPTION
            "Audio Pair 3/4 Non-PCM Data Invalid Alert on Input3"
    ::= 2045

-- end of lossOfNonPCMAudio34 Input3 trap

-- beginning of lossOfNonPCMAudio34 Input4 trap

    faultlossOfNonPCMAudio34Input4False TRAP-TYPE
        ENTERPRISE  trapFault
        VARIABLES   { trapTag }
        DESCRIPTION
            "Audio Pair 3/4 Non-PCM Data Invalid Cleared on Input4"
    ::= 2046
    
    faultlossOfNonPCMAudio34Input4True TRAP-TYPE
        ENTERPRISE  trapFault
        VARIABLES   { trapTag }
        DESCRIPTION
            "Audio Pair 3/4 Non-PCM Data Invalid Alert on Input4"
    ::= 2047

-- end of lossOfNonPCMAudio34 Input4 trap

-- beginning of lossOfNonPCMAudio34 Input5 trap

    faultlossOfNonPCMAudio34Input5False TRAP-TYPE
        ENTERPRISE  trapFault
        VARIABLES   { trapTag }
        DESCRIPTION
            "Audio Pair 3/4 Non-PCM Data Invalid Cleared on Input5"
    ::= 2048
    
    faultlossOfNonPCMAudio34Input5True TRAP-TYPE
        ENTERPRISE  trapFault
        VARIABLES   { trapTag }
        DESCRIPTION
            "Audio Pair 3/4 Non-PCM Data Invalid Alert on Input5"
    ::= 2049

-- end of lossOfNonPCMAudio34 Input5 trap

-- beginning of lossOfNonPCMAudio34 Input6 trap

    faultlossOfNonPCMAudio34Input6False TRAP-TYPE
        ENTERPRISE  trapFault
        VARIABLES   { trapTag }
        DESCRIPTION
            "Audio Pair 3/4 Non-PCM Data Invalid Cleared on Input6"
    ::= 2050
    
    faultlossOfNonPCMAudio34Input6True TRAP-TYPE
        ENTERPRISE  trapFault
        VARIABLES   { trapTag }
        DESCRIPTION
            "Audio Pair 3/4 Non-PCM Data Invalid Alert on Input6"
    ::= 2051

-- end of lossOfNonPCMAudio34 Input6 trap

-- beginning of lossOfNonPCMAudio34 Input7 trap

    faultlossOfNonPCMAudio34Input7False TRAP-TYPE
        ENTERPRISE  trapFault
        VARIABLES   { trapTag }
        DESCRIPTION
            "Audio Pair 3/4 Non-PCM Data Invalid Cleared on Input7"
    ::= 2052
    
    faultlossOfNonPCMAudio34Input7True TRAP-TYPE
        ENTERPRISE  trapFault
        VARIABLES   { trapTag }
        DESCRIPTION
            "Audio Pair 3/4 Non-PCM Data Invalid Alert on Input7"
    ::= 2053

-- end of lossOfNonPCMAudio34 Input7 trap

-- beginning of lossOfNonPCMAudio34 Input8 trap

    faultlossOfNonPCMAudio34Input8False TRAP-TYPE
        ENTERPRISE  trapFault
        VARIABLES   { trapTag }
        DESCRIPTION
            "Audio Pair 3/4 Non-PCM Data Invalid Cleared on Input8"
    ::= 2054
    
    faultlossOfNonPCMAudio34Input8True TRAP-TYPE
        ENTERPRISE  trapFault
        VARIABLES   { trapTag }
        DESCRIPTION
            "Audio Pair 3/4 Non-PCM Data Invalid Alert on Input8"
    ::= 2055

-- end of lossOfNonPCMAudio34 Input8 trap

-- beginning of lossOfNonPCMAudio56 Input1 trap

    faultlossOfNonPCMAudio56Input1False TRAP-TYPE
        ENTERPRISE  trapFault
        VARIABLES   { trapTag }
        DESCRIPTION
            "Audio Pair 5/6 Non-PCM Data Invalid Cleared on Input1"
    ::= 2056
    
    faultlossOfNonPCMAudio56Input1True TRAP-TYPE
        ENTERPRISE  trapFault
        VARIABLES   { trapTag }
        DESCRIPTION
            "Audio Pair 5/6 Non-PCM Data Invalid Alert on Input1"
    ::= 2057

-- end of lossOfNonPCMAudio56 Input1 trap

-- beginning of lossOfNonPCMAudio56 Input2 trap

    faultlossOfNonPCMAudio56Input2False TRAP-TYPE
        ENTERPRISE  trapFault
        VARIABLES   { trapTag }
        DESCRIPTION
            "Audio Pair 5/6 Non-PCM Data Invalid Cleared on Input2"
    ::= 2058
    
    faultlossOfNonPCMAudio56Input2True TRAP-TYPE
        ENTERPRISE  trapFault
        VARIABLES   { trapTag }
        DESCRIPTION
            "Audio Pair 5/6 Non-PCM Data Invalid Alert on Input2"
    ::= 2059

-- end of lossOfNonPCMAudio56 Input2 trap

-- beginning of lossOfNonPCMAudio56 Input3 trap

    faultlossOfNonPCMAudio56Input3False TRAP-TYPE
        ENTERPRISE  trapFault
        VARIABLES   { trapTag }
        DESCRIPTION
            "Audio Pair 5/6 Non-PCM Data Invalid Cleared on Input3"
    ::= 2060
    
    faultlossOfNonPCMAudio56Input3True TRAP-TYPE
        ENTERPRISE  trapFault
        VARIABLES   { trapTag }
        DESCRIPTION
            "Audio Pair 5/6 Non-PCM Data Invalid Alert on Input3"
    ::= 2061

-- end of lossOfNonPCMAudio56 Input3 trap

-- beginning of lossOfNonPCMAudio56 Input4 trap

    faultlossOfNonPCMAudio56Input4False TRAP-TYPE
        ENTERPRISE  trapFault
        VARIABLES   { trapTag }
        DESCRIPTION
            "Audio Pair 5/6 Non-PCM Data Invalid Cleared on Input4"
    ::= 2062
    
    faultlossOfNonPCMAudio56Input4True TRAP-TYPE
        ENTERPRISE  trapFault
        VARIABLES   { trapTag }
        DESCRIPTION
            "Audio Pair 5/6 Non-PCM Data Invalid Alert on Input4"
    ::= 2063

-- end of lossOfNonPCMAudio56 Input4 trap

-- beginning of lossOfNonPCMAudio56 Input5 trap

    faultlossOfNonPCMAudio56Input5False TRAP-TYPE
        ENTERPRISE  trapFault
        VARIABLES   { trapTag }
        DESCRIPTION
            "Audio Pair 5/6 Non-PCM Data Invalid Cleared on Input5"
    ::= 2064
    
    faultlossOfNonPCMAudio56Input5True TRAP-TYPE
        ENTERPRISE  trapFault
        VARIABLES   { trapTag }
        DESCRIPTION
            "Audio Pair 5/6 Non-PCM Data Invalid Alert on Input5"
    ::= 2065

-- end of lossOfNonPCMAudio56 Input5 trap

-- beginning of lossOfNonPCMAudio56 Input6 trap

    faultlossOfNonPCMAudio56Input6False TRAP-TYPE
        ENTERPRISE  trapFault
        VARIABLES   { trapTag }
        DESCRIPTION
            "Audio Pair 5/6 Non-PCM Data Invalid Cleared on Input6"
    ::= 2066
    
    faultlossOfNonPCMAudio56Input6True TRAP-TYPE
        ENTERPRISE  trapFault
        VARIABLES   { trapTag }
        DESCRIPTION
            "Audio Pair 5/6 Non-PCM Data Invalid Alert on Input6"
    ::= 2067

-- end of lossOfNonPCMAudio56 Input6 trap

-- beginning of lossOfNonPCMAudio56 Input7 trap

    faultlossOfNonPCMAudio56Input7False TRAP-TYPE
        ENTERPRISE  trapFault
        VARIABLES   { trapTag }
        DESCRIPTION
            "Audio Pair 5/6 Non-PCM Data Invalid Cleared on Input7"
    ::= 2068
    
    faultlossOfNonPCMAudio56Input7True TRAP-TYPE
        ENTERPRISE  trapFault
        VARIABLES   { trapTag }
        DESCRIPTION
            "Audio Pair 5/6 Non-PCM Data Invalid Alert on Input7"
    ::= 2069

-- end of lossOfNonPCMAudio56 Input7 trap

-- beginning of lossOfNonPCMAudio56 Input8 trap

    faultlossOfNonPCMAudio56Input8False TRAP-TYPE
        ENTERPRISE  trapFault
        VARIABLES   { trapTag }
        DESCRIPTION
            "Audio Pair 5/6 Non-PCM Data Invalid Cleared on Input8"
    ::= 2070
    
    faultlossOfNonPCMAudio56Input8True TRAP-TYPE
        ENTERPRISE  trapFault
        VARIABLES   { trapTag }
        DESCRIPTION
            "Audio Pair 5/6 Non-PCM Data Invalid Alert on Input8"
    ::= 2071

-- end of lossOfNonPCMAudio56 Input8 trap

-- beginning of lossOfNonPCMAudio78 Input1 trap

    faultlossOfNonPCMAudio78Input1False TRAP-TYPE
        ENTERPRISE  trapFault
        VARIABLES   { trapTag }
        DESCRIPTION
            "Audio Pair 7/8 Non-PCM Data Invalid Cleared on Input1"
    ::= 2072
    
    faultlossOfNonPCMAudio78Input1True TRAP-TYPE
        ENTERPRISE  trapFault
        VARIABLES   { trapTag }
        DESCRIPTION
            "Audio Pair 7/8 Non-PCM Data Invalid Alert on Input1"
    ::= 2073

-- end of lossOfNonPCMAudio78 Input1 trap

-- beginning of lossOfNonPCMAudio78 Input2 trap

    faultlossOfNonPCMAudio78Input2False TRAP-TYPE
        ENTERPRISE  trapFault
        VARIABLES   { trapTag }
        DESCRIPTION
            "Audio Pair 7/8 Non-PCM Data Invalid Cleared on Input2"
    ::= 2074
    
    faultlossOfNonPCMAudio78Input2True TRAP-TYPE
        ENTERPRISE  trapFault
        VARIABLES   { trapTag }
        DESCRIPTION
            "Audio Pair 7/8 Non-PCM Data Invalid Alert on Input2"
    ::= 2075

-- end of lossOfNonPCMAudio78 Input2 trap

-- beginning of lossOfNonPCMAudio78 Input3 trap

    faultlossOfNonPCMAudio78Input3False TRAP-TYPE
        ENTERPRISE  trapFault
        VARIABLES   { trapTag }
        DESCRIPTION
            "Audio Pair 7/8 Non-PCM Data Invalid Cleared on Input3"
    ::= 2076
    
    faultlossOfNonPCMAudio78Input3True TRAP-TYPE
        ENTERPRISE  trapFault
        VARIABLES   { trapTag }
        DESCRIPTION
            "Audio Pair 7/8 Non-PCM Data Invalid Alert on Input3"
    ::= 2077

-- end of lossOfNonPCMAudio78 Input3 trap

-- beginning of lossOfNonPCMAudio78 Input4 trap

    faultlossOfNonPCMAudio78Input4False TRAP-TYPE
        ENTERPRISE  trapFault
        VARIABLES   { trapTag }
        DESCRIPTION
            "Audio Pair 7/8 Non-PCM Data Invalid Cleared on Input4"
    ::= 2078
    
    faultlossOfNonPCMAudio78Input4True TRAP-TYPE
        ENTERPRISE  trapFault
        VARIABLES   { trapTag }
        DESCRIPTION
            "Audio Pair 7/8 Non-PCM Data Invalid Alert on Input4"
    ::= 2079

-- end of lossOfNonPCMAudio78 Input4 trap

-- beginning of lossOfNonPCMAudio78 Input5 trap

    faultlossOfNonPCMAudio78Input5False TRAP-TYPE
        ENTERPRISE  trapFault
        VARIABLES   { trapTag }
        DESCRIPTION
            "Audio Pair 7/8 Non-PCM Data Invalid Cleared on Input5"
    ::= 2080
    
    faultlossOfNonPCMAudio78Input5True TRAP-TYPE
        ENTERPRISE  trapFault
        VARIABLES   { trapTag }
        DESCRIPTION
            "Audio Pair 7/8 Non-PCM Data Invalid Alert on Input5"
    ::= 2081

-- end of lossOfNonPCMAudio78 Input5 trap

-- beginning of lossOfNonPCMAudio78 Input6 trap

    faultlossOfNonPCMAudio78Input6False TRAP-TYPE
        ENTERPRISE  trapFault
        VARIABLES   { trapTag }
        DESCRIPTION
            "Audio Pair 7/8 Non-PCM Data Invalid Cleared on Input6"
    ::= 2082
    
    faultlossOfNonPCMAudio78Input6True TRAP-TYPE
        ENTERPRISE  trapFault
        VARIABLES   { trapTag }
        DESCRIPTION
            "Audio Pair 7/8 Non-PCM Data Invalid Alert on Input6"
    ::= 2083

-- end of lossOfNonPCMAudio78 Input6 trap

-- beginning of lossOfNonPCMAudio78 Input7 trap

    faultlossOfNonPCMAudio78Input7False TRAP-TYPE
        ENTERPRISE  trapFault
        VARIABLES   { trapTag }
        DESCRIPTION
            "Audio Pair 7/8 Non-PCM Data Invalid Cleared on Input7"
    ::= 2084
    
    faultlossOfNonPCMAudio78Input7True TRAP-TYPE
        ENTERPRISE  trapFault
        VARIABLES   { trapTag }
        DESCRIPTION
            "Audio Pair 7/8 Non-PCM Data Invalid Alert on Input7"
    ::= 2085

-- end of lossOfNonPCMAudio78 Input7 trap

-- beginning of lossOfNonPCMAudio78 Input8 trap

    faultlossOfNonPCMAudio78Input8False TRAP-TYPE
        ENTERPRISE  trapFault
        VARIABLES   { trapTag }
        DESCRIPTION
            "Audio Pair 7/8 Non-PCM Data Invalid Cleared on Input8"
    ::= 2086
    
    faultlossOfNonPCMAudio78Input8True TRAP-TYPE
        ENTERPRISE  trapFault
        VARIABLES   { trapTag }
        DESCRIPTION
            "Audio Pair 7/8 Non-PCM Data Invalid Alert on Input8"
    ::= 2087

-- end of lossOfNonPCMAudio78 Input8 trap

-- beginning of futureUse4 Input1 trap

    faultfutureUse4Input1False TRAP-TYPE
        ENTERPRISE  trapFault
        VARIABLES   { trapTag }
        DESCRIPTION
            "FutureUse4 Cleared on Input1"
    ::= 2088
    
    faultfutureUse4Input1True TRAP-TYPE
        ENTERPRISE  trapFault
        VARIABLES   { trapTag }
        DESCRIPTION
            "FutureUse4 Alert on Input1"
    ::= 2089

-- end of futureUse4 Input1 trap

-- beginning of futureUse4 Input2 trap

    faultfutureUse4Input2False TRAP-TYPE
        ENTERPRISE  trapFault
        VARIABLES   { trapTag }
        DESCRIPTION
            "FutureUse4 Cleared on Input2"
    ::= 2090
    
    faultfutureUse4Input2True TRAP-TYPE
        ENTERPRISE  trapFault
        VARIABLES   { trapTag }
        DESCRIPTION
            "FutureUse4 Alert on Input2"
    ::= 2091

-- end of futureUse4 Input2 trap

-- beginning of futureUse4 Input3 trap

    faultfutureUse4Input3False TRAP-TYPE
        ENTERPRISE  trapFault
        VARIABLES   { trapTag }
        DESCRIPTION
            "FutureUse4 Cleared on Input3"
    ::= 2092
    
    faultfutureUse4Input3True TRAP-TYPE
        ENTERPRISE  trapFault
        VARIABLES   { trapTag }
        DESCRIPTION
            "FutureUse4 Alert on Input3"
    ::= 2093

-- end of futureUse4 Input3 trap

-- beginning of futureUse4 Input4 trap

    faultfutureUse4Input4False TRAP-TYPE
        ENTERPRISE  trapFault
        VARIABLES   { trapTag }
        DESCRIPTION
            "FutureUse4 Cleared on Input4"
    ::= 2094
    
    faultfutureUse4Input4True TRAP-TYPE
        ENTERPRISE  trapFault
        VARIABLES   { trapTag }
        DESCRIPTION
            "FutureUse4 Alert on Input4"
    ::= 2095

-- end of futureUse4 Input4 trap

-- beginning of futureUse4 Input5 trap

    faultfutureUse4Input5False TRAP-TYPE
        ENTERPRISE  trapFault
        VARIABLES   { trapTag }
        DESCRIPTION
            "FutureUse4 Cleared on Input5"
    ::= 2096
    
    faultfutureUse4Input5True TRAP-TYPE
        ENTERPRISE  trapFault
        VARIABLES   { trapTag }
        DESCRIPTION
            "FutureUse4 Alert on Input5"
    ::= 2097

-- end of futureUse4 Input5 trap

-- beginning of futureUse4 Input6 trap

    faultfutureUse4Input6False TRAP-TYPE
        ENTERPRISE  trapFault
        VARIABLES   { trapTag }
        DESCRIPTION
            "FutureUse4 Cleared on Input6"
    ::= 2098
    
    faultfutureUse4Input6True TRAP-TYPE
        ENTERPRISE  trapFault
        VARIABLES   { trapTag }
        DESCRIPTION
            "FutureUse4 Alert on Input6"
    ::= 2099

-- end of futureUse4 Input6 trap

-- beginning of futureUse4 Input7 trap

    faultfutureUse4Input7False TRAP-TYPE
        ENTERPRISE  trapFault
        VARIABLES   { trapTag }
        DESCRIPTION
            "FutureUse4 Cleared on Input7"
    ::= 2100
    
    faultfutureUse4Input7True TRAP-TYPE
        ENTERPRISE  trapFault
        VARIABLES   { trapTag }
        DESCRIPTION
            "FutureUse4 Alert on Input7"
    ::= 2101

-- end of futureUse4 Input7 trap

-- beginning of futureUse4 Input8 trap

    faultfutureUse4Input8False TRAP-TYPE
        ENTERPRISE  trapFault
        VARIABLES   { trapTag }
        DESCRIPTION
            "FutureUse4 Cleared on Input8"
    ::= 2102
    
    faultfutureUse4Input8True TRAP-TYPE
        ENTERPRISE  trapFault
        VARIABLES   { trapTag }
        DESCRIPTION
            "FutureUse4 Alert on Input8"
    ::= 2103

-- end of futureUse4 Input8 trap

-- beginning of futureUse5 Input1 trap

    faultfutureUse5Input1False TRAP-TYPE
        ENTERPRISE  trapFault
        VARIABLES   { trapTag }
        DESCRIPTION
            "FutureUse5 Cleared on Input1"
    ::= 2104
    
    faultfutureUse5Input1True TRAP-TYPE
        ENTERPRISE  trapFault
        VARIABLES   { trapTag }
        DESCRIPTION
            "FutureUse5 Alert on Input1"
    ::= 2105

-- end of futureUse5 Input1 trap

-- beginning of futureUse5 Input2 trap

    faultfutureUse5Input2False TRAP-TYPE
        ENTERPRISE  trapFault
        VARIABLES   { trapTag }
        DESCRIPTION
            "FutureUse5 Cleared on Input2"
    ::= 2106
    
    faultfutureUse5Input2True TRAP-TYPE
        ENTERPRISE  trapFault
        VARIABLES   { trapTag }
        DESCRIPTION
            "FutureUse5 Alert on Input2"
    ::= 2107

-- end of futureUse5 Input2 trap

-- beginning of futureUse5 Input3 trap

    faultfutureUse5Input3False TRAP-TYPE
        ENTERPRISE  trapFault
        VARIABLES   { trapTag }
        DESCRIPTION
            "FutureUse5 Cleared on Input3"
    ::= 2108
    
    faultfutureUse5Input3True TRAP-TYPE
        ENTERPRISE  trapFault
        VARIABLES   { trapTag }
        DESCRIPTION
            "FutureUse5 Alert on Input3"
    ::= 2109

-- end of futureUse5 Input3 trap

-- beginning of futureUse5 Input4 trap

    faultfutureUse5Input4False TRAP-TYPE
        ENTERPRISE  trapFault
        VARIABLES   { trapTag }
        DESCRIPTION
            "FutureUse5 Cleared on Input4"
    ::= 2110
    
    faultfutureUse5Input4True TRAP-TYPE
        ENTERPRISE  trapFault
        VARIABLES   { trapTag }
        DESCRIPTION
            "FutureUse5 Alert on Input4"
    ::= 2111

-- end of futureUse5 Input4 trap

-- beginning of futureUse5 Input5 trap

    faultfutureUse5Input5False TRAP-TYPE
        ENTERPRISE  trapFault
        VARIABLES   { trapTag }
        DESCRIPTION
            "FutureUse5 Cleared on Input5"
    ::= 2112
    
    faultfutureUse5Input5True TRAP-TYPE
        ENTERPRISE  trapFault
        VARIABLES   { trapTag }
        DESCRIPTION
            "FutureUse5 Alert on Input5"
    ::= 2113

-- end of futureUse5 Input5 trap

-- beginning of futureUse5 Input6 trap

    faultfutureUse5Input6False TRAP-TYPE
        ENTERPRISE  trapFault
        VARIABLES   { trapTag }
        DESCRIPTION
            "FutureUse5 Cleared on Input6"
    ::= 2114
    
    faultfutureUse5Input6True TRAP-TYPE
        ENTERPRISE  trapFault
        VARIABLES   { trapTag }
        DESCRIPTION
            "FutureUse5 Alert on Input6"
    ::= 2115

-- end of futureUse5 Input6 trap

-- beginning of futureUse5 Input7 trap

    faultfutureUse5Input7False TRAP-TYPE
        ENTERPRISE  trapFault
        VARIABLES   { trapTag }
        DESCRIPTION
            "FutureUse5 Cleared on Input7"
    ::= 2116
    
    faultfutureUse5Input7True TRAP-TYPE
        ENTERPRISE  trapFault
        VARIABLES   { trapTag }
        DESCRIPTION
            "FutureUse5 Alert on Input7"
    ::= 2117

-- end of futureUse5 Input7 trap

-- beginning of futureUse5 Input8 trap

    faultfutureUse5Input8False TRAP-TYPE
        ENTERPRISE  trapFault
        VARIABLES   { trapTag }
        DESCRIPTION
            "FutureUse5 Cleared on Input8"
    ::= 2118
    
    faultfutureUse5Input8True TRAP-TYPE
        ENTERPRISE  trapFault
        VARIABLES   { trapTag }
        DESCRIPTION
            "FutureUse5 Alert on Input8"
    ::= 2119

-- end of futureUse5 Input8 trap

-- beginning of futureUse6 Input1 trap

    faultfutureUse6Input1False TRAP-TYPE
        ENTERPRISE  trapFault
        VARIABLES   { trapTag }
        DESCRIPTION
            "FutureUse6 Cleared on Input1"
    ::= 2120
    
    faultfutureUse6Input1True TRAP-TYPE
        ENTERPRISE  trapFault
        VARIABLES   { trapTag }
        DESCRIPTION
            "FutureUse6 Alert on Input1"
    ::= 2121

-- end of futureUse6 Input1 trap

-- beginning of futureUse6 Input2 trap

    faultfutureUse6Input2False TRAP-TYPE
        ENTERPRISE  trapFault
        VARIABLES   { trapTag }
        DESCRIPTION
            "FutureUse6 Cleared on Input2"
    ::= 2122
    
    faultfutureUse6Input2True TRAP-TYPE
        ENTERPRISE  trapFault
        VARIABLES   { trapTag }
        DESCRIPTION
            "FutureUse6 Alert on Input2"
    ::= 2123

-- end of futureUse6 Input2 trap

-- beginning of futureUse6 Input3 trap

    faultfutureUse6Input3False TRAP-TYPE
        ENTERPRISE  trapFault
        VARIABLES   { trapTag }
        DESCRIPTION
            "FutureUse6 Cleared on Input3"
    ::= 2124
    
    faultfutureUse6Input3True TRAP-TYPE
        ENTERPRISE  trapFault
        VARIABLES   { trapTag }
        DESCRIPTION
            "FutureUse6 Alert on Input3"
    ::= 2125

-- end of futureUse6 Input3 trap

-- beginning of futureUse6 Input4 trap

    faultfutureUse6Input4False TRAP-TYPE
        ENTERPRISE  trapFault
        VARIABLES   { trapTag }
        DESCRIPTION
            "FutureUse6 Cleared on Input4"
    ::= 2126
    
    faultfutureUse6Input4True TRAP-TYPE
        ENTERPRISE  trapFault
        VARIABLES   { trapTag }
        DESCRIPTION
            "FutureUse6 Alert on Input4"
    ::= 2127

-- end of futureUse6 Input4 trap

-- beginning of futureUse6 Input5 trap

    faultfutureUse6Input5False TRAP-TYPE
        ENTERPRISE  trapFault
        VARIABLES   { trapTag }
        DESCRIPTION
            "FutureUse6 Cleared on Input5"
    ::= 2128
    
    faultfutureUse6Input5True TRAP-TYPE
        ENTERPRISE  trapFault
        VARIABLES   { trapTag }
        DESCRIPTION
            "FutureUse6 Alert on Input5"
    ::= 2129

-- end of futureUse6 Input5 trap

-- beginning of futureUse6 Input6 trap

    faultfutureUse6Input6False TRAP-TYPE
        ENTERPRISE  trapFault
        VARIABLES   { trapTag }
        DESCRIPTION
            "FutureUse6 Cleared on Input6"
    ::= 2130
    
    faultfutureUse6Input6True TRAP-TYPE
        ENTERPRISE  trapFault
        VARIABLES   { trapTag }
        DESCRIPTION
            "FutureUse6 Alert on Input6"
    ::= 2131

-- end of futureUse6 Input6 trap

-- beginning of futureUse6 Input7 trap

    faultfutureUse6Input7False TRAP-TYPE
        ENTERPRISE  trapFault
        VARIABLES   { trapTag }
        DESCRIPTION
            "FutureUse6 Cleared on Input7"
    ::= 2132
    
    faultfutureUse6Input7True TRAP-TYPE
        ENTERPRISE  trapFault
        VARIABLES   { trapTag }
        DESCRIPTION
            "FutureUse6 Alert on Input7"
    ::= 2133

-- end of futureUse6 Input7 trap

-- beginning of futureUse6 Input8 trap

    faultfutureUse6Input8False TRAP-TYPE
        ENTERPRISE  trapFault
        VARIABLES   { trapTag }
        DESCRIPTION
            "FutureUse6 Cleared on Input8"
    ::= 2134
    
    faultfutureUse6Input8True TRAP-TYPE
        ENTERPRISE  trapFault
        VARIABLES   { trapTag }
        DESCRIPTION
            "FutureUse6 Alert on Input8"
    ::= 2135

-- end of futureUse6 Input8 trap

-- beginning of futureUse7 Input1 trap

    faultfutureUse7Input1False TRAP-TYPE
        ENTERPRISE  trapFault
        VARIABLES   { trapTag }
        DESCRIPTION
            "FutureUse7 Cleared on Input1"
    ::= 2136
    
    faultfutureUse7Input1True TRAP-TYPE
        ENTERPRISE  trapFault
        VARIABLES   { trapTag }
        DESCRIPTION
            "FutureUse7 Alert on Input1"
    ::= 2137

-- end of futureUse7 Input1 trap

-- beginning of futureUse7 Input2 trap

    faultfutureUse7Input2False TRAP-TYPE
        ENTERPRISE  trapFault
        VARIABLES   { trapTag }
        DESCRIPTION
            "FutureUse7 Cleared on Input2"
    ::= 2138
    
    faultfutureUse7Input2True TRAP-TYPE
        ENTERPRISE  trapFault
        VARIABLES   { trapTag }
        DESCRIPTION
            "FutureUse7 Alert on Input2"
    ::= 2139

-- end of futureUse7 Input2 trap

-- beginning of futureUse7 Input3 trap

    faultfutureUse7Input3False TRAP-TYPE
        ENTERPRISE  trapFault
        VARIABLES   { trapTag }
        DESCRIPTION
            "FutureUse7 Cleared on Input3"
    ::= 2140
    
    faultfutureUse7Input3True TRAP-TYPE
        ENTERPRISE  trapFault
        VARIABLES   { trapTag }
        DESCRIPTION
            "FutureUse7 Alert on Input3"
    ::= 2141

-- end of futureUse7 Input3 trap

-- beginning of futureUse7 Input4 trap

    faultfutureUse7Input4False TRAP-TYPE
        ENTERPRISE  trapFault
        VARIABLES   { trapTag }
        DESCRIPTION
            "FutureUse7 Cleared on Input4"
    ::= 2142
    
    faultfutureUse7Input4True TRAP-TYPE
        ENTERPRISE  trapFault
        VARIABLES   { trapTag }
        DESCRIPTION
            "FutureUse7 Alert on Input4"
    ::= 2143

-- end of futureUse7 Input4 trap

-- beginning of futureUse7 Input5 trap

    faultfutureUse7Input5False TRAP-TYPE
        ENTERPRISE  trapFault
        VARIABLES   { trapTag }
        DESCRIPTION
            "FutureUse7 Cleared on Input5"
    ::= 2144
    
    faultfutureUse7Input5True TRAP-TYPE
        ENTERPRISE  trapFault
        VARIABLES   { trapTag }
        DESCRIPTION
            "FutureUse7 Alert on Input5"
    ::= 2145

-- end of futureUse7 Input5 trap

-- beginning of futureUse7 Input6 trap

    faultfutureUse7Input6False TRAP-TYPE
        ENTERPRISE  trapFault
        VARIABLES   { trapTag }
        DESCRIPTION
            "FutureUse7 Cleared on Input6"
    ::= 2146
    
    faultfutureUse7Input6True TRAP-TYPE
        ENTERPRISE  trapFault
        VARIABLES   { trapTag }
        DESCRIPTION
            "FutureUse7 Alert on Input6"
    ::= 2147

-- end of futureUse7 Input6 trap

-- beginning of futureUse7 Input7 trap

    faultfutureUse7Input7False TRAP-TYPE
        ENTERPRISE  trapFault
        VARIABLES   { trapTag }
        DESCRIPTION
            "FutureUse7 Cleared on Input7"
    ::= 2148
    
    faultfutureUse7Input7True TRAP-TYPE
        ENTERPRISE  trapFault
        VARIABLES   { trapTag }
        DESCRIPTION
            "FutureUse7 Alert on Input7"
    ::= 2149

-- end of futureUse7 Input7 trap

-- beginning of futureUse7 Input8 trap

    faultfutureUse7Input8False TRAP-TYPE
        ENTERPRISE  trapFault
        VARIABLES   { trapTag }
        DESCRIPTION
            "FutureUse7 Cleared on Input8"
    ::= 2150
    
    faultfutureUse7Input8True TRAP-TYPE
        ENTERPRISE  trapFault
        VARIABLES   { trapTag }
        DESCRIPTION
            "FutureUse7 Alert on Input8"
    ::= 2151

-- end of futureUse7 Input8 trap

-- beginning of futureUse8 Input1 trap

    faultfutureUse8Input1False TRAP-TYPE
        ENTERPRISE  trapFault
        VARIABLES   { trapTag }
        DESCRIPTION
            "FutureUse8 Cleared on Input1"
    ::= 2152
    
    faultfutureUse8Input1True TRAP-TYPE
        ENTERPRISE  trapFault
        VARIABLES   { trapTag }
        DESCRIPTION
            "FutureUse8 Alert on Input1"
    ::= 2153

-- end of futureUse8 Input1 trap

-- beginning of futureUse8 Input2 trap

    faultfutureUse8Input2False TRAP-TYPE
        ENTERPRISE  trapFault
        VARIABLES   { trapTag }
        DESCRIPTION
            "FutureUse8 Cleared on Input2"
    ::= 2154
    
    faultfutureUse8Input2True TRAP-TYPE
        ENTERPRISE  trapFault
        VARIABLES   { trapTag }
        DESCRIPTION
            "FutureUse8 Alert on Input2"
    ::= 2155

-- end of futureUse8 Input2 trap

-- beginning of futureUse8 Input3 trap

    faultfutureUse8Input3False TRAP-TYPE
        ENTERPRISE  trapFault
        VARIABLES   { trapTag }
        DESCRIPTION
            "FutureUse8 Cleared on Input3"
    ::= 2156
    
    faultfutureUse8Input3True TRAP-TYPE
        ENTERPRISE  trapFault
        VARIABLES   { trapTag }
        DESCRIPTION
            "FutureUse8 Alert on Input3"
    ::= 2157

-- end of futureUse8 Input3 trap

-- beginning of futureUse8 Input4 trap

    faultfutureUse8Input4False TRAP-TYPE
        ENTERPRISE  trapFault
        VARIABLES   { trapTag }
        DESCRIPTION
            "FutureUse8 Cleared on Input4"
    ::= 2158
    
    faultfutureUse8Input4True TRAP-TYPE
        ENTERPRISE  trapFault
        VARIABLES   { trapTag }
        DESCRIPTION
            "FutureUse8 Alert on Input4"
    ::= 2159

-- end of futureUse8 Input4 trap

-- beginning of futureUse8 Input5 trap

    faultfutureUse8Input5False TRAP-TYPE
        ENTERPRISE  trapFault
        VARIABLES   { trapTag }
        DESCRIPTION
            "FutureUse8 Cleared on Input5"
    ::= 2160
    
    faultfutureUse8Input5True TRAP-TYPE
        ENTERPRISE  trapFault
        VARIABLES   { trapTag }
        DESCRIPTION
            "FutureUse8 Alert on Input5"
    ::= 2161

-- end of futureUse8 Input5 trap

-- beginning of futureUse8 Input6 trap

    faultfutureUse8Input6False TRAP-TYPE
        ENTERPRISE  trapFault
        VARIABLES   { trapTag }
        DESCRIPTION
            "FutureUse8 Cleared on Input6"
    ::= 2162
    
    faultfutureUse8Input6True TRAP-TYPE
        ENTERPRISE  trapFault
        VARIABLES   { trapTag }
        DESCRIPTION
            "FutureUse8 Alert on Input6"
    ::= 2163

-- end of futureUse8 Input6 trap

-- beginning of futureUse8 Input7 trap

    faultfutureUse8Input7False TRAP-TYPE
        ENTERPRISE  trapFault
        VARIABLES   { trapTag }
        DESCRIPTION
            "FutureUse8 Cleared on Input7"
    ::= 2164
    
    faultfutureUse8Input7True TRAP-TYPE
        ENTERPRISE  trapFault
        VARIABLES   { trapTag }
        DESCRIPTION
            "FutureUse8 Alert on Input7"
    ::= 2165

-- end of futureUse8 Input7 trap

-- beginning of futureUse8 Input8 trap

    faultfutureUse8Input8False TRAP-TYPE
        ENTERPRISE  trapFault
        VARIABLES   { trapTag }
        DESCRIPTION
            "FutureUse8 Cleared on Input8"
    ::= 2166
    
    faultfutureUse8Input8True TRAP-TYPE
        ENTERPRISE  trapFault
        VARIABLES   { trapTag }
        DESCRIPTION
            "FutureUse8 Alert on Input8"
    ::= 2167

-- end of futureUse8 Input8 trap

-- beginning of futureUse9 Input1 trap

    faultfutureUse9Input1False TRAP-TYPE
        ENTERPRISE  trapFault
        VARIABLES   { trapTag }
        DESCRIPTION
            "FutureUse9 Cleared on Input1"
    ::= 2168
    
    faultfutureUse9Input1True TRAP-TYPE
        ENTERPRISE  trapFault
        VARIABLES   { trapTag }
        DESCRIPTION
            "FutureUse9 Alert on Input1"
    ::= 2169

-- end of futureUse9 Input1 trap

-- beginning of futureUse9 Input2 trap

    faultfutureUse9Input2False TRAP-TYPE
        ENTERPRISE  trapFault
        VARIABLES   { trapTag }
        DESCRIPTION
            "FutureUse9 Cleared on Input2"
    ::= 2170
    
    faultfutureUse9Input2True TRAP-TYPE
        ENTERPRISE  trapFault
        VARIABLES   { trapTag }
        DESCRIPTION
            "FutureUse9 Alert on Input2"
    ::= 2171

-- end of futureUse9 Input2 trap

-- beginning of futureUse9 Input3 trap

    faultfutureUse9Input3False TRAP-TYPE
        ENTERPRISE  trapFault
        VARIABLES   { trapTag }
        DESCRIPTION
            "FutureUse9 Cleared on Input3"
    ::= 2172
    
    faultfutureUse9Input3True TRAP-TYPE
        ENTERPRISE  trapFault
        VARIABLES   { trapTag }
        DESCRIPTION
            "FutureUse9 Alert on Input3"
    ::= 2173

-- end of futureUse9 Input3 trap

-- beginning of futureUse9 Input4 trap

    faultfutureUse9Input4False TRAP-TYPE
        ENTERPRISE  trapFault
        VARIABLES   { trapTag }
        DESCRIPTION
            "FutureUse9 Cleared on Input4"
    ::= 2174
    
    faultfutureUse9Input4True TRAP-TYPE
        ENTERPRISE  trapFault
        VARIABLES   { trapTag }
        DESCRIPTION
            "FutureUse9 Alert on Input4"
    ::= 2175

-- end of futureUse9 Input4 trap

-- beginning of futureUse9 Input5 trap

    faultfutureUse9Input5False TRAP-TYPE
        ENTERPRISE  trapFault
        VARIABLES   { trapTag }
        DESCRIPTION
            "FutureUse9 Cleared on Input5"
    ::= 2176
    
    faultfutureUse9Input5True TRAP-TYPE
        ENTERPRISE  trapFault
        VARIABLES   { trapTag }
        DESCRIPTION
            "FutureUse9 Alert on Input5"
    ::= 2177

-- end of futureUse9 Input5 trap

-- beginning of futureUse9 Input6 trap

    faultfutureUse9Input6False TRAP-TYPE
        ENTERPRISE  trapFault
        VARIABLES   { trapTag }
        DESCRIPTION
            "FutureUse9 Cleared on Input6"
    ::= 2178
    
    faultfutureUse9Input6True TRAP-TYPE
        ENTERPRISE  trapFault
        VARIABLES   { trapTag }
        DESCRIPTION
            "FutureUse9 Alert on Input6"
    ::= 2179

-- end of futureUse9 Input6 trap

-- beginning of futureUse9 Input7 trap

    faultfutureUse9Input7False TRAP-TYPE
        ENTERPRISE  trapFault
        VARIABLES   { trapTag }
        DESCRIPTION
            "FutureUse9 Cleared on Input7"
    ::= 2180
    
    faultfutureUse9Input7True TRAP-TYPE
        ENTERPRISE  trapFault
        VARIABLES   { trapTag }
        DESCRIPTION
            "FutureUse9 Alert on Input7"
    ::= 2181

-- end of futureUse9 Input7 trap

-- beginning of futureUse9 Input8 trap

    faultfutureUse9Input8False TRAP-TYPE
        ENTERPRISE  trapFault
        VARIABLES   { trapTag }
        DESCRIPTION
            "FutureUse9 Cleared on Input8"
    ::= 2182
    
    faultfutureUse9Input8True TRAP-TYPE
        ENTERPRISE  trapFault
        VARIABLES   { trapTag }
        DESCRIPTION
            "FutureUse9 Alert on Input8"
    ::= 2183

-- end of futureUse9 Input8 trap

-- beginning of futureUse10 Input1 trap

    faultfutureUse10Input1False TRAP-TYPE
        ENTERPRISE  trapFault
        VARIABLES   { trapTag }
        DESCRIPTION
            "FutureUse10 Cleared on Input1"
    ::= 2184
    
    faultfutureUse10Input1True TRAP-TYPE
        ENTERPRISE  trapFault
        VARIABLES   { trapTag }
        DESCRIPTION
            "FutureUse10 Alert on Input1"
    ::= 2185

-- end of futureUse10 Input1 trap

-- beginning of futureUse10 Input2 trap

    faultfutureUse10Input2False TRAP-TYPE
        ENTERPRISE  trapFault
        VARIABLES   { trapTag }
        DESCRIPTION
            "FutureUse10 Cleared on Input2"
    ::= 2186
    
    faultfutureUse10Input2True TRAP-TYPE
        ENTERPRISE  trapFault
        VARIABLES   { trapTag }
        DESCRIPTION
            "FutureUse10 Alert on Input2"
    ::= 2187

-- end of futureUse10 Input2 trap

-- beginning of futureUse10 Input3 trap

    faultfutureUse10Input3False TRAP-TYPE
        ENTERPRISE  trapFault
        VARIABLES   { trapTag }
        DESCRIPTION
            "FutureUse10 Cleared on Input3"
    ::= 2188
    
    faultfutureUse10Input3True TRAP-TYPE
        ENTERPRISE  trapFault
        VARIABLES   { trapTag }
        DESCRIPTION
            "FutureUse10 Alert on Input3"
    ::= 2189

-- end of futureUse10 Input3 trap

-- beginning of futureUse10 Input4 trap

    faultfutureUse10Input4False TRAP-TYPE
        ENTERPRISE  trapFault
        VARIABLES   { trapTag }
        DESCRIPTION
            "FutureUse10 Cleared on Input4"
    ::= 2190
    
    faultfutureUse10Input4True TRAP-TYPE
        ENTERPRISE  trapFault
        VARIABLES   { trapTag }
        DESCRIPTION
            "FutureUse10 Alert on Input4"
    ::= 2191

-- end of futureUse10 Input4 trap

-- beginning of futureUse10 Input5 trap

    faultfutureUse10Input5False TRAP-TYPE
        ENTERPRISE  trapFault
        VARIABLES   { trapTag }
        DESCRIPTION
            "FutureUse10 Cleared on Input5"
    ::= 2192
    
    faultfutureUse10Input5True TRAP-TYPE
        ENTERPRISE  trapFault
        VARIABLES   { trapTag }
        DESCRIPTION
            "FutureUse10 Alert on Input5"
    ::= 2193

-- end of futureUse10 Input5 trap

-- beginning of futureUse10 Input6 trap

    faultfutureUse10Input6False TRAP-TYPE
        ENTERPRISE  trapFault
        VARIABLES   { trapTag }
        DESCRIPTION
            "FutureUse10 Cleared on Input6"
    ::= 2194
    
    faultfutureUse10Input6True TRAP-TYPE
        ENTERPRISE  trapFault
        VARIABLES   { trapTag }
        DESCRIPTION
            "FutureUse10 Alert on Input6"
    ::= 2195

-- end of futureUse10 Input6 trap

-- beginning of futureUse10 Input7 trap

    faultfutureUse10Input7False TRAP-TYPE
        ENTERPRISE  trapFault
        VARIABLES   { trapTag }
        DESCRIPTION
            "FutureUse10 Cleared on Input7"
    ::= 2196
    
    faultfutureUse10Input7True TRAP-TYPE
        ENTERPRISE  trapFault
        VARIABLES   { trapTag }
        DESCRIPTION
            "FutureUse10 Alert on Input7"
    ::= 2197

-- end of futureUse10 Input7 trap

-- beginning of futureUse10 Input8 trap

    faultfutureUse10Input8False TRAP-TYPE
        ENTERPRISE  trapFault
        VARIABLES   { trapTag }
        DESCRIPTION
            "FutureUse10 Cleared on Input8"
    ::= 2198
    
    faultfutureUse10Input8True TRAP-TYPE
        ENTERPRISE  trapFault
        VARIABLES   { trapTag }
        DESCRIPTION
            "FutureUse10 Alert on Input8"
    ::= 2199

-- end of futureUse10 Input8 trap

-- beginning of futureUse11 Input1 trap

    faultfutureUse11Input1False TRAP-TYPE
        ENTERPRISE  trapFault
        VARIABLES   { trapTag }
        DESCRIPTION
            "FutureUse11 Cleared on Input1"
    ::= 2200
    
    faultfutureUse11Input1True TRAP-TYPE
        ENTERPRISE  trapFault
        VARIABLES   { trapTag }
        DESCRIPTION
            "FutureUse11 Alert on Input1"
    ::= 2201

-- end of futureUse11 Input1 trap

-- beginning of futureUse11 Input2 trap

    faultfutureUse11Input2False TRAP-TYPE
        ENTERPRISE  trapFault
        VARIABLES   { trapTag }
        DESCRIPTION
            "FutureUse11 Cleared on Input2"
    ::= 2202
    
    faultfutureUse11Input2True TRAP-TYPE
        ENTERPRISE  trapFault
        VARIABLES   { trapTag }
        DESCRIPTION
            "FutureUse11 Alert on Input2"
    ::= 2203

-- end of futureUse11 Input2 trap

-- beginning of futureUse11 Input3 trap

    faultfutureUse11Input3False TRAP-TYPE
        ENTERPRISE  trapFault
        VARIABLES   { trapTag }
        DESCRIPTION
            "FutureUse11 Cleared on Input3"
    ::= 2204
    
    faultfutureUse11Input3True TRAP-TYPE
        ENTERPRISE  trapFault
        VARIABLES   { trapTag }
        DESCRIPTION
            "FutureUse11 Alert on Input3"
    ::= 2205

-- end of futureUse11 Input3 trap

-- beginning of futureUse11 Input4 trap

    faultfutureUse11Input4False TRAP-TYPE
        ENTERPRISE  trapFault
        VARIABLES   { trapTag }
        DESCRIPTION
            "FutureUse11 Cleared on Input4"
    ::= 2206
    
    faultfutureUse11Input4True TRAP-TYPE
        ENTERPRISE  trapFault
        VARIABLES   { trapTag }
        DESCRIPTION
            "FutureUse11 Alert on Input4"
    ::= 2207

-- end of futureUse11 Input4 trap

-- beginning of futureUse11 Input5 trap

    faultfutureUse11Input5False TRAP-TYPE
        ENTERPRISE  trapFault
        VARIABLES   { trapTag }
        DESCRIPTION
            "FutureUse11 Cleared on Input5"
    ::= 2208
    
    faultfutureUse11Input5True TRAP-TYPE
        ENTERPRISE  trapFault
        VARIABLES   { trapTag }
        DESCRIPTION
            "FutureUse11 Alert on Input5"
    ::= 2209

-- end of futureUse11 Input5 trap

-- beginning of futureUse11 Input6 trap

    faultfutureUse11Input6False TRAP-TYPE
        ENTERPRISE  trapFault
        VARIABLES   { trapTag }
        DESCRIPTION
            "FutureUse11 Cleared on Input6"
    ::= 2210
    
    faultfutureUse11Input6True TRAP-TYPE
        ENTERPRISE  trapFault
        VARIABLES   { trapTag }
        DESCRIPTION
            "FutureUse11 Alert on Input6"
    ::= 2211

-- end of futureUse11 Input6 trap

-- beginning of futureUse11 Input7 trap

    faultfutureUse11Input7False TRAP-TYPE
        ENTERPRISE  trapFault
        VARIABLES   { trapTag }
        DESCRIPTION
            "FutureUse11 Cleared on Input7"
    ::= 2212
    
    faultfutureUse11Input7True TRAP-TYPE
        ENTERPRISE  trapFault
        VARIABLES   { trapTag }
        DESCRIPTION
            "FutureUse11 Alert on Input7"
    ::= 2213

-- end of futureUse11 Input7 trap

-- beginning of futureUse11 Input8 trap

    faultfutureUse11Input8False TRAP-TYPE
        ENTERPRISE  trapFault
        VARIABLES   { trapTag }
        DESCRIPTION
            "FutureUse11 Cleared on Input8"
    ::= 2214
    
    faultfutureUse11Input8True TRAP-TYPE
        ENTERPRISE  trapFault
        VARIABLES   { trapTag }
        DESCRIPTION
            "FutureUse11 Alert on Input8"
    ::= 2215

-- end of futureUse11 Input8 trap

-- beginning of futureUse12 Input1 trap

    faultfutureUse12Input1False TRAP-TYPE
        ENTERPRISE  trapFault
        VARIABLES   { trapTag }
        DESCRIPTION
            "FutureUse12 Cleared on Input1"
    ::= 2216
    
    faultfutureUse12Input1True TRAP-TYPE
        ENTERPRISE  trapFault
        VARIABLES   { trapTag }
        DESCRIPTION
            "FutureUse12 Alert on Input1"
    ::= 2217

-- end of futureUse12 Input1 trap

-- beginning of futureUse12 Input2 trap

    faultfutureUse12Input2False TRAP-TYPE
        ENTERPRISE  trapFault
        VARIABLES   { trapTag }
        DESCRIPTION
            "FutureUse12 Cleared on Input2"
    ::= 2218
    
    faultfutureUse12Input2True TRAP-TYPE
        ENTERPRISE  trapFault
        VARIABLES   { trapTag }
        DESCRIPTION
            "FutureUse12 Alert on Input2"
    ::= 2219

-- end of futureUse12 Input2 trap

-- beginning of futureUse12 Input3 trap

    faultfutureUse12Input3False TRAP-TYPE
        ENTERPRISE  trapFault
        VARIABLES   { trapTag }
        DESCRIPTION
            "FutureUse12 Cleared on Input3"
    ::= 2220
    
    faultfutureUse12Input3True TRAP-TYPE
        ENTERPRISE  trapFault
        VARIABLES   { trapTag }
        DESCRIPTION
            "FutureUse12 Alert on Input3"
    ::= 2221

-- end of futureUse12 Input3 trap

-- beginning of futureUse12 Input4 trap

    faultfutureUse12Input4False TRAP-TYPE
        ENTERPRISE  trapFault
        VARIABLES   { trapTag }
        DESCRIPTION
            "FutureUse12 Cleared on Input4"
    ::= 2222
    
    faultfutureUse12Input4True TRAP-TYPE
        ENTERPRISE  trapFault
        VARIABLES   { trapTag }
        DESCRIPTION
            "FutureUse12 Alert on Input4"
    ::= 2223

-- end of futureUse12 Input4 trap

-- beginning of futureUse12 Input5 trap

    faultfutureUse12Input5False TRAP-TYPE
        ENTERPRISE  trapFault
        VARIABLES   { trapTag }
        DESCRIPTION
            "FutureUse12 Cleared on Input5"
    ::= 2224
    
    faultfutureUse12Input5True TRAP-TYPE
        ENTERPRISE  trapFault
        VARIABLES   { trapTag }
        DESCRIPTION
            "FutureUse12 Alert on Input5"
    ::= 2225

-- end of futureUse12 Input5 trap

-- beginning of futureUse12 Input6 trap

    faultfutureUse12Input6False TRAP-TYPE
        ENTERPRISE  trapFault
        VARIABLES   { trapTag }
        DESCRIPTION
            "FutureUse12 Cleared on Input6"
    ::= 2226
    
    faultfutureUse12Input6True TRAP-TYPE
        ENTERPRISE  trapFault
        VARIABLES   { trapTag }
        DESCRIPTION
            "FutureUse12 Alert on Input6"
    ::= 2227

-- end of futureUse12 Input6 trap

-- beginning of futureUse12 Input7 trap

    faultfutureUse12Input7False TRAP-TYPE
        ENTERPRISE  trapFault
        VARIABLES   { trapTag }
        DESCRIPTION
            "FutureUse12 Cleared on Input7"
    ::= 2228
    
    faultfutureUse12Input7True TRAP-TYPE
        ENTERPRISE  trapFault
        VARIABLES   { trapTag }
        DESCRIPTION
            "FutureUse12 Alert on Input7"
    ::= 2229

-- end of futureUse12 Input7 trap

-- beginning of futureUse12 Input8 trap

    faultfutureUse12Input8False TRAP-TYPE
        ENTERPRISE  trapFault
        VARIABLES   { trapTag }
        DESCRIPTION
            "FutureUse12 Cleared on Input8"
    ::= 2230
    
    faultfutureUse12Input8True TRAP-TYPE
        ENTERPRISE  trapFault
        VARIABLES   { trapTag }
        DESCRIPTION
            "FutureUse12 Alert on Input8"
    ::= 2231

-- end of futureUse12 Input8 trap

-- beginning of futureUse13 Input1 trap

    faultfutureUse13Input1False TRAP-TYPE
        ENTERPRISE  trapFault
        VARIABLES   { trapTag }
        DESCRIPTION
            "FutureUse13 Cleared on Input1"
    ::= 2232
    
    faultfutureUse13Input1True TRAP-TYPE
        ENTERPRISE  trapFault
        VARIABLES   { trapTag }
        DESCRIPTION
            "FutureUse13 Alert on Input1"
    ::= 2233

-- end of futureUse13 Input1 trap

-- beginning of futureUse13 Input2 trap

    faultfutureUse13Input2False TRAP-TYPE
        ENTERPRISE  trapFault
        VARIABLES   { trapTag }
        DESCRIPTION
            "FutureUse13 Cleared on Input2"
    ::= 2234
    
    faultfutureUse13Input2True TRAP-TYPE
        ENTERPRISE  trapFault
        VARIABLES   { trapTag }
        DESCRIPTION
            "FutureUse13 Alert on Input2"
    ::= 2235

-- end of futureUse13 Input2 trap

-- beginning of futureUse13 Input3 trap

    faultfutureUse13Input3False TRAP-TYPE
        ENTERPRISE  trapFault
        VARIABLES   { trapTag }
        DESCRIPTION
            "FutureUse13 Cleared on Input3"
    ::= 2236
    
    faultfutureUse13Input3True TRAP-TYPE
        ENTERPRISE  trapFault
        VARIABLES   { trapTag }
        DESCRIPTION
            "FutureUse13 Alert on Input3"
    ::= 2237

-- end of futureUse13 Input3 trap

-- beginning of futureUse13 Input4 trap

    faultfutureUse13Input4False TRAP-TYPE
        ENTERPRISE  trapFault
        VARIABLES   { trapTag }
        DESCRIPTION
            "FutureUse13 Cleared on Input4"
    ::= 2238
    
    faultfutureUse13Input4True TRAP-TYPE
        ENTERPRISE  trapFault
        VARIABLES   { trapTag }
        DESCRIPTION
            "FutureUse13 Alert on Input4"
    ::= 2239

-- end of futureUse13 Input4 trap

-- beginning of futureUse13 Input5 trap

    faultfutureUse13Input5False TRAP-TYPE
        ENTERPRISE  trapFault
        VARIABLES   { trapTag }
        DESCRIPTION
            "FutureUse13 Cleared on Input5"
    ::= 2240
    
    faultfutureUse13Input5True TRAP-TYPE
        ENTERPRISE  trapFault
        VARIABLES   { trapTag }
        DESCRIPTION
            "FutureUse13 Alert on Input5"
    ::= 2241

-- end of futureUse13 Input5 trap

-- beginning of futureUse13 Input6 trap

    faultfutureUse13Input6False TRAP-TYPE
        ENTERPRISE  trapFault
        VARIABLES   { trapTag }
        DESCRIPTION
            "FutureUse13 Cleared on Input6"
    ::= 2242
    
    faultfutureUse13Input6True TRAP-TYPE
        ENTERPRISE  trapFault
        VARIABLES   { trapTag }
        DESCRIPTION
            "FutureUse13 Alert on Input6"
    ::= 2243

-- end of futureUse13 Input6 trap

-- beginning of futureUse13 Input7 trap

    faultfutureUse13Input7False TRAP-TYPE
        ENTERPRISE  trapFault
        VARIABLES   { trapTag }
        DESCRIPTION
            "FutureUse13 Cleared on Input7"
    ::= 2244
    
    faultfutureUse13Input7True TRAP-TYPE
        ENTERPRISE  trapFault
        VARIABLES   { trapTag }
        DESCRIPTION
            "FutureUse13 Alert on Input7"
    ::= 2245

-- end of futureUse13 Input7 trap

-- beginning of futureUse13 Input8 trap

    faultfutureUse13Input8False TRAP-TYPE
        ENTERPRISE  trapFault
        VARIABLES   { trapTag }
        DESCRIPTION
            "FutureUse13 Cleared on Input8"
    ::= 2246
    
    faultfutureUse13Input8True TRAP-TYPE
        ENTERPRISE  trapFault
        VARIABLES   { trapTag }
        DESCRIPTION
            "FutureUse13 Alert on Input8"
    ::= 2247

-- end of futureUse13 Input8 trap

-- beginning of futureUse14 Input1 trap

    faultfutureUse14Input1False TRAP-TYPE
        ENTERPRISE  trapFault
        VARIABLES   { trapTag }
        DESCRIPTION
            "FutureUse14 Cleared on Input1"
    ::= 2248
    
    faultfutureUse14Input1True TRAP-TYPE
        ENTERPRISE  trapFault
        VARIABLES   { trapTag }
        DESCRIPTION
            "FutureUse14 Alert on Input1"
    ::= 2249

-- end of futureUse14 Input1 trap

-- beginning of futureUse14 Input2 trap

    faultfutureUse14Input2False TRAP-TYPE
        ENTERPRISE  trapFault
        VARIABLES   { trapTag }
        DESCRIPTION
            "FutureUse14 Cleared on Input2"
    ::= 2250
    
    faultfutureUse14Input2True TRAP-TYPE
        ENTERPRISE  trapFault
        VARIABLES   { trapTag }
        DESCRIPTION
            "FutureUse14 Alert on Input2"
    ::= 2251

-- end of futureUse14 Input2 trap

-- beginning of futureUse14 Input3 trap

    faultfutureUse14Input3False TRAP-TYPE
        ENTERPRISE  trapFault
        VARIABLES   { trapTag }
        DESCRIPTION
            "FutureUse14 Cleared on Input3"
    ::= 2252
    
    faultfutureUse14Input3True TRAP-TYPE
        ENTERPRISE  trapFault
        VARIABLES   { trapTag }
        DESCRIPTION
            "FutureUse14 Alert on Input3"
    ::= 2253

-- end of futureUse14 Input3 trap

-- beginning of futureUse14 Input4 trap

    faultfutureUse14Input4False TRAP-TYPE
        ENTERPRISE  trapFault
        VARIABLES   { trapTag }
        DESCRIPTION
            "FutureUse14 Cleared on Input4"
    ::= 2254
    
    faultfutureUse14Input4True TRAP-TYPE
        ENTERPRISE  trapFault
        VARIABLES   { trapTag }
        DESCRIPTION
            "FutureUse14 Alert on Input4"
    ::= 2255

-- end of futureUse14 Input4 trap

-- beginning of futureUse14 Input5 trap

    faultfutureUse14Input5False TRAP-TYPE
        ENTERPRISE  trapFault
        VARIABLES   { trapTag }
        DESCRIPTION
            "FutureUse14 Cleared on Input5"
    ::= 2256
    
    faultfutureUse14Input5True TRAP-TYPE
        ENTERPRISE  trapFault
        VARIABLES   { trapTag }
        DESCRIPTION
            "FutureUse14 Alert on Input5"
    ::= 2257

-- end of futureUse14 Input5 trap

-- beginning of futureUse14 Input6 trap

    faultfutureUse14Input6False TRAP-TYPE
        ENTERPRISE  trapFault
        VARIABLES   { trapTag }
        DESCRIPTION
            "FutureUse14 Cleared on Input6"
    ::= 2258
    
    faultfutureUse14Input6True TRAP-TYPE
        ENTERPRISE  trapFault
        VARIABLES   { trapTag }
        DESCRIPTION
            "FutureUse14 Alert on Input6"
    ::= 2259

-- end of futureUse14 Input6 trap

-- beginning of futureUse14 Input7 trap

    faultfutureUse14Input7False TRAP-TYPE
        ENTERPRISE  trapFault
        VARIABLES   { trapTag }
        DESCRIPTION
            "FutureUse14 Cleared on Input7"
    ::= 2260
    
    faultfutureUse14Input7True TRAP-TYPE
        ENTERPRISE  trapFault
        VARIABLES   { trapTag }
        DESCRIPTION
            "FutureUse14 Alert on Input7"
    ::= 2261

-- end of futureUse14 Input7 trap

-- beginning of futureUse14 Input8 trap

    faultfutureUse14Input8False TRAP-TYPE
        ENTERPRISE  trapFault
        VARIABLES   { trapTag }
        DESCRIPTION
            "FutureUse14 Cleared on Input8"
    ::= 2262
    
    faultfutureUse14Input8True TRAP-TYPE
        ENTERPRISE  trapFault
        VARIABLES   { trapTag }
        DESCRIPTION
            "FutureUse14 Alert on Input8"
    ::= 2263

-- end of futureUse14 Input8 trap

-- beginning of futureUse15 Input1 trap

    faultfutureUse15Input1False TRAP-TYPE
        ENTERPRISE  trapFault
        VARIABLES   { trapTag }
        DESCRIPTION
            "FutureUse15 Cleared on Input1"
    ::= 2264
    
    faultfutureUse15Input1True TRAP-TYPE
        ENTERPRISE  trapFault
        VARIABLES   { trapTag }
        DESCRIPTION
            "FutureUse15 Alert on Input1"
    ::= 2265

-- end of futureUse15 Input1 trap

-- beginning of futureUse15 Input2 trap

    faultfutureUse15Input2False TRAP-TYPE
        ENTERPRISE  trapFault
        VARIABLES   { trapTag }
        DESCRIPTION
            "FutureUse15 Cleared on Input2"
    ::= 2266
    
    faultfutureUse15Input2True TRAP-TYPE
        ENTERPRISE  trapFault
        VARIABLES   { trapTag }
        DESCRIPTION
            "FutureUse15 Alert on Input2"
    ::= 2267

-- end of futureUse15 Input2 trap

-- beginning of futureUse15 Input3 trap

    faultfutureUse15Input3False TRAP-TYPE
        ENTERPRISE  trapFault
        VARIABLES   { trapTag }
        DESCRIPTION
            "FutureUse15 Cleared on Input3"
    ::= 2268
    
    faultfutureUse15Input3True TRAP-TYPE
        ENTERPRISE  trapFault
        VARIABLES   { trapTag }
        DESCRIPTION
            "FutureUse15 Alert on Input3"
    ::= 2269

-- end of futureUse15 Input3 trap

-- beginning of futureUse15 Input4 trap

    faultfutureUse15Input4False TRAP-TYPE
        ENTERPRISE  trapFault
        VARIABLES   { trapTag }
        DESCRIPTION
            "FutureUse15 Cleared on Input4"
    ::= 2270
    
    faultfutureUse15Input4True TRAP-TYPE
        ENTERPRISE  trapFault
        VARIABLES   { trapTag }
        DESCRIPTION
            "FutureUse15 Alert on Input4"
    ::= 2271

-- end of futureUse15 Input4 trap

-- beginning of futureUse15 Input5 trap

    faultfutureUse15Input5False TRAP-TYPE
        ENTERPRISE  trapFault
        VARIABLES   { trapTag }
        DESCRIPTION
            "FutureUse15 Cleared on Input5"
    ::= 2272
    
    faultfutureUse15Input5True TRAP-TYPE
        ENTERPRISE  trapFault
        VARIABLES   { trapTag }
        DESCRIPTION
            "FutureUse15 Alert on Input5"
    ::= 2273

-- end of futureUse15 Input5 trap

-- beginning of futureUse15 Input6 trap

    faultfutureUse15Input6False TRAP-TYPE
        ENTERPRISE  trapFault
        VARIABLES   { trapTag }
        DESCRIPTION
            "FutureUse15 Cleared on Input6"
    ::= 2274
    
    faultfutureUse15Input6True TRAP-TYPE
        ENTERPRISE  trapFault
        VARIABLES   { trapTag }
        DESCRIPTION
            "FutureUse15 Alert on Input6"
    ::= 2275

-- end of futureUse15 Input6 trap

-- beginning of futureUse15 Input7 trap

    faultfutureUse15Input7False TRAP-TYPE
        ENTERPRISE  trapFault
        VARIABLES   { trapTag }
        DESCRIPTION
            "FutureUse15 Cleared on Input7"
    ::= 2276
    
    faultfutureUse15Input7True TRAP-TYPE
        ENTERPRISE  trapFault
        VARIABLES   { trapTag }
        DESCRIPTION
            "FutureUse15 Alert on Input7"
    ::= 2277

-- end of futureUse15 Input7 trap

-- beginning of futureUse15 Input8 trap

    faultfutureUse15Input8False TRAP-TYPE
        ENTERPRISE  trapFault
        VARIABLES   { trapTag }
        DESCRIPTION
            "FutureUse15 Cleared on Input8"
    ::= 2278
    
    faultfutureUse15Input8True TRAP-TYPE
        ENTERPRISE  trapFault
        VARIABLES   { trapTag }
        DESCRIPTION
            "FutureUse15 Alert on Input8"
    ::= 2279

-- end of futureUse15 Input8 trap

-- beginning of futureUse16 Input1 trap

    faultfutureUse16Input1False TRAP-TYPE
        ENTERPRISE  trapFault
        VARIABLES   { trapTag }
        DESCRIPTION
            "FutureUse16 Cleared on Input1"
    ::= 2280
    
    faultfutureUse16Input1True TRAP-TYPE
        ENTERPRISE  trapFault
        VARIABLES   { trapTag }
        DESCRIPTION
            "FutureUse16 Alert on Input1"
    ::= 2281

-- end of futureUse16 Input1 trap

-- beginning of futureUse16 Input2 trap

    faultfutureUse16Input2False TRAP-TYPE
        ENTERPRISE  trapFault
        VARIABLES   { trapTag }
        DESCRIPTION
            "FutureUse16 Cleared on Input2"
    ::= 2282
    
    faultfutureUse16Input2True TRAP-TYPE
        ENTERPRISE  trapFault
        VARIABLES   { trapTag }
        DESCRIPTION
            "FutureUse16 Alert on Input2"
    ::= 2283

-- end of futureUse16 Input2 trap

-- beginning of futureUse16 Input3 trap

    faultfutureUse16Input3False TRAP-TYPE
        ENTERPRISE  trapFault
        VARIABLES   { trapTag }
        DESCRIPTION
            "FutureUse16 Cleared on Input3"
    ::= 2284
    
    faultfutureUse16Input3True TRAP-TYPE
        ENTERPRISE  trapFault
        VARIABLES   { trapTag }
        DESCRIPTION
            "FutureUse16 Alert on Input3"
    ::= 2285

-- end of futureUse16 Input3 trap

-- beginning of futureUse16 Input4 trap

    faultfutureUse16Input4False TRAP-TYPE
        ENTERPRISE  trapFault
        VARIABLES   { trapTag }
        DESCRIPTION
            "FutureUse16 Cleared on Input4"
    ::= 2286
    
    faultfutureUse16Input4True TRAP-TYPE
        ENTERPRISE  trapFault
        VARIABLES   { trapTag }
        DESCRIPTION
            "FutureUse16 Alert on Input4"
    ::= 2287

-- end of futureUse16 Input4 trap

-- beginning of futureUse16 Input5 trap

    faultfutureUse16Input5False TRAP-TYPE
        ENTERPRISE  trapFault
        VARIABLES   { trapTag }
        DESCRIPTION
            "FutureUse16 Cleared on Input5"
    ::= 2288
    
    faultfutureUse16Input5True TRAP-TYPE
        ENTERPRISE  trapFault
        VARIABLES   { trapTag }
        DESCRIPTION
            "FutureUse16 Alert on Input5"
    ::= 2289

-- end of futureUse16 Input5 trap

-- beginning of futureUse16 Input6 trap

    faultfutureUse16Input6False TRAP-TYPE
        ENTERPRISE  trapFault
        VARIABLES   { trapTag }
        DESCRIPTION
            "FutureUse16 Cleared on Input6"
    ::= 2290
    
    faultfutureUse16Input6True TRAP-TYPE
        ENTERPRISE  trapFault
        VARIABLES   { trapTag }
        DESCRIPTION
            "FutureUse16 Alert on Input6"
    ::= 2291

-- end of futureUse16 Input6 trap

-- beginning of futureUse16 Input7 trap

    faultfutureUse16Input7False TRAP-TYPE
        ENTERPRISE  trapFault
        VARIABLES   { trapTag }
        DESCRIPTION
            "FutureUse16 Cleared on Input7"
    ::= 2292
    
    faultfutureUse16Input7True TRAP-TYPE
        ENTERPRISE  trapFault
        VARIABLES   { trapTag }
        DESCRIPTION
            "FutureUse16 Alert on Input7"
    ::= 2293

-- end of futureUse16 Input7 trap

-- beginning of futureUse16 Input8 trap

    faultfutureUse16Input8False TRAP-TYPE
        ENTERPRISE  trapFault
        VARIABLES   { trapTag }
        DESCRIPTION
            "FutureUse16 Cleared on Input8"
    ::= 2294
    
    faultfutureUse16Input8True TRAP-TYPE
        ENTERPRISE  trapFault
        VARIABLES   { trapTag }
        DESCRIPTION
            "FutureUse16 Alert on Input8"
    ::= 2295

-- end of futureUse16 Input8 trap

-- beginning of futureUse17 Input1 trap

    faultfutureUse17Input1False TRAP-TYPE
        ENTERPRISE  trapFault
        VARIABLES   { trapTag }
        DESCRIPTION
            "FutureUse17 Cleared on Input1"
    ::= 2296
    
    faultfutureUse17Input1True TRAP-TYPE
        ENTERPRISE  trapFault
        VARIABLES   { trapTag }
        DESCRIPTION
            "FutureUse17 Alert on Input1"
    ::= 2297

-- end of futureUse17 Input1 trap

-- beginning of futureUse17 Input2 trap

    faultfutureUse17Input2False TRAP-TYPE
        ENTERPRISE  trapFault
        VARIABLES   { trapTag }
        DESCRIPTION
            "FutureUse17 Cleared on Input2"
    ::= 2298
    
    faultfutureUse17Input2True TRAP-TYPE
        ENTERPRISE  trapFault
        VARIABLES   { trapTag }
        DESCRIPTION
            "FutureUse17 Alert on Input2"
    ::= 2299

-- end of futureUse17 Input2 trap

-- beginning of futureUse17 Input3 trap

    faultfutureUse17Input3False TRAP-TYPE
        ENTERPRISE  trapFault
        VARIABLES   { trapTag }
        DESCRIPTION
            "FutureUse17 Cleared on Input3"
    ::= 2300
    
    faultfutureUse17Input3True TRAP-TYPE
        ENTERPRISE  trapFault
        VARIABLES   { trapTag }
        DESCRIPTION
            "FutureUse17 Alert on Input3"
    ::= 2301

-- end of futureUse17 Input3 trap

-- beginning of futureUse17 Input4 trap

    faultfutureUse17Input4False TRAP-TYPE
        ENTERPRISE  trapFault
        VARIABLES   { trapTag }
        DESCRIPTION
            "FutureUse17 Cleared on Input4"
    ::= 2302
    
    faultfutureUse17Input4True TRAP-TYPE
        ENTERPRISE  trapFault
        VARIABLES   { trapTag }
        DESCRIPTION
            "FutureUse17 Alert on Input4"
    ::= 2303

-- end of futureUse17 Input4 trap

-- beginning of futureUse17 Input5 trap

    faultfutureUse17Input5False TRAP-TYPE
        ENTERPRISE  trapFault
        VARIABLES   { trapTag }
        DESCRIPTION
            "FutureUse17 Cleared on Input5"
    ::= 2304
    
    faultfutureUse17Input5True TRAP-TYPE
        ENTERPRISE  trapFault
        VARIABLES   { trapTag }
        DESCRIPTION
            "FutureUse17 Alert on Input5"
    ::= 2305

-- end of futureUse17 Input5 trap

-- beginning of futureUse17 Input6 trap

    faultfutureUse17Input6False TRAP-TYPE
        ENTERPRISE  trapFault
        VARIABLES   { trapTag }
        DESCRIPTION
            "FutureUse17 Cleared on Input6"
    ::= 2306
    
    faultfutureUse17Input6True TRAP-TYPE
        ENTERPRISE  trapFault
        VARIABLES   { trapTag }
        DESCRIPTION
            "FutureUse17 Alert on Input6"
    ::= 2307

-- end of futureUse17 Input6 trap

-- beginning of futureUse17 Input7 trap

    faultfutureUse17Input7False TRAP-TYPE
        ENTERPRISE  trapFault
        VARIABLES   { trapTag }
        DESCRIPTION
            "FutureUse17 Cleared on Input7"
    ::= 2308
    
    faultfutureUse17Input7True TRAP-TYPE
        ENTERPRISE  trapFault
        VARIABLES   { trapTag }
        DESCRIPTION
            "FutureUse17 Alert on Input7"
    ::= 2309

-- end of futureUse17 Input7 trap

-- beginning of futureUse17 Input8 trap

    faultfutureUse17Input8False TRAP-TYPE
        ENTERPRISE  trapFault
        VARIABLES   { trapTag }
        DESCRIPTION
            "FutureUse17 Cleared on Input8"
    ::= 2310
    
    faultfutureUse17Input8True TRAP-TYPE
        ENTERPRISE  trapFault
        VARIABLES   { trapTag }
        DESCRIPTION
            "FutureUse17 Alert on Input8"
    ::= 2311

-- end of futureUse17 Input8 trap

-- beginning of futureUse18 Input1 trap

    faultfutureUse18Input1False TRAP-TYPE
        ENTERPRISE  trapFault
        VARIABLES   { trapTag }
        DESCRIPTION
            "FutureUse18 Cleared on Input1"
    ::= 2312
    
    faultfutureUse18Input1True TRAP-TYPE
        ENTERPRISE  trapFault
        VARIABLES   { trapTag }
        DESCRIPTION
            "FutureUse18 Alert on Input1"
    ::= 2313

-- end of futureUse18 Input1 trap

-- beginning of futureUse18 Input2 trap

    faultfutureUse18Input2False TRAP-TYPE
        ENTERPRISE  trapFault
        VARIABLES   { trapTag }
        DESCRIPTION
            "FutureUse18 Cleared on Input2"
    ::= 2314
    
    faultfutureUse18Input2True TRAP-TYPE
        ENTERPRISE  trapFault
        VARIABLES   { trapTag }
        DESCRIPTION
            "FutureUse18 Alert on Input2"
    ::= 2315

-- end of futureUse18 Input2 trap

-- beginning of futureUse18 Input3 trap

    faultfutureUse18Input3False TRAP-TYPE
        ENTERPRISE  trapFault
        VARIABLES   { trapTag }
        DESCRIPTION
            "FutureUse18 Cleared on Input3"
    ::= 2316
    
    faultfutureUse18Input3True TRAP-TYPE
        ENTERPRISE  trapFault
        VARIABLES   { trapTag }
        DESCRIPTION
            "FutureUse18 Alert on Input3"
    ::= 2317

-- end of futureUse18 Input3 trap

-- beginning of futureUse18 Input4 trap

    faultfutureUse18Input4False TRAP-TYPE
        ENTERPRISE  trapFault
        VARIABLES   { trapTag }
        DESCRIPTION
            "FutureUse18 Cleared on Input4"
    ::= 2318
    
    faultfutureUse18Input4True TRAP-TYPE
        ENTERPRISE  trapFault
        VARIABLES   { trapTag }
        DESCRIPTION
            "FutureUse18 Alert on Input4"
    ::= 2319

-- end of futureUse18 Input4 trap

-- beginning of futureUse18 Input5 trap

    faultfutureUse18Input5False TRAP-TYPE
        ENTERPRISE  trapFault
        VARIABLES   { trapTag }
        DESCRIPTION
            "FutureUse18 Cleared on Input5"
    ::= 2320
    
    faultfutureUse18Input5True TRAP-TYPE
        ENTERPRISE  trapFault
        VARIABLES   { trapTag }
        DESCRIPTION
            "FutureUse18 Alert on Input5"
    ::= 2321

-- end of futureUse18 Input5 trap

-- beginning of futureUse18 Input6 trap

    faultfutureUse18Input6False TRAP-TYPE
        ENTERPRISE  trapFault
        VARIABLES   { trapTag }
        DESCRIPTION
            "FutureUse18 Cleared on Input6"
    ::= 2322
    
    faultfutureUse18Input6True TRAP-TYPE
        ENTERPRISE  trapFault
        VARIABLES   { trapTag }
        DESCRIPTION
            "FutureUse18 Alert on Input6"
    ::= 2323

-- end of futureUse18 Input6 trap

-- beginning of futureUse18 Input7 trap

    faultfutureUse18Input7False TRAP-TYPE
        ENTERPRISE  trapFault
        VARIABLES   { trapTag }
        DESCRIPTION
            "FutureUse18 Cleared on Input7"
    ::= 2324
    
    faultfutureUse18Input7True TRAP-TYPE
        ENTERPRISE  trapFault
        VARIABLES   { trapTag }
        DESCRIPTION
            "FutureUse18 Alert on Input7"
    ::= 2325

-- end of futureUse18 Input7 trap

-- beginning of futureUse18 Input8 trap

    faultfutureUse18Input8False TRAP-TYPE
        ENTERPRISE  trapFault
        VARIABLES   { trapTag }
        DESCRIPTION
            "FutureUse18 Cleared on Input8"
    ::= 2326
    
    faultfutureUse18Input8True TRAP-TYPE
        ENTERPRISE  trapFault
        VARIABLES   { trapTag }
        DESCRIPTION
            "FutureUse18 Alert on Input8"
    ::= 2327

-- end of futureUse18 Input8 trap

-- beginning of futureUse19 Input1 trap

    faultfutureUse19Input1False TRAP-TYPE
        ENTERPRISE  trapFault
        VARIABLES   { trapTag }
        DESCRIPTION
            "FutureUse19 Cleared on Input1"
    ::= 2328
    
    faultfutureUse19Input1True TRAP-TYPE
        ENTERPRISE  trapFault
        VARIABLES   { trapTag }
        DESCRIPTION
            "FutureUse19 Alert on Input1"
    ::= 2329

-- end of futureUse19 Input1 trap

-- beginning of futureUse19 Input2 trap

    faultfutureUse19Input2False TRAP-TYPE
        ENTERPRISE  trapFault
        VARIABLES   { trapTag }
        DESCRIPTION
            "FutureUse19 Cleared on Input2"
    ::= 2330
    
    faultfutureUse19Input2True TRAP-TYPE
        ENTERPRISE  trapFault
        VARIABLES   { trapTag }
        DESCRIPTION
            "FutureUse19 Alert on Input2"
    ::= 2331

-- end of futureUse19 Input2 trap

-- beginning of futureUse19 Input3 trap

    faultfutureUse19Input3False TRAP-TYPE
        ENTERPRISE  trapFault
        VARIABLES   { trapTag }
        DESCRIPTION
            "FutureUse19 Cleared on Input3"
    ::= 2332
    
    faultfutureUse19Input3True TRAP-TYPE
        ENTERPRISE  trapFault
        VARIABLES   { trapTag }
        DESCRIPTION
            "FutureUse19 Alert on Input3"
    ::= 2333

-- end of futureUse19 Input3 trap

-- beginning of futureUse19 Input4 trap

    faultfutureUse19Input4False TRAP-TYPE
        ENTERPRISE  trapFault
        VARIABLES   { trapTag }
        DESCRIPTION
            "FutureUse19 Cleared on Input4"
    ::= 2334
    
    faultfutureUse19Input4True TRAP-TYPE
        ENTERPRISE  trapFault
        VARIABLES   { trapTag }
        DESCRIPTION
            "FutureUse19 Alert on Input4"
    ::= 2335

-- end of futureUse19 Input4 trap

-- beginning of futureUse19 Input5 trap

    faultfutureUse19Input5False TRAP-TYPE
        ENTERPRISE  trapFault
        VARIABLES   { trapTag }
        DESCRIPTION
            "FutureUse19 Cleared on Input5"
    ::= 2336
    
    faultfutureUse19Input5True TRAP-TYPE
        ENTERPRISE  trapFault
        VARIABLES   { trapTag }
        DESCRIPTION
            "FutureUse19 Alert on Input5"
    ::= 2337

-- end of futureUse19 Input5 trap

-- beginning of futureUse19 Input6 trap

    faultfutureUse19Input6False TRAP-TYPE
        ENTERPRISE  trapFault
        VARIABLES   { trapTag }
        DESCRIPTION
            "FutureUse19 Cleared on Input6"
    ::= 2338
    
    faultfutureUse19Input6True TRAP-TYPE
        ENTERPRISE  trapFault
        VARIABLES   { trapTag }
        DESCRIPTION
            "FutureUse19 Alert on Input6"
    ::= 2339

-- end of futureUse19 Input6 trap

-- beginning of futureUse19 Input7 trap

    faultfutureUse19Input7False TRAP-TYPE
        ENTERPRISE  trapFault
        VARIABLES   { trapTag }
        DESCRIPTION
            "FutureUse19 Cleared on Input7"
    ::= 2340
    
    faultfutureUse19Input7True TRAP-TYPE
        ENTERPRISE  trapFault
        VARIABLES   { trapTag }
        DESCRIPTION
            "FutureUse19 Alert on Input7"
    ::= 2341

-- end of futureUse19 Input7 trap

-- beginning of futureUse19 Input8 trap

    faultfutureUse19Input8False TRAP-TYPE
        ENTERPRISE  trapFault
        VARIABLES   { trapTag }
        DESCRIPTION
            "FutureUse19 Cleared on Input8"
    ::= 2342
    
    faultfutureUse19Input8True TRAP-TYPE
        ENTERPRISE  trapFault
        VARIABLES   { trapTag }
        DESCRIPTION
            "FutureUse19 Alert on Input8"
    ::= 2343

-- end of futureUse19 Input8 trap

-- beginning of futureUse20 Input1 trap

    faultfutureUse20Input1False TRAP-TYPE
        ENTERPRISE  trapFault
        VARIABLES   { trapTag }
        DESCRIPTION
            "FutureUse20 Cleared on Input1"
    ::= 2344
    
    faultfutureUse20Input1True TRAP-TYPE
        ENTERPRISE  trapFault
        VARIABLES   { trapTag }
        DESCRIPTION
            "FutureUse20 Alert on Input1"
    ::= 2345

-- end of futureUse20 Input1 trap

-- beginning of futureUse20 Input2 trap

    faultfutureUse20Input2False TRAP-TYPE
        ENTERPRISE  trapFault
        VARIABLES   { trapTag }
        DESCRIPTION
            "FutureUse20 Cleared on Input2"
    ::= 2346
    
    faultfutureUse20Input2True TRAP-TYPE
        ENTERPRISE  trapFault
        VARIABLES   { trapTag }
        DESCRIPTION
            "FutureUse20 Alert on Input2"
    ::= 2347

-- end of futureUse20 Input2 trap

-- beginning of futureUse20 Input3 trap

    faultfutureUse20Input3False TRAP-TYPE
        ENTERPRISE  trapFault
        VARIABLES   { trapTag }
        DESCRIPTION
            "FutureUse20 Cleared on Input3"
    ::= 2348
    
    faultfutureUse20Input3True TRAP-TYPE
        ENTERPRISE  trapFault
        VARIABLES   { trapTag }
        DESCRIPTION
            "FutureUse20 Alert on Input3"
    ::= 2349

-- end of futureUse20 Input3 trap

-- beginning of futureUse20 Input4 trap

    faultfutureUse20Input4False TRAP-TYPE
        ENTERPRISE  trapFault
        VARIABLES   { trapTag }
        DESCRIPTION
            "FutureUse20 Cleared on Input4"
    ::= 2350
    
    faultfutureUse20Input4True TRAP-TYPE
        ENTERPRISE  trapFault
        VARIABLES   { trapTag }
        DESCRIPTION
            "FutureUse20 Alert on Input4"
    ::= 2351

-- end of futureUse20 Input4 trap

-- beginning of futureUse20 Input5 trap

    faultfutureUse20Input5False TRAP-TYPE
        ENTERPRISE  trapFault
        VARIABLES   { trapTag }
        DESCRIPTION
            "FutureUse20 Cleared on Input5"
    ::= 2352
    
    faultfutureUse20Input5True TRAP-TYPE
        ENTERPRISE  trapFault
        VARIABLES   { trapTag }
        DESCRIPTION
            "FutureUse20 Alert on Input5"
    ::= 2353

-- end of futureUse20 Input5 trap

-- beginning of futureUse20 Input6 trap

    faultfutureUse20Input6False TRAP-TYPE
        ENTERPRISE  trapFault
        VARIABLES   { trapTag }
        DESCRIPTION
            "FutureUse20 Cleared on Input6"
    ::= 2354
    
    faultfutureUse20Input6True TRAP-TYPE
        ENTERPRISE  trapFault
        VARIABLES   { trapTag }
        DESCRIPTION
            "FutureUse20 Alert on Input6"
    ::= 2355

-- end of futureUse20 Input6 trap

-- beginning of futureUse20 Input7 trap

    faultfutureUse20Input7False TRAP-TYPE
        ENTERPRISE  trapFault
        VARIABLES   { trapTag }
        DESCRIPTION
            "FutureUse20 Cleared on Input7"
    ::= 2356
    
    faultfutureUse20Input7True TRAP-TYPE
        ENTERPRISE  trapFault
        VARIABLES   { trapTag }
        DESCRIPTION
            "FutureUse20 Alert on Input7"
    ::= 2357

-- end of futureUse20 Input7 trap

-- beginning of futureUse20 Input8 trap

    faultfutureUse20Input8False TRAP-TYPE
        ENTERPRISE  trapFault
        VARIABLES   { trapTag }
        DESCRIPTION
            "FutureUse20 Cleared on Input8"
    ::= 2358
    
    faultfutureUse20Input8True TRAP-TYPE
        ENTERPRISE  trapFault
        VARIABLES   { trapTag }
        DESCRIPTION
            "FutureUse20 Alert on Input8"
    ::= 2359

-- end of futureUse20 Input8 trap

-- beginning of futureUse21 Input1 trap

    faultfutureUse21Input1False TRAP-TYPE
        ENTERPRISE  trapFault
        VARIABLES   { trapTag }
        DESCRIPTION
            "FutureUse21 Cleared on Input1"
    ::= 2360
    
    faultfutureUse21Input1True TRAP-TYPE
        ENTERPRISE  trapFault
        VARIABLES   { trapTag }
        DESCRIPTION
            "FutureUse21 Alert on Input1"
    ::= 2361

-- end of futureUse21 Input1 trap

-- beginning of futureUse21 Input2 trap

    faultfutureUse21Input2False TRAP-TYPE
        ENTERPRISE  trapFault
        VARIABLES   { trapTag }
        DESCRIPTION
            "FutureUse21 Cleared on Input2"
    ::= 2362
    
    faultfutureUse21Input2True TRAP-TYPE
        ENTERPRISE  trapFault
        VARIABLES   { trapTag }
        DESCRIPTION
            "FutureUse21 Alert on Input2"
    ::= 2363

-- end of futureUse21 Input2 trap

-- beginning of futureUse21 Input3 trap

    faultfutureUse21Input3False TRAP-TYPE
        ENTERPRISE  trapFault
        VARIABLES   { trapTag }
        DESCRIPTION
            "FutureUse21 Cleared on Input3"
    ::= 2364
    
    faultfutureUse21Input3True TRAP-TYPE
        ENTERPRISE  trapFault
        VARIABLES   { trapTag }
        DESCRIPTION
            "FutureUse21 Alert on Input3"
    ::= 2365

-- end of futureUse21 Input3 trap

-- beginning of futureUse21 Input4 trap

    faultfutureUse21Input4False TRAP-TYPE
        ENTERPRISE  trapFault
        VARIABLES   { trapTag }
        DESCRIPTION
            "FutureUse21 Cleared on Input4"
    ::= 2366
    
    faultfutureUse21Input4True TRAP-TYPE
        ENTERPRISE  trapFault
        VARIABLES   { trapTag }
        DESCRIPTION
            "FutureUse21 Alert on Input4"
    ::= 2367

-- end of futureUse21 Input4 trap

-- beginning of futureUse21 Input5 trap

    faultfutureUse21Input5False TRAP-TYPE
        ENTERPRISE  trapFault
        VARIABLES   { trapTag }
        DESCRIPTION
            "FutureUse21 Cleared on Input5"
    ::= 2368
    
    faultfutureUse21Input5True TRAP-TYPE
        ENTERPRISE  trapFault
        VARIABLES   { trapTag }
        DESCRIPTION
            "FutureUse21 Alert on Input5"
    ::= 2369

-- end of futureUse21 Input5 trap

-- beginning of futureUse21 Input6 trap

    faultfutureUse21Input6False TRAP-TYPE
        ENTERPRISE  trapFault
        VARIABLES   { trapTag }
        DESCRIPTION
            "FutureUse21 Cleared on Input6"
    ::= 2370
    
    faultfutureUse21Input6True TRAP-TYPE
        ENTERPRISE  trapFault
        VARIABLES   { trapTag }
        DESCRIPTION
            "FutureUse21 Alert on Input6"
    ::= 2371

-- end of futureUse21 Input6 trap

-- beginning of futureUse21 Input7 trap

    faultfutureUse21Input7False TRAP-TYPE
        ENTERPRISE  trapFault
        VARIABLES   { trapTag }
        DESCRIPTION
            "FutureUse21 Cleared on Input7"
    ::= 2372
    
    faultfutureUse21Input7True TRAP-TYPE
        ENTERPRISE  trapFault
        VARIABLES   { trapTag }
        DESCRIPTION
            "FutureUse21 Alert on Input7"
    ::= 2373

-- end of futureUse21 Input7 trap

-- beginning of futureUse21 Input8 trap

    faultfutureUse21Input8False TRAP-TYPE
        ENTERPRISE  trapFault
        VARIABLES   { trapTag }
        DESCRIPTION
            "FutureUse21 Cleared on Input8"
    ::= 2374
    
    faultfutureUse21Input8True TRAP-TYPE
        ENTERPRISE  trapFault
        VARIABLES   { trapTag }
        DESCRIPTION
            "FutureUse21 Alert on Input8"
    ::= 2375

-- end of futureUse21 Input8 trap

-- beginning of futureUse22 Input1 trap

    faultfutureUse22Input1False TRAP-TYPE
        ENTERPRISE  trapFault
        VARIABLES   { trapTag }
        DESCRIPTION
            "FutureUse22 Cleared on Input1"
    ::= 2376
    
    faultfutureUse22Input1True TRAP-TYPE
        ENTERPRISE  trapFault
        VARIABLES   { trapTag }
        DESCRIPTION
            "FutureUse22 Alert on Input1"
    ::= 2377

-- end of futureUse22 Input1 trap

-- beginning of futureUse22 Input2 trap

    faultfutureUse22Input2False TRAP-TYPE
        ENTERPRISE  trapFault
        VARIABLES   { trapTag }
        DESCRIPTION
            "FutureUse22 Cleared on Input2"
    ::= 2378
    
    faultfutureUse22Input2True TRAP-TYPE
        ENTERPRISE  trapFault
        VARIABLES   { trapTag }
        DESCRIPTION
            "FutureUse22 Alert on Input2"
    ::= 2379

-- end of futureUse22 Input2 trap

-- beginning of futureUse22 Input3 trap

    faultfutureUse22Input3False TRAP-TYPE
        ENTERPRISE  trapFault
        VARIABLES   { trapTag }
        DESCRIPTION
            "FutureUse22 Cleared on Input3"
    ::= 2380
    
    faultfutureUse22Input3True TRAP-TYPE
        ENTERPRISE  trapFault
        VARIABLES   { trapTag }
        DESCRIPTION
            "FutureUse22 Alert on Input3"
    ::= 2381

-- end of futureUse22 Input3 trap

-- beginning of futureUse22 Input4 trap

    faultfutureUse22Input4False TRAP-TYPE
        ENTERPRISE  trapFault
        VARIABLES   { trapTag }
        DESCRIPTION
            "FutureUse22 Cleared on Input4"
    ::= 2382
    
    faultfutureUse22Input4True TRAP-TYPE
        ENTERPRISE  trapFault
        VARIABLES   { trapTag }
        DESCRIPTION
            "FutureUse22 Alert on Input4"
    ::= 2383

-- end of futureUse22 Input4 trap

-- beginning of futureUse22 Input5 trap

    faultfutureUse22Input5False TRAP-TYPE
        ENTERPRISE  trapFault
        VARIABLES   { trapTag }
        DESCRIPTION
            "FutureUse22 Cleared on Input5"
    ::= 2384
    
    faultfutureUse22Input5True TRAP-TYPE
        ENTERPRISE  trapFault
        VARIABLES   { trapTag }
        DESCRIPTION
            "FutureUse22 Alert on Input5"
    ::= 2385

-- end of futureUse22 Input5 trap

-- beginning of futureUse22 Input6 trap

    faultfutureUse22Input6False TRAP-TYPE
        ENTERPRISE  trapFault
        VARIABLES   { trapTag }
        DESCRIPTION
            "FutureUse22 Cleared on Input6"
    ::= 2386
    
    faultfutureUse22Input6True TRAP-TYPE
        ENTERPRISE  trapFault
        VARIABLES   { trapTag }
        DESCRIPTION
            "FutureUse22 Alert on Input6"
    ::= 2387

-- end of futureUse22 Input6 trap

-- beginning of futureUse22 Input7 trap

    faultfutureUse22Input7False TRAP-TYPE
        ENTERPRISE  trapFault
        VARIABLES   { trapTag }
        DESCRIPTION
            "FutureUse22 Cleared on Input7"
    ::= 2388
    
    faultfutureUse22Input7True TRAP-TYPE
        ENTERPRISE  trapFault
        VARIABLES   { trapTag }
        DESCRIPTION
            "FutureUse22 Alert on Input7"
    ::= 2389

-- end of futureUse22 Input7 trap

-- beginning of futureUse22 Input8 trap

    faultfutureUse22Input8False TRAP-TYPE
        ENTERPRISE  trapFault
        VARIABLES   { trapTag }
        DESCRIPTION
            "FutureUse22 Cleared on Input8"
    ::= 2390
    
    faultfutureUse22Input8True TRAP-TYPE
        ENTERPRISE  trapFault
        VARIABLES   { trapTag }
        DESCRIPTION
            "FutureUse22 Alert on Input8"
    ::= 2391

-- end of futureUse22 Input8 trap

-- beginning of futureUse23 Input1 trap

    faultfutureUse23Input1False TRAP-TYPE
        ENTERPRISE  trapFault
        VARIABLES   { trapTag }
        DESCRIPTION
            "FutureUse23 Cleared on Input1"
    ::= 2392
    
    faultfutureUse23Input1True TRAP-TYPE
        ENTERPRISE  trapFault
        VARIABLES   { trapTag }
        DESCRIPTION
            "FutureUse23 Alert on Input1"
    ::= 2393

-- end of futureUse23 Input1 trap

-- beginning of futureUse23 Input2 trap

    faultfutureUse23Input2False TRAP-TYPE
        ENTERPRISE  trapFault
        VARIABLES   { trapTag }
        DESCRIPTION
            "FutureUse23 Cleared on Input2"
    ::= 2394
    
    faultfutureUse23Input2True TRAP-TYPE
        ENTERPRISE  trapFault
        VARIABLES   { trapTag }
        DESCRIPTION
            "FutureUse23 Alert on Input2"
    ::= 2395

-- end of futureUse23 Input2 trap

-- beginning of futureUse23 Input3 trap

    faultfutureUse23Input3False TRAP-TYPE
        ENTERPRISE  trapFault
        VARIABLES   { trapTag }
        DESCRIPTION
            "FutureUse23 Cleared on Input3"
    ::= 2396
    
    faultfutureUse23Input3True TRAP-TYPE
        ENTERPRISE  trapFault
        VARIABLES   { trapTag }
        DESCRIPTION
            "FutureUse23 Alert on Input3"
    ::= 2397

-- end of futureUse23 Input3 trap

-- beginning of futureUse23 Input4 trap

    faultfutureUse23Input4False TRAP-TYPE
        ENTERPRISE  trapFault
        VARIABLES   { trapTag }
        DESCRIPTION
            "FutureUse23 Cleared on Input4"
    ::= 2398
    
    faultfutureUse23Input4True TRAP-TYPE
        ENTERPRISE  trapFault
        VARIABLES   { trapTag }
        DESCRIPTION
            "FutureUse23 Alert on Input4"
    ::= 2399

-- end of futureUse23 Input4 trap

-- beginning of futureUse23 Input5 trap

    faultfutureUse23Input5False TRAP-TYPE
        ENTERPRISE  trapFault
        VARIABLES   { trapTag }
        DESCRIPTION
            "FutureUse23 Cleared on Input5"
    ::= 2400
    
    faultfutureUse23Input5True TRAP-TYPE
        ENTERPRISE  trapFault
        VARIABLES   { trapTag }
        DESCRIPTION
            "FutureUse23 Alert on Input5"
    ::= 2401

-- end of futureUse23 Input5 trap

-- beginning of futureUse23 Input6 trap

    faultfutureUse23Input6False TRAP-TYPE
        ENTERPRISE  trapFault
        VARIABLES   { trapTag }
        DESCRIPTION
            "FutureUse23 Cleared on Input6"
    ::= 2402
    
    faultfutureUse23Input6True TRAP-TYPE
        ENTERPRISE  trapFault
        VARIABLES   { trapTag }
        DESCRIPTION
            "FutureUse23 Alert on Input6"
    ::= 2403

-- end of futureUse23 Input6 trap

-- beginning of futureUse23 Input7 trap

    faultfutureUse23Input7False TRAP-TYPE
        ENTERPRISE  trapFault
        VARIABLES   { trapTag }
        DESCRIPTION
            "FutureUse23 Cleared on Input7"
    ::= 2404
    
    faultfutureUse23Input7True TRAP-TYPE
        ENTERPRISE  trapFault
        VARIABLES   { trapTag }
        DESCRIPTION
            "FutureUse23 Alert on Input7"
    ::= 2405

-- end of futureUse23 Input7 trap

-- beginning of futureUse23 Input8 trap

    faultfutureUse23Input8False TRAP-TYPE
        ENTERPRISE  trapFault
        VARIABLES   { trapTag }
        DESCRIPTION
            "FutureUse23 Cleared on Input8"
    ::= 2406
    
    faultfutureUse23Input8True TRAP-TYPE
        ENTERPRISE  trapFault
        VARIABLES   { trapTag }
        DESCRIPTION
            "FutureUse23 Alert on Input8"
    ::= 2407

-- end of futureUse23 Input8 trap

-- beginning of futureUse24 Input1 trap

    faultfutureUse24Input1False TRAP-TYPE
        ENTERPRISE  trapFault
        VARIABLES   { trapTag }
        DESCRIPTION
            "FutureUse24 Cleared on Input1"
    ::= 2408
    
    faultfutureUse24Input1True TRAP-TYPE
        ENTERPRISE  trapFault
        VARIABLES   { trapTag }
        DESCRIPTION
            "FutureUse24 Alert on Input1"
    ::= 2409

-- end of futureUse24 Input1 trap

-- beginning of futureUse24 Input2 trap

    faultfutureUse24Input2False TRAP-TYPE
        ENTERPRISE  trapFault
        VARIABLES   { trapTag }
        DESCRIPTION
            "FutureUse24 Cleared on Input2"
    ::= 2410
    
    faultfutureUse24Input2True TRAP-TYPE
        ENTERPRISE  trapFault
        VARIABLES   { trapTag }
        DESCRIPTION
            "FutureUse24 Alert on Input2"
    ::= 2411

-- end of futureUse24 Input2 trap

-- beginning of futureUse24 Input3 trap

    faultfutureUse24Input3False TRAP-TYPE
        ENTERPRISE  trapFault
        VARIABLES   { trapTag }
        DESCRIPTION
            "FutureUse24 Cleared on Input3"
    ::= 2412
    
    faultfutureUse24Input3True TRAP-TYPE
        ENTERPRISE  trapFault
        VARIABLES   { trapTag }
        DESCRIPTION
            "FutureUse24 Alert on Input3"
    ::= 2413

-- end of futureUse24 Input3 trap

-- beginning of futureUse24 Input4 trap

    faultfutureUse24Input4False TRAP-TYPE
        ENTERPRISE  trapFault
        VARIABLES   { trapTag }
        DESCRIPTION
            "FutureUse24 Cleared on Input4"
    ::= 2414
    
    faultfutureUse24Input4True TRAP-TYPE
        ENTERPRISE  trapFault
        VARIABLES   { trapTag }
        DESCRIPTION
            "FutureUse24 Alert on Input4"
    ::= 2415

-- end of futureUse24 Input4 trap

-- beginning of futureUse24 Input5 trap

    faultfutureUse24Input5False TRAP-TYPE
        ENTERPRISE  trapFault
        VARIABLES   { trapTag }
        DESCRIPTION
            "FutureUse24 Cleared on Input5"
    ::= 2416
    
    faultfutureUse24Input5True TRAP-TYPE
        ENTERPRISE  trapFault
        VARIABLES   { trapTag }
        DESCRIPTION
            "FutureUse24 Alert on Input5"
    ::= 2417

-- end of futureUse24 Input5 trap

-- beginning of futureUse24 Input6 trap

    faultfutureUse24Input6False TRAP-TYPE
        ENTERPRISE  trapFault
        VARIABLES   { trapTag }
        DESCRIPTION
            "FutureUse24 Cleared on Input6"
    ::= 2418
    
    faultfutureUse24Input6True TRAP-TYPE
        ENTERPRISE  trapFault
        VARIABLES   { trapTag }
        DESCRIPTION
            "FutureUse24 Alert on Input6"
    ::= 2419

-- end of futureUse24 Input6 trap

-- beginning of futureUse24 Input7 trap

    faultfutureUse24Input7False TRAP-TYPE
        ENTERPRISE  trapFault
        VARIABLES   { trapTag }
        DESCRIPTION
            "FutureUse24 Cleared on Input7"
    ::= 2420
    
    faultfutureUse24Input7True TRAP-TYPE
        ENTERPRISE  trapFault
        VARIABLES   { trapTag }
        DESCRIPTION
            "FutureUse24 Alert on Input7"
    ::= 2421

-- end of futureUse24 Input7 trap

-- beginning of futureUse24 Input8 trap

    faultfutureUse24Input8False TRAP-TYPE
        ENTERPRISE  trapFault
        VARIABLES   { trapTag }
        DESCRIPTION
            "FutureUse24 Cleared on Input8"
    ::= 2422
    
    faultfutureUse24Input8True TRAP-TYPE
        ENTERPRISE  trapFault
        VARIABLES   { trapTag }
        DESCRIPTION
            "FutureUse24 Alert on Input8"
    ::= 2423

-- end of futureUse24 Input8 trap

-- beginning of futureUse25 Input1 trap

    faultfutureUse25Input1False TRAP-TYPE
        ENTERPRISE  trapFault
        VARIABLES   { trapTag }
        DESCRIPTION
            "FutureUse25 Cleared on Input1"
    ::= 2424
    
    faultfutureUse25Input1True TRAP-TYPE
        ENTERPRISE  trapFault
        VARIABLES   { trapTag }
        DESCRIPTION
            "FutureUse25 Alert on Input1"
    ::= 2425

-- end of futureUse25 Input1 trap

-- beginning of futureUse25 Input2 trap

    faultfutureUse25Input2False TRAP-TYPE
        ENTERPRISE  trapFault
        VARIABLES   { trapTag }
        DESCRIPTION
            "FutureUse25 Cleared on Input2"
    ::= 2426
    
    faultfutureUse25Input2True TRAP-TYPE
        ENTERPRISE  trapFault
        VARIABLES   { trapTag }
        DESCRIPTION
            "FutureUse25 Alert on Input2"
    ::= 2427

-- end of futureUse25 Input2 trap

-- beginning of futureUse25 Input3 trap

    faultfutureUse25Input3False TRAP-TYPE
        ENTERPRISE  trapFault
        VARIABLES   { trapTag }
        DESCRIPTION
            "FutureUse25 Cleared on Input3"
    ::= 2428
    
    faultfutureUse25Input3True TRAP-TYPE
        ENTERPRISE  trapFault
        VARIABLES   { trapTag }
        DESCRIPTION
            "FutureUse25 Alert on Input3"
    ::= 2429

-- end of futureUse25 Input3 trap

-- beginning of futureUse25 Input4 trap

    faultfutureUse25Input4False TRAP-TYPE
        ENTERPRISE  trapFault
        VARIABLES   { trapTag }
        DESCRIPTION
            "FutureUse25 Cleared on Input4"
    ::= 2430
    
    faultfutureUse25Input4True TRAP-TYPE
        ENTERPRISE  trapFault
        VARIABLES   { trapTag }
        DESCRIPTION
            "FutureUse25 Alert on Input4"
    ::= 2431

-- end of futureUse25 Input4 trap

-- beginning of futureUse25 Input5 trap

    faultfutureUse25Input5False TRAP-TYPE
        ENTERPRISE  trapFault
        VARIABLES   { trapTag }
        DESCRIPTION
            "FutureUse25 Cleared on Input5"
    ::= 2432
    
    faultfutureUse25Input5True TRAP-TYPE
        ENTERPRISE  trapFault
        VARIABLES   { trapTag }
        DESCRIPTION
            "FutureUse25 Alert on Input5"
    ::= 2433

-- end of futureUse25 Input5 trap

-- beginning of futureUse25 Input6 trap

    faultfutureUse25Input6False TRAP-TYPE
        ENTERPRISE  trapFault
        VARIABLES   { trapTag }
        DESCRIPTION
            "FutureUse25 Cleared on Input6"
    ::= 2434
    
    faultfutureUse25Input6True TRAP-TYPE
        ENTERPRISE  trapFault
        VARIABLES   { trapTag }
        DESCRIPTION
            "FutureUse25 Alert on Input6"
    ::= 2435

-- end of futureUse25 Input6 trap

-- beginning of futureUse25 Input7 trap

    faultfutureUse25Input7False TRAP-TYPE
        ENTERPRISE  trapFault
        VARIABLES   { trapTag }
        DESCRIPTION
            "FutureUse25 Cleared on Input7"
    ::= 2436
    
    faultfutureUse25Input7True TRAP-TYPE
        ENTERPRISE  trapFault
        VARIABLES   { trapTag }
        DESCRIPTION
            "FutureUse25 Alert on Input7"
    ::= 2437

-- end of futureUse25 Input7 trap

-- beginning of futureUse25 Input8 trap

    faultfutureUse25Input8False TRAP-TYPE
        ENTERPRISE  trapFault
        VARIABLES   { trapTag }
        DESCRIPTION
            "FutureUse25 Cleared on Input8"
    ::= 2438
    
    faultfutureUse25Input8True TRAP-TYPE
        ENTERPRISE  trapFault
        VARIABLES   { trapTag }
        DESCRIPTION
            "FutureUse25 Alert on Input8"
    ::= 2439

-- end of futureUse25 Input8 trap

-- beginning of futureUse26 Input1 trap

    faultfutureUse26Input1False TRAP-TYPE
        ENTERPRISE  trapFault
        VARIABLES   { trapTag }
        DESCRIPTION
            "FutureUse26 Cleared on Input1"
    ::= 2440
    
    faultfutureUse26Input1True TRAP-TYPE
        ENTERPRISE  trapFault
        VARIABLES   { trapTag }
        DESCRIPTION
            "FutureUse26 Alert on Input1"
    ::= 2441

-- end of futureUse26 Input1 trap

-- beginning of futureUse26 Input2 trap

    faultfutureUse26Input2False TRAP-TYPE
        ENTERPRISE  trapFault
        VARIABLES   { trapTag }
        DESCRIPTION
            "FutureUse26 Cleared on Input2"
    ::= 2442
    
    faultfutureUse26Input2True TRAP-TYPE
        ENTERPRISE  trapFault
        VARIABLES   { trapTag }
        DESCRIPTION
            "FutureUse26 Alert on Input2"
    ::= 2443

-- end of futureUse26 Input2 trap

-- beginning of futureUse26 Input3 trap

    faultfutureUse26Input3False TRAP-TYPE
        ENTERPRISE  trapFault
        VARIABLES   { trapTag }
        DESCRIPTION
            "FutureUse26 Cleared on Input3"
    ::= 2444
    
    faultfutureUse26Input3True TRAP-TYPE
        ENTERPRISE  trapFault
        VARIABLES   { trapTag }
        DESCRIPTION
            "FutureUse26 Alert on Input3"
    ::= 2445

-- end of futureUse26 Input3 trap

-- beginning of futureUse26 Input4 trap

    faultfutureUse26Input4False TRAP-TYPE
        ENTERPRISE  trapFault
        VARIABLES   { trapTag }
        DESCRIPTION
            "FutureUse26 Cleared on Input4"
    ::= 2446
    
    faultfutureUse26Input4True TRAP-TYPE
        ENTERPRISE  trapFault
        VARIABLES   { trapTag }
        DESCRIPTION
            "FutureUse26 Alert on Input4"
    ::= 2447

-- end of futureUse26 Input4 trap

-- beginning of futureUse26 Input5 trap

    faultfutureUse26Input5False TRAP-TYPE
        ENTERPRISE  trapFault
        VARIABLES   { trapTag }
        DESCRIPTION
            "FutureUse26 Cleared on Input5"
    ::= 2448
    
    faultfutureUse26Input5True TRAP-TYPE
        ENTERPRISE  trapFault
        VARIABLES   { trapTag }
        DESCRIPTION
            "FutureUse26 Alert on Input5"
    ::= 2449

-- end of futureUse26 Input5 trap

-- beginning of futureUse26 Input6 trap

    faultfutureUse26Input6False TRAP-TYPE
        ENTERPRISE  trapFault
        VARIABLES   { trapTag }
        DESCRIPTION
            "FutureUse26 Cleared on Input6"
    ::= 2450
    
    faultfutureUse26Input6True TRAP-TYPE
        ENTERPRISE  trapFault
        VARIABLES   { trapTag }
        DESCRIPTION
            "FutureUse26 Alert on Input6"
    ::= 2451

-- end of futureUse26 Input6 trap

-- beginning of futureUse26 Input7 trap

    faultfutureUse26Input7False TRAP-TYPE
        ENTERPRISE  trapFault
        VARIABLES   { trapTag }
        DESCRIPTION
            "FutureUse26 Cleared on Input7"
    ::= 2452
    
    faultfutureUse26Input7True TRAP-TYPE
        ENTERPRISE  trapFault
        VARIABLES   { trapTag }
        DESCRIPTION
            "FutureUse26 Alert on Input7"
    ::= 2453

-- end of futureUse26 Input7 trap

-- beginning of futureUse26 Input8 trap

    faultfutureUse26Input8False TRAP-TYPE
        ENTERPRISE  trapFault
        VARIABLES   { trapTag }
        DESCRIPTION
            "FutureUse26 Cleared on Input8"
    ::= 2454
    
    faultfutureUse26Input8True TRAP-TYPE
        ENTERPRISE  trapFault
        VARIABLES   { trapTag }
        DESCRIPTION
            "FutureUse26 Alert on Input8"
    ::= 2455

-- end of futureUse26 Input8 trap

-- beginning of futureUse27 Input1 trap

    faultfutureUse27Input1False TRAP-TYPE
        ENTERPRISE  trapFault
        VARIABLES   { trapTag }
        DESCRIPTION
            "FutureUse27 Cleared on Input1"
    ::= 2456
    
    faultfutureUse27Input1True TRAP-TYPE
        ENTERPRISE  trapFault
        VARIABLES   { trapTag }
        DESCRIPTION
            "FutureUse27 Alert on Input1"
    ::= 2457

-- end of futureUse27 Input1 trap

-- beginning of futureUse27 Input2 trap

    faultfutureUse27Input2False TRAP-TYPE
        ENTERPRISE  trapFault
        VARIABLES   { trapTag }
        DESCRIPTION
            "FutureUse27 Cleared on Input2"
    ::= 2458
    
    faultfutureUse27Input2True TRAP-TYPE
        ENTERPRISE  trapFault
        VARIABLES   { trapTag }
        DESCRIPTION
            "FutureUse27 Alert on Input2"
    ::= 2459

-- end of futureUse27 Input2 trap

-- beginning of futureUse27 Input3 trap

    faultfutureUse27Input3False TRAP-TYPE
        ENTERPRISE  trapFault
        VARIABLES   { trapTag }
        DESCRIPTION
            "FutureUse27 Cleared on Input3"
    ::= 2460
    
    faultfutureUse27Input3True TRAP-TYPE
        ENTERPRISE  trapFault
        VARIABLES   { trapTag }
        DESCRIPTION
            "FutureUse27 Alert on Input3"
    ::= 2461

-- end of futureUse27 Input3 trap

-- beginning of futureUse27 Input4 trap

    faultfutureUse27Input4False TRAP-TYPE
        ENTERPRISE  trapFault
        VARIABLES   { trapTag }
        DESCRIPTION
            "FutureUse27 Cleared on Input4"
    ::= 2462
    
    faultfutureUse27Input4True TRAP-TYPE
        ENTERPRISE  trapFault
        VARIABLES   { trapTag }
        DESCRIPTION
            "FutureUse27 Alert on Input4"
    ::= 2463

-- end of futureUse27 Input4 trap

-- beginning of futureUse27 Input5 trap

    faultfutureUse27Input5False TRAP-TYPE
        ENTERPRISE  trapFault
        VARIABLES   { trapTag }
        DESCRIPTION
            "FutureUse27 Cleared on Input5"
    ::= 2464
    
    faultfutureUse27Input5True TRAP-TYPE
        ENTERPRISE  trapFault
        VARIABLES   { trapTag }
        DESCRIPTION
            "FutureUse27 Alert on Input5"
    ::= 2465

-- end of futureUse27 Input5 trap

-- beginning of futureUse27 Input6 trap

    faultfutureUse27Input6False TRAP-TYPE
        ENTERPRISE  trapFault
        VARIABLES   { trapTag }
        DESCRIPTION
            "FutureUse27 Cleared on Input6"
    ::= 2466
    
    faultfutureUse27Input6True TRAP-TYPE
        ENTERPRISE  trapFault
        VARIABLES   { trapTag }
        DESCRIPTION
            "FutureUse27 Alert on Input6"
    ::= 2467

-- end of futureUse27 Input6 trap

-- beginning of futureUse27 Input7 trap

    faultfutureUse27Input7False TRAP-TYPE
        ENTERPRISE  trapFault
        VARIABLES   { trapTag }
        DESCRIPTION
            "FutureUse27 Cleared on Input7"
    ::= 2468
    
    faultfutureUse27Input7True TRAP-TYPE
        ENTERPRISE  trapFault
        VARIABLES   { trapTag }
        DESCRIPTION
            "FutureUse27 Alert on Input7"
    ::= 2469

-- end of futureUse27 Input7 trap

-- beginning of futureUse27 Input8 trap

    faultfutureUse27Input8False TRAP-TYPE
        ENTERPRISE  trapFault
        VARIABLES   { trapTag }
        DESCRIPTION
            "FutureUse27 Cleared on Input8"
    ::= 2470
    
    faultfutureUse27Input8True TRAP-TYPE
        ENTERPRISE  trapFault
        VARIABLES   { trapTag }
        DESCRIPTION
            "FutureUse27 Alert on Input8"
    ::= 2471

-- end of futureUse27 Input8 trap

-- beginning of futureUse28 Input1 trap

    faultfutureUse28Input1False TRAP-TYPE
        ENTERPRISE  trapFault
        VARIABLES   { trapTag }
        DESCRIPTION
            "FutureUse28 Cleared on Input1"
    ::= 2472
    
    faultfutureUse28Input1True TRAP-TYPE
        ENTERPRISE  trapFault
        VARIABLES   { trapTag }
        DESCRIPTION
            "FutureUse28 Alert on Input1"
    ::= 2473

-- end of futureUse28 Input1 trap

-- beginning of futureUse28 Input2 trap

    faultfutureUse28Input2False TRAP-TYPE
        ENTERPRISE  trapFault
        VARIABLES   { trapTag }
        DESCRIPTION
            "FutureUse28 Cleared on Input2"
    ::= 2474
    
    faultfutureUse28Input2True TRAP-TYPE
        ENTERPRISE  trapFault
        VARIABLES   { trapTag }
        DESCRIPTION
            "FutureUse28 Alert on Input2"
    ::= 2475

-- end of futureUse28 Input2 trap

-- beginning of futureUse28 Input3 trap

    faultfutureUse28Input3False TRAP-TYPE
        ENTERPRISE  trapFault
        VARIABLES   { trapTag }
        DESCRIPTION
            "FutureUse28 Cleared on Input3"
    ::= 2476
    
    faultfutureUse28Input3True TRAP-TYPE
        ENTERPRISE  trapFault
        VARIABLES   { trapTag }
        DESCRIPTION
            "FutureUse28 Alert on Input3"
    ::= 2477

-- end of futureUse28 Input3 trap

-- beginning of futureUse28 Input4 trap

    faultfutureUse28Input4False TRAP-TYPE
        ENTERPRISE  trapFault
        VARIABLES   { trapTag }
        DESCRIPTION
            "FutureUse28 Cleared on Input4"
    ::= 2478
    
    faultfutureUse28Input4True TRAP-TYPE
        ENTERPRISE  trapFault
        VARIABLES   { trapTag }
        DESCRIPTION
            "FutureUse28 Alert on Input4"
    ::= 2479

-- end of futureUse28 Input4 trap

-- beginning of futureUse28 Input5 trap

    faultfutureUse28Input5False TRAP-TYPE
        ENTERPRISE  trapFault
        VARIABLES   { trapTag }
        DESCRIPTION
            "FutureUse28 Cleared on Input5"
    ::= 2480
    
    faultfutureUse28Input5True TRAP-TYPE
        ENTERPRISE  trapFault
        VARIABLES   { trapTag }
        DESCRIPTION
            "FutureUse28 Alert on Input5"
    ::= 2481

-- end of futureUse28 Input5 trap

-- beginning of futureUse28 Input6 trap

    faultfutureUse28Input6False TRAP-TYPE
        ENTERPRISE  trapFault
        VARIABLES   { trapTag }
        DESCRIPTION
            "FutureUse28 Cleared on Input6"
    ::= 2482
    
    faultfutureUse28Input6True TRAP-TYPE
        ENTERPRISE  trapFault
        VARIABLES   { trapTag }
        DESCRIPTION
            "FutureUse28 Alert on Input6"
    ::= 2483

-- end of futureUse28 Input6 trap

-- beginning of futureUse28 Input7 trap

    faultfutureUse28Input7False TRAP-TYPE
        ENTERPRISE  trapFault
        VARIABLES   { trapTag }
        DESCRIPTION
            "FutureUse28 Cleared on Input7"
    ::= 2484
    
    faultfutureUse28Input7True TRAP-TYPE
        ENTERPRISE  trapFault
        VARIABLES   { trapTag }
        DESCRIPTION
            "FutureUse28 Alert on Input7"
    ::= 2485

-- end of futureUse28 Input7 trap

-- beginning of futureUse28 Input8 trap

    faultfutureUse28Input8False TRAP-TYPE
        ENTERPRISE  trapFault
        VARIABLES   { trapTag }
        DESCRIPTION
            "FutureUse28 Cleared on Input8"
    ::= 2486
    
    faultfutureUse28Input8True TRAP-TYPE
        ENTERPRISE  trapFault
        VARIABLES   { trapTag }
        DESCRIPTION
            "FutureUse28 Alert on Input8"
    ::= 2487

-- end of futureUse28 Input8 trap

-- beginning of futureUse29 Input1 trap

    faultfutureUse29Input1False TRAP-TYPE
        ENTERPRISE  trapFault
        VARIABLES   { trapTag }
        DESCRIPTION
            "FutureUse29 Cleared on Input1"
    ::= 2488
    
    faultfutureUse29Input1True TRAP-TYPE
        ENTERPRISE  trapFault
        VARIABLES   { trapTag }
        DESCRIPTION
            "FutureUse29 Alert on Input1"
    ::= 2489

-- end of futureUse29 Input1 trap

-- beginning of futureUse29 Input2 trap

    faultfutureUse29Input2False TRAP-TYPE
        ENTERPRISE  trapFault
        VARIABLES   { trapTag }
        DESCRIPTION
            "FutureUse29 Cleared on Input2"
    ::= 2490
    
    faultfutureUse29Input2True TRAP-TYPE
        ENTERPRISE  trapFault
        VARIABLES   { trapTag }
        DESCRIPTION
            "FutureUse29 Alert on Input2"
    ::= 2491

-- end of futureUse29 Input2 trap

-- beginning of futureUse29 Input3 trap

    faultfutureUse29Input3False TRAP-TYPE
        ENTERPRISE  trapFault
        VARIABLES   { trapTag }
        DESCRIPTION
            "FutureUse29 Cleared on Input3"
    ::= 2492
    
    faultfutureUse29Input3True TRAP-TYPE
        ENTERPRISE  trapFault
        VARIABLES   { trapTag }
        DESCRIPTION
            "FutureUse29 Alert on Input3"
    ::= 2493

-- end of futureUse29 Input3 trap

-- beginning of futureUse29 Input4 trap

    faultfutureUse29Input4False TRAP-TYPE
        ENTERPRISE  trapFault
        VARIABLES   { trapTag }
        DESCRIPTION
            "FutureUse29 Cleared on Input4"
    ::= 2494
    
    faultfutureUse29Input4True TRAP-TYPE
        ENTERPRISE  trapFault
        VARIABLES   { trapTag }
        DESCRIPTION
            "FutureUse29 Alert on Input4"
    ::= 2495

-- end of futureUse29 Input4 trap

-- beginning of futureUse29 Input5 trap

    faultfutureUse29Input5False TRAP-TYPE
        ENTERPRISE  trapFault
        VARIABLES   { trapTag }
        DESCRIPTION
            "FutureUse29 Cleared on Input5"
    ::= 2496
    
    faultfutureUse29Input5True TRAP-TYPE
        ENTERPRISE  trapFault
        VARIABLES   { trapTag }
        DESCRIPTION
            "FutureUse29 Alert on Input5"
    ::= 2497

-- end of futureUse29 Input5 trap

-- beginning of futureUse29 Input6 trap

    faultfutureUse29Input6False TRAP-TYPE
        ENTERPRISE  trapFault
        VARIABLES   { trapTag }
        DESCRIPTION
            "FutureUse29 Cleared on Input6"
    ::= 2498
    
    faultfutureUse29Input6True TRAP-TYPE
        ENTERPRISE  trapFault
        VARIABLES   { trapTag }
        DESCRIPTION
            "FutureUse29 Alert on Input6"
    ::= 2499

-- end of futureUse29 Input6 trap

-- beginning of futureUse29 Input7 trap

    faultfutureUse29Input7False TRAP-TYPE
        ENTERPRISE  trapFault
        VARIABLES   { trapTag }
        DESCRIPTION
            "FutureUse29 Cleared on Input7"
    ::= 2500
    
    faultfutureUse29Input7True TRAP-TYPE
        ENTERPRISE  trapFault
        VARIABLES   { trapTag }
        DESCRIPTION
            "FutureUse29 Alert on Input7"
    ::= 2501

-- end of futureUse29 Input7 trap

-- beginning of futureUse29 Input8 trap

    faultfutureUse29Input8False TRAP-TYPE
        ENTERPRISE  trapFault
        VARIABLES   { trapTag }
        DESCRIPTION
            "FutureUse29 Cleared on Input8"
    ::= 2502
    
    faultfutureUse29Input8True TRAP-TYPE
        ENTERPRISE  trapFault
        VARIABLES   { trapTag }
        DESCRIPTION
            "FutureUse29 Alert on Input8"
    ::= 2503

-- end of futureUse29 Input8 trap

-- beginning of futureUse30 Input1 trap

    faultfutureUse30Input1False TRAP-TYPE
        ENTERPRISE  trapFault
        VARIABLES   { trapTag }
        DESCRIPTION
            "FutureUse30 Cleared on Input1"
    ::= 2504
    
    faultfutureUse30Input1True TRAP-TYPE
        ENTERPRISE  trapFault
        VARIABLES   { trapTag }
        DESCRIPTION
            "FutureUse30 Alert on Input1"
    ::= 2505

-- end of futureUse30 Input1 trap

-- beginning of futureUse30 Input2 trap

    faultfutureUse30Input2False TRAP-TYPE
        ENTERPRISE  trapFault
        VARIABLES   { trapTag }
        DESCRIPTION
            "FutureUse30 Cleared on Input2"
    ::= 2506
    
    faultfutureUse30Input2True TRAP-TYPE
        ENTERPRISE  trapFault
        VARIABLES   { trapTag }
        DESCRIPTION
            "FutureUse30 Alert on Input2"
    ::= 2507

-- end of futureUse30 Input2 trap

-- beginning of futureUse30 Input3 trap

    faultfutureUse30Input3False TRAP-TYPE
        ENTERPRISE  trapFault
        VARIABLES   { trapTag }
        DESCRIPTION
            "FutureUse30 Cleared on Input3"
    ::= 2508
    
    faultfutureUse30Input3True TRAP-TYPE
        ENTERPRISE  trapFault
        VARIABLES   { trapTag }
        DESCRIPTION
            "FutureUse30 Alert on Input3"
    ::= 2509

-- end of futureUse30 Input3 trap

-- beginning of futureUse30 Input4 trap

    faultfutureUse30Input4False TRAP-TYPE
        ENTERPRISE  trapFault
        VARIABLES   { trapTag }
        DESCRIPTION
            "FutureUse30 Cleared on Input4"
    ::= 2510
    
    faultfutureUse30Input4True TRAP-TYPE
        ENTERPRISE  trapFault
        VARIABLES   { trapTag }
        DESCRIPTION
            "FutureUse30 Alert on Input4"
    ::= 2511

-- end of futureUse30 Input4 trap

-- beginning of futureUse30 Input5 trap

    faultfutureUse30Input5False TRAP-TYPE
        ENTERPRISE  trapFault
        VARIABLES   { trapTag }
        DESCRIPTION
            "FutureUse30 Cleared on Input5"
    ::= 2512
    
    faultfutureUse30Input5True TRAP-TYPE
        ENTERPRISE  trapFault
        VARIABLES   { trapTag }
        DESCRIPTION
            "FutureUse30 Alert on Input5"
    ::= 2513

-- end of futureUse30 Input5 trap

-- beginning of futureUse30 Input6 trap

    faultfutureUse30Input6False TRAP-TYPE
        ENTERPRISE  trapFault
        VARIABLES   { trapTag }
        DESCRIPTION
            "FutureUse30 Cleared on Input6"
    ::= 2514
    
    faultfutureUse30Input6True TRAP-TYPE
        ENTERPRISE  trapFault
        VARIABLES   { trapTag }
        DESCRIPTION
            "FutureUse30 Alert on Input6"
    ::= 2515

-- end of futureUse30 Input6 trap

-- beginning of futureUse30 Input7 trap

    faultfutureUse30Input7False TRAP-TYPE
        ENTERPRISE  trapFault
        VARIABLES   { trapTag }
        DESCRIPTION
            "FutureUse30 Cleared on Input7"
    ::= 2516
    
    faultfutureUse30Input7True TRAP-TYPE
        ENTERPRISE  trapFault
        VARIABLES   { trapTag }
        DESCRIPTION
            "FutureUse30 Alert on Input7"
    ::= 2517

-- end of futureUse30 Input7 trap

-- beginning of futureUse30 Input8 trap

    faultfutureUse30Input8False TRAP-TYPE
        ENTERPRISE  trapFault
        VARIABLES   { trapTag }
        DESCRIPTION
            "FutureUse30 Cleared on Input8"
    ::= 2518
    
    faultfutureUse30Input8True TRAP-TYPE
        ENTERPRISE  trapFault
        VARIABLES   { trapTag }
        DESCRIPTION
            "FutureUse30 Alert on Input8"
    ::= 2519

-- end of futureUse30 Input8 trap

-- beginning of futureUse31 Input1 trap

    faultfutureUse31Input1False TRAP-TYPE
        ENTERPRISE  trapFault
        VARIABLES   { trapTag }
        DESCRIPTION
            "FutureUse31 Cleared on Input1"
    ::= 2520
    
    faultfutureUse31Input1True TRAP-TYPE
        ENTERPRISE  trapFault
        VARIABLES   { trapTag }
        DESCRIPTION
            "FutureUse31 Alert on Input1"
    ::= 2521

-- end of futureUse31 Input1 trap

-- beginning of futureUse31 Input2 trap

    faultfutureUse31Input2False TRAP-TYPE
        ENTERPRISE  trapFault
        VARIABLES   { trapTag }
        DESCRIPTION
            "FutureUse31 Cleared on Input2"
    ::= 2522
    
    faultfutureUse31Input2True TRAP-TYPE
        ENTERPRISE  trapFault
        VARIABLES   { trapTag }
        DESCRIPTION
            "FutureUse31 Alert on Input2"
    ::= 2523

-- end of futureUse31 Input2 trap

-- beginning of futureUse31 Input3 trap

    faultfutureUse31Input3False TRAP-TYPE
        ENTERPRISE  trapFault
        VARIABLES   { trapTag }
        DESCRIPTION
            "FutureUse31 Cleared on Input3"
    ::= 2524
    
    faultfutureUse31Input3True TRAP-TYPE
        ENTERPRISE  trapFault
        VARIABLES   { trapTag }
        DESCRIPTION
            "FutureUse31 Alert on Input3"
    ::= 2525

-- end of futureUse31 Input3 trap

-- beginning of futureUse31 Input4 trap

    faultfutureUse31Input4False TRAP-TYPE
        ENTERPRISE  trapFault
        VARIABLES   { trapTag }
        DESCRIPTION
            "FutureUse31 Cleared on Input4"
    ::= 2526
    
    faultfutureUse31Input4True TRAP-TYPE
        ENTERPRISE  trapFault
        VARIABLES   { trapTag }
        DESCRIPTION
            "FutureUse31 Alert on Input4"
    ::= 2527

-- end of futureUse31 Input4 trap

-- beginning of futureUse31 Input5 trap

    faultfutureUse31Input5False TRAP-TYPE
        ENTERPRISE  trapFault
        VARIABLES   { trapTag }
        DESCRIPTION
            "FutureUse31 Cleared on Input5"
    ::= 2528
    
    faultfutureUse31Input5True TRAP-TYPE
        ENTERPRISE  trapFault
        VARIABLES   { trapTag }
        DESCRIPTION
            "FutureUse31 Alert on Input5"
    ::= 2529

-- end of futureUse31 Input5 trap

-- beginning of futureUse31 Input6 trap

    faultfutureUse31Input6False TRAP-TYPE
        ENTERPRISE  trapFault
        VARIABLES   { trapTag }
        DESCRIPTION
            "FutureUse31 Cleared on Input6"
    ::= 2530
    
    faultfutureUse31Input6True TRAP-TYPE
        ENTERPRISE  trapFault
        VARIABLES   { trapTag }
        DESCRIPTION
            "FutureUse31 Alert on Input6"
    ::= 2531

-- end of futureUse31 Input6 trap

-- beginning of futureUse31 Input7 trap

    faultfutureUse31Input7False TRAP-TYPE
        ENTERPRISE  trapFault
        VARIABLES   { trapTag }
        DESCRIPTION
            "FutureUse31 Cleared on Input7"
    ::= 2532
    
    faultfutureUse31Input7True TRAP-TYPE
        ENTERPRISE  trapFault
        VARIABLES   { trapTag }
        DESCRIPTION
            "FutureUse31 Alert on Input7"
    ::= 2533

-- end of futureUse31 Input7 trap

-- beginning of futureUse31 Input8 trap

    faultfutureUse31Input8False TRAP-TYPE
        ENTERPRISE  trapFault
        VARIABLES   { trapTag }
        DESCRIPTION
            "FutureUse31 Cleared on Input8"
    ::= 2534
    
    faultfutureUse31Input8True TRAP-TYPE
        ENTERPRISE  trapFault
        VARIABLES   { trapTag }
        DESCRIPTION
            "FutureUse31 Alert on Input8"
    ::= 2535

-- end of futureUse31 Input8 trap




END
