-- Copyright 2002 Evertz Microsystems Ltd.
-- 07/12/02
-- Confidential
-- Preliminary

FC7800-MIB DEFINITIONS ::= BEGIN

IMPORTS
        exprFC7800
                FROM EVERTZ-EXPERIMENTAL-NODE
        OBJECT-TYPE
                FROM RFC-1212;

-- AGENT       
        fcNetworkSnmpSetup	        OBJECT IDENTIFIER ::= { exprFC7800 2 }  
        fcProductLocation		OBJECT IDENTIFIER ::= { exprFC7800 3 }  
        fcHardware			OBJECT IDENTIFIER ::= { exprFC7800 4 }
        fcSoftware			OBJECT IDENTIFIER ::= { exprFC7800 5 }
        mgmFaultNotify			OBJECT IDENTIFIER ::= { exprFC7800 6 }
        fcTraps				OBJECT IDENTIFIER ::= { exprFC7800 7 }
        fcTimeManagement    OBJECT IDENTIFIER ::= { exprFC7800 8 }    

-- end of declaration section

-- beginning of the network/snmp setup info


	readCommunityString OBJECT-TYPE
			 SYNTAX  OCTET STRING (SIZE(16))
			 ACCESS  read-write
			 STATUS  mandatory
			 DESCRIPTION 
			 "
	 This parameter allows the user to get and set the value of the Read Community String.
			 "
	::= { fcNetworkSnmpSetup 1 }

	readwriteCommunityString OBJECT-TYPE
			 SYNTAX  OCTET STRING (SIZE(16))
			 ACCESS  read-write
			 STATUS  mandatory
			 DESCRIPTION 
			 "
	 This parameter allows the user to get and set the value of the Read/Write Community String.
			 "
	::= { fcNetworkSnmpSetup 2 }



	trapDestination1 OBJECT-TYPE
			 SYNTAX  OCTET STRING (SIZE(16))
			 ACCESS  read-only
			 STATUS  mandatory
			 DESCRIPTION 
			 "
	 This parameter allows the user to get and set the value of the trap desination 1.
			 "
	::= { fcNetworkSnmpSetup 3 }


	trapDestination2 OBJECT-TYPE
			 SYNTAX  OCTET STRING (SIZE(16))
			 ACCESS  read-only
			 STATUS  mandatory
			 DESCRIPTION 
			 "
	 This parameter allows the user to get and set the value of the trap desination 2.
			 "
	::= { fcNetworkSnmpSetup 4 }


	trapDestination3 OBJECT-TYPE
			 SYNTAX  OCTET STRING (SIZE(16))
			 ACCESS  read-only
			 STATUS  mandatory
			 DESCRIPTION 
			 "
	 This parameter allows the user to get and set the value of the trap desintation 3.
			 "
	::= { fcNetworkSnmpSetup 5 }


	trapDestination4 OBJECT-TYPE
			 SYNTAX  OCTET STRING (SIZE(16))
			 ACCESS  read-only
			 STATUS  mandatory
			 DESCRIPTION 
			 "
	 This parameter allows the user to get and set the value of the trap desintation 4.
			 "
	::= { fcNetworkSnmpSetup 6 }


	trapDestination5 OBJECT-TYPE
			 SYNTAX  OCTET STRING (SIZE(16))
			 ACCESS  read-only
			 STATUS  mandatory
			 DESCRIPTION 
			 "
	 This parameter allows the user to get and set the value of the trap desintation 5.
			 "
	::= { fcNetworkSnmpSetup 7 }

	trapDestination6 OBJECT-TYPE
			 SYNTAX  OCTET STRING (SIZE(16))
			 ACCESS  read-only
			 STATUS  mandatory
			 DESCRIPTION 
			 "
	 This parameter allows the user to get and set the value of the trap desintation 6.
			 "
	::= { fcNetworkSnmpSetup 8 }

	trapDestination7 OBJECT-TYPE
			 SYNTAX  OCTET STRING (SIZE(16))
			 ACCESS  read-only
			 STATUS  mandatory
			 DESCRIPTION 
			 "
	 This parameter allows the user to get and set the value of the trap desintation 7.
			 "
	::= { fcNetworkSnmpSetup 9 }

	trapDestination8 OBJECT-TYPE
			 SYNTAX  OCTET STRING (SIZE(16))
			 ACCESS  read-only
			 STATUS  mandatory
			 DESCRIPTION 
			 "
	 This parameter allows the user to get and set the value of the trap desintation 8.
			 "
	::= { fcNetworkSnmpSetup 10 }

	trapDestination9 OBJECT-TYPE
			 SYNTAX  OCTET STRING (SIZE(16))
			 ACCESS  read-only
			 STATUS  mandatory
			 DESCRIPTION 
			 "
	 This parameter allows the user to get and set the value of the trap desintation 9.
			 "
	::= { fcNetworkSnmpSetup 11 }

	trapDestination10 OBJECT-TYPE
			 SYNTAX  OCTET STRING (SIZE(16))
			 ACCESS  read-only
			 STATUS  mandatory
			 DESCRIPTION 
			 "
	 This parameter allows the user to get and set the value of the trap desintation 10.
			 "
	::= { fcNetworkSnmpSetup 12 }

	numValidTrapDestinations OBJECT-TYPE
             SYNTAX  INTEGER ( 1..10 )
			 ACCESS  read-only
			 STATUS  mandatory
			 DESCRIPTION 
			 "
	 This parameter shows the current number of valid trap destinations.
			 "
	::= { fcNetworkSnmpSetup 13 }

	addTrapDestination OBJECT-TYPE
			 SYNTAX  OCTET STRING (SIZE(16))
			 ACCESS  read-write
			 STATUS  mandatory
			 DESCRIPTION 
			 "
	 This parameter allows the user to add an IP to the trap destination list.
			 "
	::= { fcNetworkSnmpSetup 14 }

	removeTrapDestinationNumber OBJECT-TYPE
             SYNTAX  INTEGER ( 1..10 )
			 ACCESS  read-write
			 STATUS  mandatory
			 DESCRIPTION 
			 "
	 This parameter allows the user to remove a trap destination from the list.
			 "
	::= { fcNetworkSnmpSetup 15 }


-- end of the network/snmp table


-- beginning of the product info table info

	productLocationTable OBJECT-TYPE
                SYNTAX SEQUENCE OF ProductLocationEntry
                ACCESS not-accessible
                STATUS mandatory
                DESCRIPTION
                "
		This table is indexed by product location instance and contains
		information on the insertion/removal counters, product name and
		the starting/ending slots.  NOTE, end slot parameter may not work
		properly on early verions of the vistalink or on third party managers.
                "
        ::= { fcProductLocation 1 }

        productLocationEntry OBJECT-TYPE
                SYNTAX ProductLocationEntry
                ACCESS not-accessible
                STATUS mandatory
                DESCRIPTION
                " 
                "
                INDEX { locInstance }
        ::= { productLocationTable 1 }

        ProductLocationEntry ::= SEQUENCE {
                locInstance          INTEGER,
                insertionCounter     INTEGER,
                removalCounter       INTEGER,
                productName	     OCTET STRING,
                productSlotStart     INTEGER,
                productSlotEnd	     INTEGER
        }

        locInstance OBJECT-TYPE
                SYNTAX INTEGER ( 1..15 )
                ACCESS  read-only
                STATUS  mandatory
                DESCRIPTION 
                "
		This parameter is used to index everything in this table.          
                "
        ::= { productLocationEntry 1 }

        insertionCounter OBJECT-TYPE
                SYNTAX  INTEGER ( 0..32000 )
                ACCESS  read-only
                STATUS  mandatory
                DESCRIPTION 
                "
		This parameter is a counter that keeps track of the
		number of times a slot has had a product inserted in it.	         
                "
        ::= { productLocationEntry 2 }
    
        removalCounter OBJECT-TYPE
                SYNTAX  INTEGER ( 0..32000 )
                ACCESS  read-only
                STATUS  mandatory
                DESCRIPTION 
                "
		This parameter is a counter that keeps track of the number of times
		a slot has had a product removed from it.	        
                "
        ::= { productLocationEntry 3 }

        productName OBJECT-TYPE
                SYNTAX  OCTET STRING (SIZE(15))
                ACCESS  read-only
                STATUS  mandatory
                DESCRIPTION 
                "
		This parameter shows the name of the product that is currently in
		a particular slot in the frame.          
                "
        ::= { productLocationEntry 4 }

        productSlotStart OBJECT-TYPE
                SYNTAX  INTEGER (1..15)
                ACCESS  read-only
                STATUS  mandatory
                DESCRIPTION 
                "
		This parameter returns the slot in which a particular card ends in         
                "
        ::= { productLocationEntry 5 }

        productSlotEnd OBJECT-TYPE
                SYNTAX  INTEGER (1..15)
                ACCESS  read-only
                STATUS  mandatory
                DESCRIPTION 
                           "
			         
                           "
        ::= { productLocationEntry 6 }
    
-- end of the product location table
-- start of the FC hardware objects

        temperature OBJECT-TYPE
                 SYNTAX  INTEGER (-128..127)
                 ACCESS  read-write
                 STATUS  mandatory
                 DESCRIPTION 
                 "
	 	 This parameter is currently under development, it will be available on
		 later versions of the FC.  Note a value of -128 signifies that the temperature
		 feature is not supported on this FC.	         
                 "
        ::= { fcHardware 1 }

        frameStatusLine OBJECT-TYPE
                 SYNTAX  INTEGER {false(1),
				  true(2),
				  notAvailable(3)
  		 }
                 ACCESS  read-only
                 STATUS  mandatory
                 DESCRIPTION 
                 "
	 	 This parameter returns the status of the frame status line, False if the
		 frame status line light is on, true if the frame status line is off and
		 not available if the hardware build number is less than 2, since older
		 builds of the FC cannot support this option.	          
                 "
        ::= { fcHardware 2 }

	powerSupply1Status OBJECT-TYPE
                 SYNTAX  INTEGER {false(1),
				  true(2),
				  notAvailable(3)
  		 }
                 ACCESS  read-only
                 STATUS  mandatory
                 DESCRIPTION 
                 "
	 	 This parameter returns the status of the power supply 1, False if the
		 power supply 1 light is off, true if the power supply 1 is on and
		 not available if the hardware build number is less than 2, since older
		 builds of the FC cannot support this option.	          
                 "
        ::= { fcHardware 3 }

	powerSupply2Status OBJECT-TYPE
                 SYNTAX  INTEGER {false(1),
				  true(2),
				  notAvailable(3)
  		 }
                 ACCESS  read-only
                 STATUS  mandatory
                 DESCRIPTION 
                 "
	 	 This parameter returns the status of the power supply 2, False if the
		 power supply 2 light is off, true if the power supply 2 is on and
		 not available if the hardware build number is less than 2, since older
		 builds of the FC cannot support this option.	          
                 "
        ::= { fcHardware 4 }

        realTimeClock OBJECT-TYPE
                 SYNTAX  OCTET STRING (SIZE(15))
                 ACCESS  read-write
                 STATUS  mandatory
                 DESCRIPTION 
                 "
	 	 This parameter allows the user to get and set the value of the real time
		 clock.  The format for setting the clock is mm/dd/yy hh:mm, the clock will not
		 set properly if this format is now followed.	          
                 "
        ::= { fcHardware 5 }

	flashRate OBJECT-TYPE
                 SYNTAX  INTEGER (1..5)
                 ACCESS  read-write
                 STATUS  mandatory
                 DESCRIPTION 
                 "
	 	 This paramter allows the user to set the rate at which the coloured leds on the front
		 of the FC flash.  Note if a particular led is not enabled it will not flash.  You can 
		 enable and disable the leds through the ledtable.	         
                 "
        ::= { fcHardware 6 }

        
        
-- end of the fc hardware table
-- beginning of the FC Led table

        ledTable OBJECT-TYPE
                SYNTAX SEQUENCE OF LedEntry
                ACCESS not-accessible
                STATUS mandatory
                DESCRIPTION
                "
		This table contains the parameter that allows you to enable and disable the coloured
		leds on the front of the FC.            
                "
        ::= { fcHardware 7 }
         
        ledEntry OBJECT-TYPE
                SYNTAX LedEntry
                ACCESS not-accessible
                STATUS mandatory
                DESCRIPTION
                " 
                             
                "
                INDEX { ledName }
        ::= { ledTable 1 }

        LedEntry ::= SEQUENCE {
                ledName		INTEGER,
		enableLed	INTEGER   
        }


        ledName OBJECT-TYPE
                 SYNTAX  INTEGER {colouredLed1(1),
				  colouredLed2(2),
				  colouredLed3(3),
				  colouredLed4(4),
				  audioLed1(5),
				  audioLed2(6),
				  audioLed3(7),
				  audioLed4(8)
		 }
                 ACCESS  read-only
                 STATUS  mandatory
                 DESCRIPTION 
                 "
	 	 This is index for this table, its values correspond to the coloured leds in front
		 of the FC.	         
                 "
        ::= { ledEntry 1 }

	enableLed OBJECT-TYPE
                 SYNTAX  INTEGER {disable(1),
				  enable(2)
		 }
                 ACCESS  read-write
                 STATUS  mandatory
                 DESCRIPTION 
                 "
	 	 This parameter allows you to get and set the leds to flash or to stay off.	         
                 "
        ::= { ledEntry 2 }
        
-- end of the FC led table

    saveTrapInfo OBJECT-TYPE
        SYNTAX INTEGER { set(1)
        }
        ACCESS read-write
        STATUS mandatory
        DESCRIPTION
        "
            This parameter allows the user to save all the sendTrap values
            for all the products.  Note that once the user has set the value,
            they cannot do another set until 30 seconds has elapsed.
        "

        ::= { fcHardware 8 }


    rebootUpgrade OBJECT-TYPE
        SYNTAX INTEGER { set(1)
        }
        ACCESS read-write
        STATUS mandatory
        DESCRIPTION
        "
        Doing a set of 1 on this parameter will cause the frame controller
        to reboot into upgrade mode.  Get of this parameter has no
        meaning.
        "              
        ::= {fcHardware 9}
	
	rebootFc OBJECT-TYPE
		SYNTAX INTEGER { set(1)
		}
		ACCESS read-write
        STATUS mandatory
        DESCRIPTION
        "
        Doing a set of 1 on this parameter will cause the frame controller
        to reboot.  Get of this parameter has no
        meaning.
        "              
        ::= {fcHardware 10}

-- beginning of the product info table info
     
        kernalMajorRelease OBJECT-TYPE
                SYNTAX  OCTET STRING (SIZE(15))
                ACCESS  read-only
                STATUS  mandatory
                DESCRIPTION 
                "
		This parameter allows the user to get the value of the
		kernel's major release number.	         
                "
        ::= { fcSoftware 1 }

        kernalBuildDate OBJECT-TYPE
                SYNTAX  OCTET STRING (SIZE(15))
                ACCESS  read-only
                STATUS  mandatory
                DESCRIPTION 
                "
		This parameter allows the user to get the date, on which the kernel was
		built.	         
                "
        ::= { fcSoftware 2 }

        softwareBuild OBJECT-TYPE
                SYNTAX  OCTET STRING (SIZE(15))
                ACCESS  read-only
                STATUS  mandatory
                DESCRIPTION 
                "
		This parameter allows the user to get the name of the software build, and its 
		version as well.	         
                "
        ::= { fcSoftware 3 }

         tagName OBJECT-TYPE
                SYNTAX  OCTET STRING (SIZE(15))
                ACCESS  read-only
                STATUS  mandatory
                DESCRIPTION 
                "
		This parameter allows the user to get the name of FC's software tag.	         
                "
        ::= { fcSoftware 4 }

        softwareBuildDate OBJECT-TYPE
                SYNTAX  OCTET STRING (SIZE(15))
                ACCESS  read-only
                STATUS  mandatory
                DESCRIPTION 
                "
		This parameter allows the user to get the date on which the FC software was
		built.	         
                "
        ::= { fcSoftware 5 }

        ipConfigureMode OBJECT-TYPE
                SYNTAX INTEGER {
                    dhcp(1),
                    static(2)
                    }
                ACCESS read-write
                STATUS mandatory
                DESCRIPTION "Control to choose IP configure mode"
        ::= { fcSoftware 6 }

        slotIpTable OBJECT-TYPE
                SYNTAX SEQUENCE OF SlotIpEntry
                ACCESS not-accessible
                STATUS mandatory
                DESCRIPTION "The slotIpTable table"
        ::= { fcSoftware 7 }

        slotIpEntry OBJECT-TYPE
                SYNTAX SlotIpEntry
                ACCESS not-accessible
                STATUS mandatory
                DESCRIPTION " "
                INDEX { locInstance }
        ::= { slotIpTable 1} 

        SlotIpEntry ::= SEQUENCE {
                slotIPAddr  OCTET STRING,     
                slotNetMask     OCTET STRING,
                slotGateway     OCTET STRING,
                slotProxyMode   INTEGER
        }

        slotIPAddr OBJECT-TYPE
	    	    SYNTAX OCTET STRING (SIZE(16))
    	    	ACCESS read-write
        		STATUS mandatory
		        DESCRIPTION
		        "
		This parameter allows the user to configure the starting address of IP pool.
        		"
    	::= { slotIpEntry 1 }

	    slotNetMask OBJECT-TYPE
	    	    SYNTAX OCTET STRING (SIZE(16))
    	    	ACCESS read-write
        		STATUS mandatory
		        DESCRIPTION
		        "
		This parameter allows the user to configure the netmask address of IP pool.
        		"
    	::= { slotIpEntry 2 }

	    slotGateway OBJECT-TYPE
	    	    SYNTAX OCTET STRING (SIZE(16))
    	    	ACCESS read-write
        		STATUS mandatory
		        DESCRIPTION
		        "
		This parameter allows the user to configure the gateway of IP pool.
        		"
    	::= { slotIpEntry 3 }

    slotProxyMode OBJECT-TYPE
            SYNTAX INTEGER {
                disable(1),
                enable(2)
                }
            ACCESS read-write
            STATUS mandatory
            DESCRIPTION "Control to disable/enable proxy mode"
    	::= { slotIpEntry 4 }
    	
-- end of FC software table 
-- start of the Faults management table

        mgmFaultTable OBJECT-TYPE
                SYNTAX SEQUENCE OF MgmFaultEntry
                ACCESS not-accessible
                STATUS mandatory
                DESCRIPTION
                "
		This table contains information on traps and trap status for the FC.            
                "
        ::= { mgmFaultNotify 1 }

        mgmFaultEntry OBJECT-TYPE
                SYNTAX MgmFaultEntry
                ACCESS not-accessible
                STATUS mandatory
                DESCRIPTION
                " 
                "
                INDEX { faultName }
        ::= { mgmFaultTable 1 }

        MgmFaultEntry ::= SEQUENCE {
                faultName		     INTEGER,  
		sendTrap	             INTEGER,
		trapPresent		     INTEGER		              	                
        }

        faultName OBJECT-TYPE
                SYNTAX  INTEGER {insertionRemoval2(1),
				insertionRemoval3(2),
				insertionRemoval4(3),
				insertionRemoval5(4),
				insertionRemoval6(5),
				insertionRemoval7(6),
				insertionRemoval8(7),
				insertionRemoval9(8),
				insertionRemoval10(9),
				insertionRemoval11(10),
				insertionRemoval12(11),
				insertionRemoval13(12),
				insertionRemoval14(13),
				insertionRemoval15(14),
        		frameStatusLine(15),
				tempOver(16),
				tempUnder(17),
				powerSupply1NotOk(18),
				powerSupply2NotOk(19),
   				rearFan1NotOk(20),
				rearFan2NotOk(21)
                }
                ACCESS  read-only
                STATUS  mandatory
                DESCRIPTION 
                "
		This parameter is the index for this table, its values correspond to the names of the traps
		that exist on the FC.	        
                "
        ::= { mgmFaultEntry 1 }

        sendTrap OBJECT-TYPE
                SYNTAX  INTEGER {false(1),
				 true(2)
		}   
                ACCESS  read-write
                STATUS  mandatory
                DESCRIPTION 
                "
		This parameter allows the user to control whether a certain trap is sent or not sent for
		the FC.	        
                "
        ::= { mgmFaultEntry 2 }

        trapPresent OBJECT-TYPE
                SYNTAX  INTEGER {false(1),
				 true(2)
		}   
                ACCESS  read-only
                STATUS  mandatory
                DESCRIPTION 
                "
		This parameter allows the user to check the status of a particular trap.	         
                "
        ::= { mgmFaultEntry 3 }
     
-- beginning of the FC time management table info
     ntpRealTimeClock OBJECT-TYPE
                 SYNTAX  OCTET STRING (SIZE(15))
                 ACCESS  read-write
                 STATUS  mandatory
                 DESCRIPTION 
                 "
	 	 This parameter allows the user to get and set the value of the real time
		 clock.  The format for setting the clock is mm/dd/yy hh:mm, the clock will not
		 set properly if this format is now followed.	          
                 "
        ::= { fcTimeManagement 1 }            

    timeSource OBJECT-TYPE
      SYNTAX INTEGER {
            disable(1),
            local(2),
            ntp(3),
	    inbandSlot2(4),
	    inbandSlot3(5),
	    inbandSlot4(6),
	    inbandSlot5(7),
	    inbandSlot6(8),
	    inbandSlot7(9),
	    inbandSlot8(10),
	    inbandSlot9(11) 
	    inbandSlot10(12),
	    inbandSlot11(13),
	    inbandSlot12(14),
	    inbandSlot13(15) 
	    inbandSlot14(16),
	    inbandSlot15(17)
            }
      ACCESS read-write
      STATUS mandatory
      DESCRIPTION " This parameter allows the user to set the time source used to obtain system time.   "
    ::= { fcTimeManagement 2 }
 
    timeZoneOffset OBJECT-TYPE
      SYNTAX INTEGER ( -12..14 )
      ACCESS read-write
      STATUS mandatory
      DESCRIPTION " Set the time zone.   "
    ::= { fcTimeManagement 3 }

    dayLightSaving OBJECT-TYPE
      SYNTAX INTEGER {
            off(1),
            on(2)
            }
      ACCESS read-write
      STATUS mandatory
      DESCRIPTION " This parameter allows the user to set day light saving feature.   "
    ::= { fcTimeManagement 4 }

     externalNtpServer OBJECT-TYPE
                 SYNTAX  OCTET STRING (SIZE(15))
                 ACCESS  read-write
                 STATUS  mandatory
                 DESCRIPTION 
                 "
	 	 This parameter allows the user to set external NTP server IP address.	          
                 "
     ::= { fcTimeManagement 5 }  
                      
-- end of FC time management table
END
