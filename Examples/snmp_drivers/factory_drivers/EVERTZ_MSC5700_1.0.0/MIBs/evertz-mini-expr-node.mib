-- Copyright Evertz Microsystems Ltd.
-- 10/10/2000
-- Confidential

-- The first release of a MIB
-- Changes may occur

EVERTZ-MINI-EXPERIMENTAL-NODE DEFINITIONS ::= BEGIN

IMPORTS
    evtzMiniExperimental
        FROM EVERTZ-ROOT;

--Node Definitions  


    miniexprOV			OBJECT IDENTIFIER ::= { evtzMiniExperimental 1 }
    miniexprFC3000			OBJECT IDENTIFIER ::= { evtzMiniExperimental 2 }
    miniexprFC500			OBJECT IDENTIFIER ::= { evtzMiniExperimental 3 }
    miniexprDAHD			OBJECT IDENTIFIER ::= { evtzMiniExperimental 4 }
    miniexprDA			OBJECT IDENTIFIER ::= { evtzMiniExperimental 5 }
    miniexprADA			OBJECT IDENTIFIER ::= { evtzMiniExperimental 6 }
    miniexprADAEQ			OBJECT IDENTIFIER ::= { evtzMiniExperimental 7 }
    miniexprDA2QAESU			OBJECT IDENTIFIER ::= { evtzMiniExperimental 8 }
    miniexprDAAESU			OBJECT IDENTIFIER ::= { evtzMiniExperimental 9 }
    miniexprDCDAHD			OBJECT IDENTIFIER ::= { evtzMiniExperimental 10 }
    miniexprAC02HDSD			OBJECT IDENTIFIER ::= { evtzMiniExperimental 11 }
    miniexprAMDAAESU			OBJECT IDENTIFIER ::= { evtzMiniExperimental 12 }
    miniexprVMDA			OBJECT IDENTIFIER ::= { evtzMiniExperimental 13 }
    miniexprDA2QREVA			OBJECT IDENTIFIER ::= { evtzMiniExperimental 14 }
    miniexprDA2QREVB			OBJECT IDENTIFIER ::= { evtzMiniExperimental 15 }
    miniexprDA2QHD			OBJECT IDENTIFIER ::= { evtzMiniExperimental 16 }
    miniexprAD4HD520			OBJECT IDENTIFIER ::= { evtzMiniExperimental 17 }
    miniexprAD4DDHD520			OBJECT IDENTIFIER ::= { evtzMiniExperimental 18 }
    miniexprVIP			OBJECT IDENTIFIER ::= { evtzMiniExperimental 19 }
    miniexprPTX			OBJECT IDENTIFIER ::= { evtzMiniExperimental 20 }
    miniexprGLINKROUTER			OBJECT IDENTIFIER ::= { evtzMiniExperimental 21 }
    miniexprADAAUD500			OBJECT IDENTIFIER ::= { evtzMiniExperimental 22 }
    miniexprACO25600			OBJECT IDENTIFIER ::= { evtzMiniExperimental 23 }
    miniexprCARD			OBJECT IDENTIFIER ::= { evtzMiniExperimental 24 }
    miniexprMSC5600			OBJECT IDENTIFIER ::= { evtzMiniExperimental 25 }
    miniexprMVPD			OBJECT IDENTIFIER ::= { evtzMiniExperimental 26 }
    miniexprGI			OBJECT IDENTIFIER ::= { evtzMiniExperimental 27 }
    miniexprLBANDRTR			OBJECT IDENTIFIER ::= { evtzMiniExperimental 28 }
    miniexprDDAESU520			OBJECT IDENTIFIER ::= { evtzMiniExperimental 29 }
    miniexprXRF1RTR			OBJECT IDENTIFIER ::= { evtzMiniExperimental 30 }
    miniexprRTRSC			OBJECT IDENTIFIER ::= { evtzMiniExperimental 31 }
    miniexprDD1200			OBJECT IDENTIFIER ::= { evtzMiniExperimental 32 }
    miniexprDAHDL500			OBJECT IDENTIFIER ::= { evtzMiniExperimental 33 }
    miniexprADAEQL500			OBJECT IDENTIFIER ::= { evtzMiniExperimental 34 }
    miniexprNGI			OBJECT IDENTIFIER ::= { evtzMiniExperimental 35 }
    miniexprRGBR2407			OBJECT IDENTIFIER ::= { evtzMiniExperimental 36 }
    miniexprRGBT2407			OBJECT IDENTIFIER ::= { evtzMiniExperimental 37 }
    miniexprVI3500			OBJECT IDENTIFIER ::= { evtzMiniExperimental 38 }
    miniexprGI3500			OBJECT IDENTIFIER ::= { evtzMiniExperimental 39 }
    miniexprHDSD9545DLYPRO			OBJECT IDENTIFIER ::= { evtzMiniExperimental 40 }
    miniexprTPI7700			OBJECT IDENTIFIER ::= { evtzMiniExperimental 41 }
    miniexprTSM7780			OBJECT IDENTIFIER ::= { evtzMiniExperimental 42 }
    miniexprXENONOUTPUT3G			OBJECT IDENTIFIER ::= { evtzMiniExperimental 43 }
    miniexprDAL500			OBJECT IDENTIFIER ::= { evtzMiniExperimental 44 }
    miniexprPTXMT97700			OBJECT IDENTIFIER ::= { evtzMiniExperimental 45 }
    miniexprAE4HD520			OBJECT IDENTIFIER ::= { evtzMiniExperimental 46 }
    miniexprX0401			OBJECT IDENTIFIER ::= { evtzMiniExperimental 47 }
    miniexprGLINK3000			OBJECT IDENTIFIER ::= { evtzMiniExperimental 48 }
    miniexprPTXAPC7700			OBJECT IDENTIFIER ::= { evtzMiniExperimental 49 }
    miniexprPTXMT87700			OBJECT IDENTIFIER ::= { evtzMiniExperimental 50 }
    miniexprRSCCCI7700			OBJECT IDENTIFIER ::= { evtzMiniExperimental 51 }
    miniexprASIMP2SD3000			OBJECT IDENTIFIER ::= { evtzMiniExperimental 52 }
    miniexprMUX7780			OBJECT IDENTIFIER ::= { evtzMiniExperimental 53 }
    miniexprDA2QHDN			OBJECT IDENTIFIER ::= { evtzMiniExperimental 54 }
    miniexprEQXINPUT			OBJECT IDENTIFIER ::= { evtzMiniExperimental 55 }
    miniexprEQXOUTPUT			OBJECT IDENTIFIER ::= { evtzMiniExperimental 56 }
    miniexprEQXXPT			OBJECT IDENTIFIER ::= { evtzMiniExperimental 57 }
    miniexprEQXFC			OBJECT IDENTIFIER ::= { evtzMiniExperimental 58 }
    miniexprPTXMVS7700			OBJECT IDENTIFIER ::= { evtzMiniExperimental 59 }
    miniexprKEYER			OBJECT IDENTIFIER ::= { evtzMiniExperimental 60 }
    miniexprDAHDN500			OBJECT IDENTIFIER ::= { evtzMiniExperimental 61 }
    miniexprEQXMONITOR			OBJECT IDENTIFIER ::= { evtzMiniExperimental 62 }
    miniexprRTR7700			OBJECT IDENTIFIER ::= { evtzMiniExperimental 63 }
    miniexprRTRTOPAZ3G			OBJECT IDENTIFIER ::= { evtzMiniExperimental 64 }
    miniexprDA2Q3G500			OBJECT IDENTIFIER ::= { evtzMiniExperimental 65 }
    miniexprDA3G500			OBJECT IDENTIFIER ::= { evtzMiniExperimental 66 }
    miniexprS2IPRCL7700			OBJECT IDENTIFIER ::= { evtzMiniExperimental 67 }
    miniexprRSCBRC7700			OBJECT IDENTIFIER ::= { evtzMiniExperimental 68 }
    miniexprSDI2IP2B7780			OBJECT IDENTIFIER ::= { evtzMiniExperimental 69 }
    miniexprEQXIP18ASIMP2			OBJECT IDENTIFIER ::= { evtzMiniExperimental 70 }
    miniexprEQXOP36SAVM			OBJECT IDENTIFIER ::= { evtzMiniExperimental 71 }
    miniexprTG7780			OBJECT IDENTIFIER ::= { evtzMiniExperimental 72 }
    miniexprASIIP27780			OBJECT IDENTIFIER ::= { evtzMiniExperimental 73 }
    miniexprIPASI27780			OBJECT IDENTIFIER ::= { evtzMiniExperimental 74 }
    miniexprXENONAAIP			OBJECT IDENTIFIER ::= { evtzMiniExperimental 75 }
    miniexprXENONAAOP			OBJECT IDENTIFIER ::= { evtzMiniExperimental 76 }
    miniexprACO25601			OBJECT IDENTIFIER ::= { evtzMiniExperimental 77 }
    miniexprMSC5601			OBJECT IDENTIFIER ::= { evtzMiniExperimental 78 }
    miniexprVIPPRO			OBJECT IDENTIFIER ::= { evtzMiniExperimental 79 }
    miniexprUCHD7712MINI			OBJECT IDENTIFIER ::= { evtzMiniExperimental 80 }
    miniexprEQXINPUT3G			OBJECT IDENTIFIER ::= { evtzMiniExperimental 81 }
    miniexprEQXOUTPUT3G			OBJECT IDENTIFIER ::= { evtzMiniExperimental 82 }
    miniexprEQXDDOUTPUT3G			OBJECT IDENTIFIER ::= { evtzMiniExperimental 83 }
    miniexprXENONDAOP			OBJECT IDENTIFIER ::= { evtzMiniExperimental 84 }
    miniexprPIPRMUXASI7780			OBJECT IDENTIFIER ::= { evtzMiniExperimental 85 }
    miniexprDM8VSB7780			OBJECT IDENTIFIER ::= { evtzMiniExperimental 86 }
    miniexprPTXACOS7700			OBJECT IDENTIFIER ::= { evtzMiniExperimental 87 }
    miniexprVLPRODATASTORAGESERVER			OBJECT IDENTIFIER ::= { evtzMiniExperimental 88 }
    miniexprVIP9767			OBJECT IDENTIFIER ::= { evtzMiniExperimental 89 }
    miniexprDA4SLKEHD7700			OBJECT IDENTIFIER ::= { evtzMiniExperimental 90 }
    miniexprDCDAHD510			OBJECT IDENTIFIER ::= { evtzMiniExperimental 91 }
    miniexprADAEQ501			OBJECT IDENTIFIER ::= { evtzMiniExperimental 92 }
    miniexprMP2DEC3000			OBJECT IDENTIFIER ::= { evtzMiniExperimental 93 }
    miniexprIPASIIP7880			OBJECT IDENTIFIER ::= { evtzMiniExperimental 94 }
    miniexprADAEQL501			OBJECT IDENTIFIER ::= { evtzMiniExperimental 95 }
    miniexprSLKPLAYER			OBJECT IDENTIFIER ::= { evtzMiniExperimental 96 }
    miniexprHD2010			OBJECT IDENTIFIER ::= { evtzMiniExperimental 97 }
    miniexprFC3405			OBJECT IDENTIFIER ::= { evtzMiniExperimental 98 }
    miniexprSLKPROXY			OBJECT IDENTIFIER ::= { evtzMiniExperimental 99 }
    miniexprEQXXPT576X576			OBJECT IDENTIFIER ::= { evtzMiniExperimental 100 }
    miniexprSWITCHR2X1			OBJECT IDENTIFIER ::= { evtzMiniExperimental 101 }
    miniexprUDXD7812MINI			OBJECT IDENTIFIER ::= { evtzMiniExperimental 102 }
    miniexprIP96AES3000EMR			OBJECT IDENTIFIER ::= { evtzMiniExperimental 103 }
    miniexprOP96AES3000EMR			OBJECT IDENTIFIER ::= { evtzMiniExperimental 104 }
    miniexprCKDVI3025			OBJECT IDENTIFIER ::= { evtzMiniExperimental 105 }
    miniexprHD20203G			OBJECT IDENTIFIER ::= { evtzMiniExperimental 106 }
    miniexprEMS			OBJECT IDENTIFIER ::= { evtzMiniExperimental 107 }
    miniexprENCMP2HDA7880			OBJECT IDENTIFIER ::= { evtzMiniExperimental 108 }
    miniexprHD2014A			OBJECT IDENTIFIER ::= { evtzMiniExperimental 109 }
    miniexprALBGE7795			OBJECT IDENTIFIER ::= { evtzMiniExperimental 110 }
    miniexprFSEAES83G7847			OBJECT IDENTIFIER ::= { evtzMiniExperimental 111 }
    miniexprEMC3025			OBJECT IDENTIFIER ::= { evtzMiniExperimental 112 }
    miniexprENCH264HDA7880			OBJECT IDENTIFIER ::= { evtzMiniExperimental 113 }
    miniexprVLPROPTXDSR			OBJECT IDENTIFIER ::= { evtzMiniExperimental 114 }
    miniexprCMP7800			OBJECT IDENTIFIER ::= { evtzMiniExperimental 115 }
    miniexprXENONFC			OBJECT IDENTIFIER ::= { evtzMiniExperimental 116 }
    miniexprASIB2DS37780			OBJECT IDENTIFIER ::= { evtzMiniExperimental 117 }
    miniexprPR3000EMR			OBJECT IDENTIFIER ::= { evtzMiniExperimental 118 }
    miniexprIGAC3IP7820			OBJECT IDENTIFIER ::= { evtzMiniExperimental 119 }
    miniexprMVIP			OBJECT IDENTIFIER ::= { evtzMiniExperimental 120 }
    miniexprEMRIP323G			OBJECT IDENTIFIER ::= { evtzMiniExperimental 121 }
    miniexprEMROP323G			OBJECT IDENTIFIER ::= { evtzMiniExperimental 122 }
    miniexprMUXOASI47880			OBJECT IDENTIFIER ::= { evtzMiniExperimental 123 }
    miniexprDMUXASI83080			OBJECT IDENTIFIER ::= { evtzMiniExperimental 124 }
    miniexprEMRAAIP			OBJECT IDENTIFIER ::= { evtzMiniExperimental 125 }
    miniexprMUXPPR3080			OBJECT IDENTIFIER ::= { evtzMiniExperimental 126 }
    miniexprENCH264HD9781			OBJECT IDENTIFIER ::= { evtzMiniExperimental 127 }
    miniexprSDIIP27780			OBJECT IDENTIFIER ::= { evtzMiniExperimental 128 }
    miniexprIPSDI27780			OBJECT IDENTIFIER ::= { evtzMiniExperimental 129 }
    miniexprAD8HD520			OBJECT IDENTIFIER ::= { evtzMiniExperimental 130 }
    miniexprAE8HD520			OBJECT IDENTIFIER ::= { evtzMiniExperimental 131 }
    miniexprEMRAAOP			OBJECT IDENTIFIER ::= { evtzMiniExperimental 132 }
    miniexprMUX8ASIIP7880			OBJECT IDENTIFIER ::= { evtzMiniExperimental 133 }
    miniexprDMLB7780BISSMINI			OBJECT IDENTIFIER ::= { evtzMiniExperimental 134 }
    miniexprEMR288X288XPT			OBJECT IDENTIFIER ::= { evtzMiniExperimental 135 }
    miniexprALR3700			OBJECT IDENTIFIER ::= { evtzMiniExperimental 136 }
    miniexprEMRTDM16DLY			OBJECT IDENTIFIER ::= { evtzMiniExperimental 137 }
    miniexprIPASI27880			OBJECT IDENTIFIER ::= { evtzMiniExperimental 138 }
    miniexprSLKCONVERTER			OBJECT IDENTIFIER ::= { evtzMiniExperimental 139 }
    miniexprVLPROVIRTUALPTX			OBJECT IDENTIFIER ::= { evtzMiniExperimental 140 }
    miniexprS3405			OBJECT IDENTIFIER ::= { evtzMiniExperimental 141 }
    miniexprSFR3405			OBJECT IDENTIFIER ::= { evtzMiniExperimental 142 }
    miniexprMP2DECMVP			OBJECT IDENTIFIER ::= { evtzMiniExperimental 143 }
    miniexprJ2KDEC			OBJECT IDENTIFIER ::= { evtzMiniExperimental 144 }
    miniexprSFP7708MINI			OBJECT IDENTIFIER ::= { evtzMiniExperimental 145 }
    miniexprXENONSPT3G			OBJECT IDENTIFIER ::= { evtzMiniExperimental 147 }
    miniexprAP3025			OBJECT IDENTIFIER ::= { evtzMiniExperimental 148 }
    miniexprVLPROIPX			OBJECT IDENTIFIER ::= { evtzMiniExperimental 149 }
    miniexprALR370048X48			OBJECT IDENTIFIER ::= { evtzMiniExperimental 150 }
    miniexprGT87790			OBJECT IDENTIFIER ::= { evtzMiniExperimental 151 }
    miniexprDMCOFDM7780			OBJECT IDENTIFIER ::= { evtzMiniExperimental 152 }
    miniexprS2IPNV97700			OBJECT IDENTIFIER ::= { evtzMiniExperimental 153 }
    miniexprIDA9IG500			OBJECT IDENTIFIER ::= { evtzMiniExperimental 154 }
    miniexprADAAUD400			OBJECT IDENTIFIER ::= { evtzMiniExperimental 155 }
    miniexprDAAESB500			OBJECT IDENTIFIER ::= { evtzMiniExperimental 156 }
    miniexprDAAESB400			OBJECT IDENTIFIER ::= { evtzMiniExperimental 157 }
    miniexprHD2014L			OBJECT IDENTIFIER ::= { evtzMiniExperimental 158 }
    miniexprIPGASI16IPGE3080			OBJECT IDENTIFIER ::= { evtzMiniExperimental 159 }
    miniexprDEC32			OBJECT IDENTIFIER ::= { evtzMiniExperimental 160 }
    miniexprTSME7880			OBJECT IDENTIFIER ::= { evtzMiniExperimental 161 }
    miniexprDMLBASIIP7780MINI			OBJECT IDENTIFIER ::= { evtzMiniExperimental 162 }
    miniexprPTXSTB7700			OBJECT IDENTIFIER ::= { evtzMiniExperimental 163 }
    miniexprASI4IP7880			OBJECT IDENTIFIER ::= { evtzMiniExperimental 164 }
    miniexprENC3480			OBJECT IDENTIFIER ::= { evtzMiniExperimental 165 }
    miniexprSLKE9780			OBJECT IDENTIFIER ::= { evtzMiniExperimental 166 }
    miniexprHDIP7880			OBJECT IDENTIFIER ::= { evtzMiniExperimental 167 }
    miniexprEQXXPTG576X288			OBJECT IDENTIFIER ::= { evtzMiniExperimental 168 }
    miniexprVLPRODPILOGGER			OBJECT IDENTIFIER ::= { evtzMiniExperimental 169 }
    miniexprSLKD160HDMI			OBJECT IDENTIFIER ::= { evtzMiniExperimental 170 }
    miniexprMUXASI16IPGE3080			OBJECT IDENTIFIER ::= { evtzMiniExperimental 171 }
    miniexprSVP7832MINI			OBJECT IDENTIFIER ::= { evtzMiniExperimental 172 }
    miniexprEMRHD16MADI			OBJECT IDENTIFIER ::= { evtzMiniExperimental 173 }
    miniexprEQXXPTG288X288			OBJECT IDENTIFIER ::= { evtzMiniExperimental 174 }
    miniexprEQXXPTG576X576			OBJECT IDENTIFIER ::= { evtzMiniExperimental 175 }
    miniexprEMSSC10RXX			OBJECT IDENTIFIER ::= { evtzMiniExperimental 176 }
    miniexprX04013G			OBJECT IDENTIFIER ::= { evtzMiniExperimental 177 }
    miniexprIDA9TSMASI500			OBJECT IDENTIFIER ::= { evtzMiniExperimental 178 }
    miniexprEQXIP16AD2TDM			OBJECT IDENTIFIER ::= { evtzMiniExperimental 179 }
    miniexprEQXOP16AE2TDM			OBJECT IDENTIFIER ::= { evtzMiniExperimental 180 }
    miniexprVQM7800			OBJECT IDENTIFIER ::= { evtzMiniExperimental 181 }
    miniexprEMXFC			OBJECT IDENTIFIER ::= { evtzMiniExperimental 182 }
    miniexprSTATMXC3480			OBJECT IDENTIFIER ::= { evtzMiniExperimental 183 }
    miniexprHD7700ITMMINI			OBJECT IDENTIFIER ::= { evtzMiniExperimental 184 }
    miniexprTXE3480			OBJECT IDENTIFIER ::= { evtzMiniExperimental 185 }
    miniexprFILESTORE			OBJECT IDENTIFIER ::= { evtzMiniExperimental 186 }
    miniexprTSMIP3480			OBJECT IDENTIFIER ::= { evtzMiniExperimental 187 }
    miniexprDECH264HD7780			OBJECT IDENTIFIER ::= { evtzMiniExperimental 188 }
    miniexprEQXFSAVIP			OBJECT IDENTIFIER ::= { evtzMiniExperimental 189 }
    miniexprIDA9IG500DMX			OBJECT IDENTIFIER ::= { evtzMiniExperimental 190 }
    miniexprALB10GE7795MINI			OBJECT IDENTIFIER ::= { evtzMiniExperimental 191 }
    miniexprIPX3080			OBJECT IDENTIFIER ::= { evtzMiniExperimental 192 }
    miniexprFSE3046			OBJECT IDENTIFIER ::= { evtzMiniExperimental 193 }
    miniexprALB10GE7795BASE			OBJECT IDENTIFIER ::= { evtzMiniExperimental 194 }
    miniexprENCJ2K2480			OBJECT IDENTIFIER ::= { evtzMiniExperimental 195 }
    miniexprDCDA4QHD7812MINI			OBJECT IDENTIFIER ::= { evtzMiniExperimental 196 }
    miniexprUDXHD8812			OBJECT IDENTIFIER ::= { evtzMiniExperimental 197 }
    miniexprEQXGINPUT3G			OBJECT IDENTIFIER ::= { evtzMiniExperimental 198 }
    miniexprVLPROTHIRDPARTYTRAP			OBJECT IDENTIFIER ::= { evtzMiniExperimental 199 }
    miniexprENC4H264HD			OBJECT IDENTIFIER ::= { evtzMiniExperimental 200 }
    miniexprDCDA3G7812MINI			OBJECT IDENTIFIER ::= { evtzMiniExperimental 201 }
    miniexprCDMF7837MINI			OBJECT IDENTIFIER ::= { evtzMiniExperimental 202 }
    miniexprSUBPRESETS			OBJECT IDENTIFIER ::= { evtzMiniExperimental 203 }
    miniexprIDA9FC500			OBJECT IDENTIFIER ::= { evtzMiniExperimental 204 }
    miniexprIP10GEHD6IPG3080			OBJECT IDENTIFIER ::= { evtzMiniExperimental 205 }
    miniexprEQXGOUTPUT3G			OBJECT IDENTIFIER ::= { evtzMiniExperimental 206 }
    miniexprHDMI3000			OBJECT IDENTIFIER ::= { evtzMiniExperimental 207 }
    miniexprH264ENCNETRAMINI			OBJECT IDENTIFIER ::= { evtzMiniExperimental 208 }
    miniexprFC3505			OBJECT IDENTIFIER ::= { evtzMiniExperimental 209 }
    miniexprKM2430USB2			OBJECT IDENTIFIER ::= { evtzMiniExperimental 210 }
    miniexprRGBTA2408A2			OBJECT IDENTIFIER ::= { evtzMiniExperimental 211 }
    miniexprRGBRA2408A2			OBJECT IDENTIFIER ::= { evtzMiniExperimental 212 }
    miniexprHD7860IM2MINI			OBJECT IDENTIFIER ::= { evtzMiniExperimental 213 }
    miniexprSC2000EQXFC			OBJECT IDENTIFIER ::= { evtzMiniExperimental 214 }
    miniexprSC2000			OBJECT IDENTIFIER ::= { evtzMiniExperimental 215 }
    miniexprCADIPASI7780			OBJECT IDENTIFIER ::= { evtzMiniExperimental 216 }
    miniexprGDAC2430RX2			OBJECT IDENTIFIER ::= { evtzMiniExperimental 217 }
    miniexprIA8EMRF			OBJECT IDENTIFIER ::= { evtzMiniExperimental 218 }
    miniexprPR23000EMR			OBJECT IDENTIFIER ::= { evtzMiniExperimental 219 }
    miniexprITX3080			OBJECT IDENTIFIER ::= { evtzMiniExperimental 220 }
    miniexpr1212T			OBJECT IDENTIFIER ::= { evtzMiniExperimental 221 }
    miniexpr1275T			OBJECT IDENTIFIER ::= { evtzMiniExperimental 222 }
    miniexprMUX3480			OBJECT IDENTIFIER ::= { evtzMiniExperimental 223 }
    miniexprMXPIG48IP3480			OBJECT IDENTIFIER ::= { evtzMiniExperimental 224 }
    miniexprVLPROPLOTTER			OBJECT IDENTIFIER ::= { evtzMiniExperimental 225 }
    miniexprNAT3080			OBJECT IDENTIFIER ::= { evtzMiniExperimental 226 }
    miniexprMUXIP3480			OBJECT IDENTIFIER ::= { evtzMiniExperimental 227 }
    miniexprADC27830MINI			OBJECT IDENTIFIER ::= { evtzMiniExperimental 228 }
    miniexprVIDEOPROC			OBJECT IDENTIFIER ::= { evtzMiniExperimental 229 }
    miniexprCE27837MINI			OBJECT IDENTIFIER ::= { evtzMiniExperimental 230 }
    miniexprVDA3G7860MINI			OBJECT IDENTIFIER ::= { evtzMiniExperimental 231 }
    miniexprFCEMRF			OBJECT IDENTIFIER ::= { evtzMiniExperimental 232 }
    miniexprRXSDI3030			OBJECT IDENTIFIER ::= { evtzMiniExperimental 233 }
    miniexprGDAC2431RX2			OBJECT IDENTIFIER ::= { evtzMiniExperimental 234 }
    miniexprMAGNUM			OBJECT IDENTIFIER ::= { evtzMiniExperimental 235 }
    miniexprCD27838			OBJECT IDENTIFIER ::= { evtzMiniExperimental 236 }
    miniexprMFX2J2K7881			OBJECT IDENTIFIER ::= { evtzMiniExperimental 237 }
    miniexprRX2430J2KIP			OBJECT IDENTIFIER ::= { evtzMiniExperimental 238 }
    miniexprMACNICA10GE			OBJECT IDENTIFIER ::= { evtzMiniExperimental 239 }
    miniexprIPGFASI27880			OBJECT IDENTIFIER ::= { evtzMiniExperimental 240 }
    miniexprRGBT2431TX2			OBJECT IDENTIFIER ::= { evtzMiniExperimental 241 }
    miniexprRGBT2432TX2			OBJECT IDENTIFIER ::= { evtzMiniExperimental 242 }
    miniexprEMRFC			OBJECT IDENTIFIER ::= { evtzMiniExperimental 243 }
    miniexprEXD7881AESU			OBJECT IDENTIFIER ::= { evtzMiniExperimental 244 }
    miniexprORT			OBJECT IDENTIFIER ::= { evtzMiniExperimental 245 }
    miniexprAUDIODEC			OBJECT IDENTIFIER ::= { evtzMiniExperimental 246 }
    miniexprXPRFFC			OBJECT IDENTIFIER ::= { evtzMiniExperimental 248 }
    miniexprREM3000RX9MTP			OBJECT IDENTIFIER ::= { evtzMiniExperimental 249 }
    miniexprREM3000TX9MTP			OBJECT IDENTIFIER ::= { evtzMiniExperimental 250 }
    miniexprSERIES3480			OBJECT IDENTIFIER ::= { evtzMiniExperimental 251 }
    miniexprEQXIP18AD3GTDM			OBJECT IDENTIFIER ::= { evtzMiniExperimental 252 }
    miniexprVIP10G3067			OBJECT IDENTIFIER ::= { evtzMiniExperimental 253 }
    miniexprENC7881J2K8MINI			OBJECT IDENTIFIER ::= { evtzMiniExperimental 254 }
    miniexprUDX2HD7814MINI			OBJECT IDENTIFIER ::= { evtzMiniExperimental 255 }
    miniexprDEC7881J2K8MINI			OBJECT IDENTIFIER ::= { evtzMiniExperimental 256 }
    miniexprDAMADI500			OBJECT IDENTIFIER ::= { evtzMiniExperimental 257 }
    miniexprADMX48X48			OBJECT IDENTIFIER ::= { evtzMiniExperimental 258 }
    miniexprX10G3080			OBJECT IDENTIFIER ::= { evtzMiniExperimental 259 }
    miniexprEQXMIOCOMMON			OBJECT IDENTIFIER ::= { evtzMiniExperimental 260 }
    miniexprVG7700			OBJECT IDENTIFIER ::= { evtzMiniExperimental 261 }
    miniexprAVB7820IPG			OBJECT IDENTIFIER ::= { evtzMiniExperimental 262 }
    miniexprADMX16X16A			OBJECT IDENTIFIER ::= { evtzMiniExperimental 263 }
    miniexprEXE			OBJECT IDENTIFIER ::= { evtzMiniExperimental 264 }
    miniexprMG7880			OBJECT IDENTIFIER ::= { evtzMiniExperimental 265 }
    miniexprUDC183GLITE3012			OBJECT IDENTIFIER ::= { evtzMiniExperimental 266 }
    miniexprVPDA2HD7815MINI			OBJECT IDENTIFIER ::= { evtzMiniExperimental 267 }
    miniexprUEP3080			OBJECT IDENTIFIER ::= { evtzMiniExperimental 268 }
    miniexprEXENCSA			OBJECT IDENTIFIER ::= { evtzMiniExperimental 269 }
    miniexprEXEVSR			OBJECT IDENTIFIER ::= { evtzMiniExperimental 270 }
    miniexprENC3080J2K			OBJECT IDENTIFIER ::= { evtzMiniExperimental 271 }
    miniexprEQXIP18IPG			OBJECT IDENTIFIER ::= { evtzMiniExperimental 272 }
    miniexprCD8A327880			OBJECT IDENTIFIER ::= { evtzMiniExperimental 273 }
    miniexprRGBT2431TX210G			OBJECT IDENTIFIER ::= { evtzMiniExperimental 274 }
    miniexprGDAC2431RX210G			OBJECT IDENTIFIER ::= { evtzMiniExperimental 275 }
    miniexprENC7880J2K10G			OBJECT IDENTIFIER ::= { evtzMiniExperimental 276 }
    miniexprENCX7882			OBJECT IDENTIFIER ::= { evtzMiniExperimental 277 }
    miniexprTS3080MADI10GE2			OBJECT IDENTIFIER ::= { evtzMiniExperimental 278 }
    miniexprMADI3080TS10GE2			OBJECT IDENTIFIER ::= { evtzMiniExperimental 279 }
    miniexprDEC7880J2K10G			OBJECT IDENTIFIER ::= { evtzMiniExperimental 280 }
    miniexprIPG7880HD610G			OBJECT IDENTIFIER ::= { evtzMiniExperimental 281 }
    miniexprEMR7800IO			OBJECT IDENTIFIER ::= { evtzMiniExperimental 282 }
    miniexprIPG5703G18SFP			OBJECT IDENTIFIER ::= { evtzMiniExperimental 283 }
    miniexprIO12MADI			OBJECT IDENTIFIER ::= { evtzMiniExperimental 284 }
    miniexprIO8MADI			OBJECT IDENTIFIER ::= { evtzMiniExperimental 285 }
    miniexprDPR22409			OBJECT IDENTIFIER ::= { evtzMiniExperimental 286 }
    miniexprVLPRODRMCATCHER			OBJECT IDENTIFIER ::= { evtzMiniExperimental 287 }
    miniexprUDCJ2K10GLT3012			OBJECT IDENTIFIER ::= { evtzMiniExperimental 288 }
    miniexprMMA10GIPX			OBJECT IDENTIFIER ::= { evtzMiniExperimental 289 }
    miniexprIPSR3080			OBJECT IDENTIFIER ::= { evtzMiniExperimental 291 }
    miniexprVIP10G30673GHW			OBJECT IDENTIFIER ::= { evtzMiniExperimental 292 }
    miniexprIPG5703G9SFP8			OBJECT IDENTIFIER ::= { evtzMiniExperimental 293 }
    miniexprENC7882H264HD			OBJECT IDENTIFIER ::= { evtzMiniExperimental 294 }
    miniexprMMA10GHUB			OBJECT IDENTIFIER ::= { evtzMiniExperimental 295 }
    miniexprRX243010G			OBJECT IDENTIFIER ::= { evtzMiniExperimental 296 }
    miniexprMVIP2			OBJECT IDENTIFIER ::= { evtzMiniExperimental 297 }
    miniexprVLPROSLASERVER			OBJECT IDENTIFIER ::= { evtzMiniExperimental 298 }
    miniexprFCAQ3405			OBJECT IDENTIFIER ::= { evtzMiniExperimental 299 }
    miniexprEQX10XPTG180			OBJECT IDENTIFIER ::= { evtzMiniExperimental 300 }
    miniexprR2X2ACS7800MINI			OBJECT IDENTIFIER ::= { evtzMiniExperimental 301 }
    miniexprDX4GPIO7880IP			OBJECT IDENTIFIER ::= { evtzMiniExperimental 302 }
    miniexprTR4800E			OBJECT IDENTIFIER ::= { evtzMiniExperimental 303 }
    miniexprIO7800ALINK2			OBJECT IDENTIFIER ::= { evtzMiniExperimental 304 }
    miniexprJ2K7882X2IPASI			OBJECT IDENTIFIER ::= { evtzMiniExperimental 305 }
    miniexprJ2K4788110GE2			OBJECT IDENTIFIER ::= { evtzMiniExperimental 306 }
    miniexprFC23405			OBJECT IDENTIFIER ::= { evtzMiniExperimental 307 }
    miniexprMSC7800MINI			OBJECT IDENTIFIER ::= { evtzMiniExperimental 308 }
    miniexprEQXFC4NET			OBJECT IDENTIFIER ::= { evtzMiniExperimental 309 }
    miniexprMMA10GIPGM6			OBJECT IDENTIFIER ::= { evtzMiniExperimental 312 }
    miniexprMMA10GTRXS			OBJECT IDENTIFIER ::= { evtzMiniExperimental 313 }
    miniexprVR44K10G2408			OBJECT IDENTIFIER ::= { evtzMiniExperimental 315 }
    miniexprMEDIATOR			OBJECT IDENTIFIER ::= { evtzMiniExperimental 316 }
    miniexprVT44K10G2408			OBJECT IDENTIFIER ::= { evtzMiniExperimental 317 }
    miniexprMMA10GVIP32			OBJECT IDENTIFIER ::= { evtzMiniExperimental 318 }
    miniexprDECX7882H264			OBJECT IDENTIFIER ::= { evtzMiniExperimental 319 }
    miniexprAG7890			OBJECT IDENTIFIER ::= { evtzMiniExperimental 320 }
    miniexprIXG7890			OBJECT IDENTIFIER ::= { evtzMiniExperimental 321 }
    miniexprIRDA7881MINI			OBJECT IDENTIFIER ::= { evtzMiniExperimental 322 }
    miniexprEQXOP18IPG			OBJECT IDENTIFIER ::= { evtzMiniExperimental 323 }
    miniexprMVP3000HDMI16			OBJECT IDENTIFIER ::= { evtzMiniExperimental 324 }
    miniexprEMR570TDMTS			OBJECT IDENTIFIER ::= { evtzMiniExperimental 325 }
    miniexprIPBLADE			OBJECT IDENTIFIER ::= { evtzMiniExperimental 326 }
    miniexprEMR7800TDM4			OBJECT IDENTIFIER ::= { evtzMiniExperimental 327 }
    miniexprUSRVAUDIOROUTER			OBJECT IDENTIFIER ::= { evtzMiniExperimental 328 }
    miniexprUSRVVIDEOPROC			OBJECT IDENTIFIER ::= { evtzMiniExperimental 329 }
    miniexprUSRVSYSTEM			OBJECT IDENTIFIER ::= { evtzMiniExperimental 330 }
    miniexprFC3606			OBJECT IDENTIFIER ::= { evtzMiniExperimental 331 }
    miniexprGMP5600			OBJECT IDENTIFIER ::= { evtzMiniExperimental 332 }
    miniexprEXELC100GIPG			OBJECT IDENTIFIER ::= { evtzMiniExperimental 333 }
    miniexprEXELC100GNAT			OBJECT IDENTIFIER ::= { evtzMiniExperimental 334 }
    miniexprIPPROCEXELCPM1A			OBJECT IDENTIFIER ::= { evtzMiniExperimental 335 }
    miniexprSLKE570H264			OBJECT IDENTIFIER ::= { evtzMiniExperimental 336 }
    miniexprIT37890			OBJECT IDENTIFIER ::= { evtzMiniExperimental 337 }
    miniexprMSC5700IP			OBJECT IDENTIFIER ::= { evtzMiniExperimental 338 }
    miniexprITXE570			OBJECT IDENTIFIER ::= { evtzMiniExperimental 339 }
    miniexprTRSM4KMMA10G			OBJECT IDENTIFIER ::= { evtzMiniExperimental 340 }
    miniexprMMA10GHUB2			OBJECT IDENTIFIER ::= { evtzMiniExperimental 341 }
    miniexprIPG570X19			OBJECT IDENTIFIER ::= { evtzMiniExperimental 342 }
    miniexprJ2K570X19			OBJECT IDENTIFIER ::= { evtzMiniExperimental 343 }
    miniexprDEC2RU			OBJECT IDENTIFIER ::= { evtzMiniExperimental 344 }
    miniexprUSRVSCALER			OBJECT IDENTIFIER ::= { evtzMiniExperimental 345 }
    miniexprUSRVKEYER			OBJECT IDENTIFIER ::= { evtzMiniExperimental 346 }
    miniexprADM3G7860			OBJECT IDENTIFIER ::= { evtzMiniExperimental 347 }
    miniexprTR7700			OBJECT IDENTIFIER ::= { evtzMiniExperimental 348 }
    miniexprEQT161612G			OBJECT IDENTIFIER ::= { evtzMiniExperimental 349 }
    miniexprUDPREPEATER			OBJECT IDENTIFIER ::= { evtzMiniExperimental 350 }
    miniexprEMR570AGHUB			OBJECT IDENTIFIER ::= { evtzMiniExperimental 351 }
    miniexprEV618VI4PL8X10G			OBJECT IDENTIFIER ::= { evtzMiniExperimental 352 }
    miniexprDMLB7880MINI			OBJECT IDENTIFIER ::= { evtzMiniExperimental 353 }
    miniexprCCCONDUCTOR			OBJECT IDENTIFIER ::= { evtzMiniExperimental 354 }
    miniexprPA7800			OBJECT IDENTIFIER ::= { evtzMiniExperimental 355 }
    miniexprEMR646412G			OBJECT IDENTIFIER ::= { evtzMiniExperimental 356 }
    miniexprGDAC2432RX2HDMI			OBJECT IDENTIFIER ::= { evtzMiniExperimental 357 }
    miniexprIXGCLOUDBRIDGE			OBJECT IDENTIFIER ::= { evtzMiniExperimental 358 }
    miniexprIPG570P12NAT			OBJECT IDENTIFIER ::= { evtzMiniExperimental 359 }
    miniexprITXE5872			OBJECT IDENTIFIER ::= { evtzMiniExperimental 360 }
    miniexprITXE5782			OBJECT IDENTIFIER ::= { evtzMiniExperimental 361 }
    miniexprMDM12G7800			OBJECT IDENTIFIER ::= { evtzMiniExperimental 362 }
    miniexprUEP570			OBJECT IDENTIFIER ::= { evtzMiniExperimental 363 }
    miniexprEQX10XPTGADMX			OBJECT IDENTIFIER ::= { evtzMiniExperimental 364 }
    miniexprCCVIRTUAL			OBJECT IDENTIFIER ::= { evtzMiniExperimental 365 }
    miniexprREM570RX910GE2			OBJECT IDENTIFIER ::= { evtzMiniExperimental 366 }
    miniexprREM570TX910GE2			OBJECT IDENTIFIER ::= { evtzMiniExperimental 367 }
    miniexprEVEO36SFP3CXP			OBJECT IDENTIFIER ::= { evtzMiniExperimental 368 }
    miniexprMG27890MINI			OBJECT IDENTIFIER ::= { evtzMiniExperimental 369 }
    miniexprFEC570			OBJECT IDENTIFIER ::= { evtzMiniExperimental 370 }
    miniexprMSC7800IP			OBJECT IDENTIFIER ::= { evtzMiniExperimental 371 }
    miniexprSRG7800IP			OBJECT IDENTIFIER ::= { evtzMiniExperimental 372 }
    miniexprEVBLADEZ10UDX			OBJECT IDENTIFIER ::= { evtzMiniExperimental 373 }
    miniexprAUTOTESTER			OBJECT IDENTIFIER ::= { evtzMiniExperimental 374 }
    miniexprX1202			OBJECT IDENTIFIER ::= { evtzMiniExperimental 375 }
    miniexprIPG570X1925G			OBJECT IDENTIFIER ::= { evtzMiniExperimental 376 }
    miniexprMG3090MINI			OBJECT IDENTIFIER ::= { evtzMiniExperimental 377 }
    miniexprEVRSC			OBJECT IDENTIFIER ::= { evtzMiniExperimental 380 }
    miniexprEVR12812G			OBJECT IDENTIFIER ::= { evtzMiniExperimental 381 }
    miniexprIRDS2X7882MINI			OBJECT IDENTIFIER ::= { evtzMiniExperimental 382 }
    miniexprASI570X1910GE2			OBJECT IDENTIFIER ::= { evtzMiniExperimental 383 }
    miniexprDMVSB7880			OBJECT IDENTIFIER ::= { evtzMiniExperimental 384 }
    miniexprDMVSB7880MINI			OBJECT IDENTIFIER ::= { evtzMiniExperimental 385 }
    miniexprFP3606			OBJECT IDENTIFIER ::= { evtzMiniExperimental 386 }
    miniexprEVBLADEZ10SW			OBJECT IDENTIFIER ::= { evtzMiniExperimental 387 }
    miniexprDEC7882H264MINI			OBJECT IDENTIFIER ::= { evtzMiniExperimental 388 }
    miniexprDEC7882SD2MINI			OBJECT IDENTIFIER ::= { evtzMiniExperimental 389 }
    miniexprND7860			OBJECT IDENTIFIER ::= { evtzMiniExperimental 390 }
    miniexprEQXOP18AE3G2TDM			OBJECT IDENTIFIER ::= { evtzMiniExperimental 391 }
    miniexprDMDVBT7880MINI			OBJECT IDENTIFIER ::= { evtzMiniExperimental 392 }
    miniexprEQXOP18A4GB2TDM			OBJECT IDENTIFIER ::= { evtzMiniExperimental 393 }
    miniexprEQXOP16A4GB2TDM			OBJECT IDENTIFIER ::= { evtzMiniExperimental 394 }
    miniexprEVRVIP			OBJECT IDENTIFIER ::= { evtzMiniExperimental 395 }
    miniexprSLKEQ			OBJECT IDENTIFIER ::= { evtzMiniExperimental 396 }
    miniexprRX243025G			OBJECT IDENTIFIER ::= { evtzMiniExperimental 397 }
    miniexprEVBLADEZ10VPROC			OBJECT IDENTIFIER ::= { evtzMiniExperimental 398 }
    miniexprEXELXCMONITOR			OBJECT IDENTIFIER ::= { evtzMiniExperimental 399 }
    miniexprEVBLADEZ10IPDLY			OBJECT IDENTIFIER ::= { evtzMiniExperimental 400 }
    miniexprIPG570FSE6X19			OBJECT IDENTIFIER ::= { evtzMiniExperimental 401 }
    miniexprMMA10GHUBAUDIO			OBJECT IDENTIFIER ::= { evtzMiniExperimental 402 }
    miniexprEVBLADEAPDOLBYP			OBJECT IDENTIFIER ::= { evtzMiniExperimental 403 }
    miniexprEVBLADEAPSW			OBJECT IDENTIFIER ::= { evtzMiniExperimental 404 }
    miniexprDMSAT7882MINI			OBJECT IDENTIFIER ::= { evtzMiniExperimental 405 }
    miniexprMG7892MINI			OBJECT IDENTIFIER ::= { evtzMiniExperimental 406 }
    miniexprEVMV25G2XQSFP			OBJECT IDENTIFIER ::= { evtzMiniExperimental 407 }
    miniexprIRDSAT7882MINI			OBJECT IDENTIFIER ::= { evtzMiniExperimental 408 }
    miniexprDREAMCATCHER			OBJECT IDENTIFIER ::= { evtzMiniExperimental 409 }
    miniexprENC570			OBJECT IDENTIFIER ::= { evtzMiniExperimental 410 }
    miniexprDSK4K25G570			OBJECT IDENTIFIER ::= { evtzMiniExperimental 411 }
    miniexprIPG670X19			OBJECT IDENTIFIER ::= { evtzMiniExperimental 412 }
    miniexprEQXIP184GB			OBJECT IDENTIFIER ::= { evtzMiniExperimental 413 }
    miniexprEQXOP184GB			OBJECT IDENTIFIER ::= { evtzMiniExperimental 414 }
    miniexprEMR7800XPT			OBJECT IDENTIFIER ::= { evtzMiniExperimental 415 }
    miniexprEMR9821AGHUB			OBJECT IDENTIFIER ::= { evtzMiniExperimental 416 }
    miniexprIVEMULTICAST			OBJECT IDENTIFIER ::= { evtzMiniExperimental 417 }
    miniexprVLPROPTXPROXY			OBJECT IDENTIFIER ::= { evtzMiniExperimental 418 }
    miniexprXRF4FC			OBJECT IDENTIFIER ::= { evtzMiniExperimental 419 }
    miniexprHDC570X1925G			OBJECT IDENTIFIER ::= { evtzMiniExperimental 420 }
    miniexprEMR570ADMX			OBJECT IDENTIFIER ::= { evtzMiniExperimental 421 }
    miniexprEQXIP1825G			OBJECT IDENTIFIER ::= { evtzMiniExperimental 422 }
    miniexprMMA10GHUBUSB			OBJECT IDENTIFIER ::= { evtzMiniExperimental 423 }
    miniexprMIOUSB			OBJECT IDENTIFIER ::= { evtzMiniExperimental 424 }
    miniexprEVBLADEZ10IPDL4			OBJECT IDENTIFIER ::= { evtzMiniExperimental 425 }
    miniexprDX83G7860			OBJECT IDENTIFIER ::= { evtzMiniExperimental 426 }
    miniexprDX83G7821			OBJECT IDENTIFIER ::= { evtzMiniExperimental 427 }
    miniexprACO570X1925G			OBJECT IDENTIFIER ::= { evtzMiniExperimental 428 }
    miniexprDCMIO			OBJECT IDENTIFIER ::= { evtzMiniExperimental 429 }
    miniexprACO570X1910G			OBJECT IDENTIFIER ::= { evtzMiniExperimental 430 }
    miniexprEQXIP1812G			OBJECT IDENTIFIER ::= { evtzMiniExperimental 431 }
    miniexprEQXOP1812G			OBJECT IDENTIFIER ::= { evtzMiniExperimental 432 }
    miniexprEQX10XPT12G180			OBJECT IDENTIFIER ::= { evtzMiniExperimental 433 }
    miniexprSCORPION2IP			OBJECT IDENTIFIER ::= { evtzMiniExperimental 434 }
    miniexprMIONDI			OBJECT IDENTIFIER ::= { evtzMiniExperimental 435 }
    miniexprEVMVVIP100G			OBJECT IDENTIFIER ::= { evtzMiniExperimental 436 }
    miniexprFC3406			OBJECT IDENTIFIER ::= { evtzMiniExperimental 437 }
    miniexprMIOGERJ45IP			OBJECT IDENTIFIER ::= { evtzMiniExperimental 438 }
    miniexprMIOBLADEUDX			OBJECT IDENTIFIER ::= { evtzMiniExperimental 439 }
    miniexprNAT570X1925G			OBJECT IDENTIFIER ::= { evtzMiniExperimental 440 }
    miniexprIM570X1910G			OBJECT IDENTIFIER ::= { evtzMiniExperimental 441 }
    miniexprSLKD570			OBJECT IDENTIFIER ::= { evtzMiniExperimental 442 }
    miniexprSLKE570			OBJECT IDENTIFIER ::= { evtzMiniExperimental 443 }
    miniexprTG100G570			OBJECT IDENTIFIER ::= { evtzMiniExperimental 444 }
    miniexprMIOHDMI4KIP			OBJECT IDENTIFIER ::= { evtzMiniExperimental 445 }
    miniexprEVBLADEZ10GWAY			OBJECT IDENTIFIER ::= { evtzMiniExperimental 446 }
    miniexprEVIPG			OBJECT IDENTIFIER ::= { evtzMiniExperimental 447 }
    miniexprMIOBLADE2QUAD			OBJECT IDENTIFIER ::= { evtzMiniExperimental 448 }
    miniexprSCORPIONX18ETH			OBJECT IDENTIFIER ::= { evtzMiniExperimental 449 }
    miniexprEQXIPAD25GE			OBJECT IDENTIFIER ::= { evtzMiniExperimental 450 }
    miniexprMIOHDMIIN3G			OBJECT IDENTIFIER ::= { evtzMiniExperimental 451 }
    miniexprSCORPION18PS6			OBJECT IDENTIFIER ::= { evtzMiniExperimental 452 }
    miniexprRFPROBE9000			OBJECT IDENTIFIER ::= { evtzMiniExperimental 453 }
    miniexprMMA10GRS4K4U			OBJECT IDENTIFIER ::= { evtzMiniExperimental 454 }
    miniexprMIOHDMIOUT3G			OBJECT IDENTIFIER ::= { evtzMiniExperimental 455 }
    miniexprMIOAPPUDX4K			OBJECT IDENTIFIER ::= { evtzMiniExperimental 456 }
    miniexprREM570TX25G			OBJECT IDENTIFIER ::= { evtzMiniExperimental 457 }
    miniexprT1378088RF			OBJECT IDENTIFIER ::= { evtzMiniExperimental 458 }
    miniexprASRUN			OBJECT IDENTIFIER ::= { evtzMiniExperimental 459 }
    miniexprSCORPIONFC			OBJECT IDENTIFIER ::= { evtzMiniExperimental 460 }
    miniexprSW7800GE			OBJECT IDENTIFIER ::= { evtzMiniExperimental 461 }
    miniexprMIODE			OBJECT IDENTIFIER ::= { evtzMiniExperimental 462 }
    miniexprMIODD			OBJECT IDENTIFIER ::= { evtzMiniExperimental 463 }
    miniexprMIOAESD4			OBJECT IDENTIFIER ::= { evtzMiniExperimental 464 }
    miniexprSCORPIONX18IPG			OBJECT IDENTIFIER ::= { evtzMiniExperimental 465 }
    miniexprSCORPIONX18ETHR			OBJECT IDENTIFIER ::= { evtzMiniExperimental 466 }
    miniexprSCORPIONX18J2K			OBJECT IDENTIFIER ::= { evtzMiniExperimental 467 }
    miniexprMIODM4LB4			OBJECT IDENTIFIER ::= { evtzMiniExperimental 468 }
    miniexprR78088RF			OBJECT IDENTIFIER ::= { evtzMiniExperimental 469 }
    miniexprEMR7800HYDRA2			OBJECT IDENTIFIER ::= { evtzMiniExperimental 470 }
    miniexprMIOMVHDMIIP			OBJECT IDENTIFIER ::= { evtzMiniExperimental 471 }
    miniexprEQXJ2KXS			OBJECT IDENTIFIER ::= { evtzMiniExperimental 472 }
    miniexprMIOXS			OBJECT IDENTIFIER ::= { evtzMiniExperimental 473 }
    miniexprXS570X1910G			OBJECT IDENTIFIER ::= { evtzMiniExperimental 474 }
    miniexprHBX670X45			OBJECT IDENTIFIER ::= { evtzMiniExperimental 475 }
    miniexprMIOCC			OBJECT IDENTIFIER ::= { evtzMiniExperimental 476 }
    miniexprXS570X1925G			OBJECT IDENTIFIER ::= { evtzMiniExperimental 477 }
    miniexprSCORPION6			OBJECT IDENTIFIER ::= { evtzMiniExperimental 478 }
    miniexprMIODLY2			OBJECT IDENTIFIER ::= { evtzMiniExperimental 479 }
    miniexprXPS5782			OBJECT IDENTIFIER ::= { evtzMiniExperimental 480 }
    miniexprSCORPIONS18			OBJECT IDENTIFIER ::= { evtzMiniExperimental 481 }
    miniexprEQXIP18AD			OBJECT IDENTIFIER ::= { evtzMiniExperimental 482 }
    miniexprEQXOP18AE			OBJECT IDENTIFIER ::= { evtzMiniExperimental 483 }
    miniexprMIOCD2			OBJECT IDENTIFIER ::= { evtzMiniExperimental 484 }
    miniexprMIOIXG			OBJECT IDENTIFIER ::= { evtzMiniExperimental 485 }
    miniexprMIODSP			OBJECT IDENTIFIER ::= { evtzMiniExperimental 486 }
    miniexprEXENAT			OBJECT IDENTIFIER ::= { evtzMiniExperimental 487 }
    miniexprXPS570APP			OBJECT IDENTIFIER ::= { evtzMiniExperimental 488 }
END
