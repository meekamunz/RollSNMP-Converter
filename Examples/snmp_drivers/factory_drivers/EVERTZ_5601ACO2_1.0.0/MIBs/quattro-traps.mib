-- Copyright 2002 Evertz Microsystems Ltd.

QUATTRO-TRAPS DEFINITIONS ::= BEGIN

IMPORTS
	quattroInstance, quattroTraps
		FROM QUATTRO-MIB
	TRAP-TYPE
		FROM RFC-1215;

	trapFault	OBJECT IDENTIFIER ::= { quattroTraps 1 }


-- beginning of fault Condition 1 Quadrant 1 trap

	faultCondition1FalseQuadrant1 TRAP-TYPE
		ENTERPRISE	trapFault
		VARIABLES	{ quattroInstance }
		DESCRIPTION
			"Fault Condition 1 Cleared"
	::= 1000

	faultCondition1TrueQuadrant1 TRAP-TYPE
		ENTERPRISE	trapFault
		VARIABLES	{ quattroInstance }
		DESCRIPTION
			"Fault Condition 1 Alert"
	::= 1001

-- end of fault Condition1 Quadrant 1 trap
-- beginning of Condition1 Quadrant2 trap

	faultCondition1FalseQuadrant2 TRAP-TYPE
		ENTERPRISE	trapFault
		VARIABLES	{ quattroInstance }
		DESCRIPTION
			"Fault Condition 1 Cleared"
	::= 1002

	faultCondition1TrueQuadrant2 TRAP-TYPE
		ENTERPRISE	trapFault
		VARIABLES	{ quattroInstance }
		DESCRIPTION
			"Fault Condition 1 Alert"
	::= 1003

-- end of Condition1 Quadrant2 trap
-- beginning of Condition1 Quadrant3 trap

	faultCondition1FalseQuadrant3 TRAP-TYPE
		ENTERPRISE	trapFault
		VARIABLES	{ quattroInstance }
		DESCRIPTION
			"Fault Condition 1 Cleared"
	::= 1004

	faultCondition1TrueQuadrant3 TRAP-TYPE
		ENTERPRISE	trapFault
		VARIABLES	{ quattroInstance }
		DESCRIPTION
			"Fault Condition 1 Alert"
	::= 1005

-- end of Condition1 Quadrant3 trap
-- beginning of Condition1 Quadrant4 trap

	faultCondition1FalseQuadrant4 TRAP-TYPE
		ENTERPRISE	trapFault
		VARIABLES	{ quattroInstance }
		DESCRIPTION
			"Fault Condition 1 Cleared"
	::= 1006

	faultCondition1TrueQuadrant4 TRAP-TYPE
		ENTERPRISE	trapFault
		VARIABLES	{ quattroInstance }
		DESCRIPTION
			"Fault Condition 1 Alert"
	::= 1007

-- end of Condition1 Quadrant4 trap
-- beginning of Condition2 Quadrant1 trap

	faultCondition2FalseQuadrant1 TRAP-TYPE
		ENTERPRISE	trapFault
		VARIABLES	{ quattroInstance }
		DESCRIPTION
			"Fault Condition 2 Cleared"
	::= 1008

	faultCondition2TrueQuadrant1 TRAP-TYPE
		ENTERPRISE	trapFault
		VARIABLES	{ quattroInstance }
		DESCRIPTION
			"Fault Condition 2 Alert"
	::= 1009

-- end of Condition2 Quadrant1 trap
-- beginning of Condition2 Quadrant2 trap

	faultCondition2FalseQuadrant2 TRAP-TYPE
		ENTERPRISE	trapFault
		VARIABLES	{ quattroInstance }
		DESCRIPTION
			"Fault Condition 2 Cleared"
	::= 1010

	faultCondition2TrueQuadrant2 TRAP-TYPE
		ENTERPRISE	trapFault
		VARIABLES	{ quattroInstance }
		DESCRIPTION
			"Fault Condition 2 Alert"
	::= 1011

-- end of Condition2 Quadrant2 trap
-- beginning of Condition2 Quadrant3 trap

	faultCondition2FalseQuadrant3 TRAP-TYPE
		ENTERPRISE	trapFault
		VARIABLES	{ quattroInstance }
		DESCRIPTION
			"Fault Condition 2 Cleared"
	::= 1012

	faultCondition2TrueQuadrant3 TRAP-TYPE
		ENTERPRISE	trapFault
		VARIABLES	{ quattroInstance }
		DESCRIPTION
			"Fault Condition 2 Alert"
	::= 1013

-- end of Condition2 Quadrant3 trap
-- beginning of Condition2 Quadrant4 trap

	faultCondition2FalseQuadrant4 TRAP-TYPE
		ENTERPRISE	trapFault
		VARIABLES	{ quattroInstance }
		DESCRIPTION
			"Fault Condition 2 Cleared"
	::= 1014

	faultCondition2TrueQuadrant4 TRAP-TYPE
		ENTERPRISE	trapFault
		VARIABLES	{ quattroInstance }
		DESCRIPTION
			"Fault Condition 2 Alert"
	::= 1015

-- end of Condition2 Quadrant4 trap
-- beginning of Condition3 Quadrant1 trap

	faultCondition3FalseQuadrant1 TRAP-TYPE
		ENTERPRISE	trapFault
		VARIABLES	{ quattroInstance }
		DESCRIPTION
			"Fault Condition 3 Cleared"
	::= 1016

	faultCondition3TrueQuadrant1 TRAP-TYPE
		ENTERPRISE	trapFault
		VARIABLES	{ quattroInstance }
		DESCRIPTION
			"Fault Condition 3 Alert"
	::= 1017

-- end of Condition3 Quadrant1 trap
-- beginning of Condition3 Quadrant2 trap

	faultCondition3FalseQuadrant2 TRAP-TYPE
		ENTERPRISE	trapFault
		VARIABLES	{ quattroInstance }
		DESCRIPTION
			"Fault Condition 3 Cleared"
	::= 1018

	faultCondition3TrueQuadrant2 TRAP-TYPE
		ENTERPRISE	trapFault
		VARIABLES	{ quattroInstance }
		DESCRIPTION
			"Fault Condition 3 Alert"
	::= 1019

-- end of Condition3 Quadrant2 trap
-- beginning of Condition3 Quadrant3 trap

	faultCondition3FalseQuadrant3 TRAP-TYPE
		ENTERPRISE	trapFault
		VARIABLES	{ quattroInstance }
		DESCRIPTION
			"Fault Condition 3 Cleared"
	::= 1020

	faultCondition3TrueQuadrant3 TRAP-TYPE
		ENTERPRISE	trapFault
		VARIABLES	{ quattroInstance }
		DESCRIPTION
			"Fault Condition 3 Alert"
	::= 1021

-- end of Condition3 Quadrant3 trap
-- beginning of Condition3 Quadrant4 trap

	faultCondition3FalseQuadrant4 TRAP-TYPE
		ENTERPRISE	trapFault
		VARIABLES	{ quattroInstance }
		DESCRIPTION
			"Fault Condition 3 Cleared"
	::= 1022

	faultCondition3TrueQuadrant4 TRAP-TYPE
		ENTERPRISE	trapFault
		VARIABLES	{ quattroInstance }
		DESCRIPTION
			"Fault Condition 3 Alert"
	::= 1023

-- end of Condition3 Quadrant4 trap
-- beginning of Condition4 Quadrant1 trap

	faultCondition4FalseQuadrant1 TRAP-TYPE
		ENTERPRISE	trapFault
		VARIABLES	{ quattroInstance }
		DESCRIPTION
			"Fault Condition 4 Cleared"
	::= 1024

	faultCondition4TrueQuadrant1 TRAP-TYPE
		ENTERPRISE	trapFault
		VARIABLES	{ quattroInstance }
		DESCRIPTION
			"Fault Condition 4 Alert"
	::= 1025

-- end of Condition4 Quadrant1 trap
-- beginning of Condition4 Quadrant2 trap

	faultCondition4FalseQuadrant2 TRAP-TYPE
		ENTERPRISE	trapFault
		VARIABLES	{ quattroInstance }
		DESCRIPTION
			"Fault Condition 4 Cleared"
	::= 1026

	faultCondition4TrueQuadrant2 TRAP-TYPE
		ENTERPRISE	trapFault
		VARIABLES	{ quattroInstance }
		DESCRIPTION
			"Fault Condition 4 Alert"
	::= 1027

-- end of Condition4 Quadrant2 trap
-- beginning of Condition4 Quadrant3 trap

	faultCondition4FalseQuadrant3 TRAP-TYPE
		ENTERPRISE	trapFault
		VARIABLES	{ quattroInstance }
		DESCRIPTION
			"Fault Condition 4 Cleared"
	::= 1028

	faultCondition4TrueQuadrant3 TRAP-TYPE
		ENTERPRISE	trapFault
		VARIABLES	{ quattroInstance }
		DESCRIPTION
			"Fault Condition 4 Alert"
	::= 1029

-- end of Condition4 Quadrant3 trap
-- beginning of Condition4 Quadrant4 trap

	faultCondition4FalseQuadrant4 TRAP-TYPE
		ENTERPRISE	trapFault
		VARIABLES	{ quattroInstance }
		DESCRIPTION
			"Fault Condition 4 Cleared"
	::= 1030

	faultCondition4TrueQuadrant4 TRAP-TYPE
		ENTERPRISE	trapFault
		VARIABLES	{ quattroInstance }
		DESCRIPTION
			"Fault Condition 4 Alert"
	::= 1031

-- end of Condition4 Quadrant4 trap
-- beginning of videoInvalid videoSourceA trap

	faultvideoInvalidFalsevideoSourceA TRAP-TYPE
		ENTERPRISE	trapFault
		VARIABLES	{ quattroInstance }
		DESCRIPTION
			"Video OK"
	::= 1032

	faultvideoInvalidTruevideoSourceA TRAP-TYPE
		ENTERPRISE	trapFault
		VARIABLES	{ quattroInstance }
		DESCRIPTION
			"Video Missing"
	::= 1033

-- end of videoInvalid videoSourceA trap
-- beginning of videoInvalid videoSourceB trap

	faultvideoInvalidFalsevideoSourceB TRAP-TYPE
		ENTERPRISE	trapFault
		VARIABLES	{ quattroInstance }
		DESCRIPTION
			"Video OK"
	::= 1034

	faultvideoInvalidTruevideoSourceB TRAP-TYPE
		ENTERPRISE	trapFault
		VARIABLES	{ quattroInstance }
		DESCRIPTION
			"Video Missing"
	::= 1035

-- end of videoInvalid videoSourceB trap
-- beginning of videoInvalid videoSourceC trap

	faultvideoInvalidFalsevideoSourceC TRAP-TYPE
		ENTERPRISE	trapFault
		VARIABLES	{ quattroInstance }
		DESCRIPTION
			"Video OK"
	::= 1036

	faultvideoInvalidTruevideoSourceC TRAP-TYPE
		ENTERPRISE	trapFault
		VARIABLES	{ quattroInstance }
		DESCRIPTION
			"Video Missing"
	::= 1037

-- end of videoInvalid videoSourceC trap
-- beginning of videoInvalid videoSourceD trap

	faultvideoInvalidFalsevideoSourceD TRAP-TYPE
		ENTERPRISE	trapFault
		VARIABLES	{ quattroInstance }
		DESCRIPTION
			"Video OK"
	::= 1038

	faultvideoInvalidTruevideoSourceD TRAP-TYPE
		ENTERPRISE	trapFault
		VARIABLES	{ quattroInstance }
		DESCRIPTION
			"Video Missing"
	::= 1039

-- end of videoInvalid videoSourceD trap
-- beginning of lossOfAudio videoSourceA trap

	faultlossOfAudioFalsevideoSourceA TRAP-TYPE
		ENTERPRISE	trapFault
		VARIABLES	{ quattroInstance }
		DESCRIPTION
			"Audio OK"
	::= 1040

	faultlossOfAudioTruevideoSourceA TRAP-TYPE
		ENTERPRISE	trapFault
		VARIABLES	{ quattroInstance }
		DESCRIPTION
			"Audio Missing"
	::= 1041

-- end of lossOfAudio videoSourceA trap
-- beginning of lossOfAudio videoSourceB trap

	faultlossOfAudioFalsevideoSourceB TRAP-TYPE
		ENTERPRISE	trapFault
		VARIABLES	{ quattroInstance }
		DESCRIPTION
			"Audio OK"
	::= 1042

	faultlossOfAudioTruevideoSourceB TRAP-TYPE
		ENTERPRISE	trapFault
		VARIABLES	{ quattroInstance }
		DESCRIPTION
			"Audio Missing"
	::= 1043

-- end of lossOfAudio videoSourceB trap
-- beginning of lossOfAudio videoSourceC trap

	faultlossOfAudioFalsevideoSourceC TRAP-TYPE
		ENTERPRISE	trapFault
		VARIABLES	{ quattroInstance }
		DESCRIPTION
			"Audio OK"
	::= 1044

	faultlossOfAudioTruevideoSourceC TRAP-TYPE
		ENTERPRISE	trapFault
		VARIABLES	{ quattroInstance }
		DESCRIPTION
			"Audio Missing"
	::= 1045

-- end of lossOfAudio videoSourceC trap
-- beginning of lossOfAudio videoSourceD trap

	faultlossOfAudioFalsevideoSourceD TRAP-TYPE
		ENTERPRISE	trapFault
		VARIABLES	{ quattroInstance }
		DESCRIPTION
			"Audio OK"
	::= 1046

	faultlossOfAudioTruevideoSourceD TRAP-TYPE
		ENTERPRISE	trapFault
		VARIABLES	{ quattroInstance }
		DESCRIPTION
			"Audio Missing"
	::= 1047

-- end of lossOfAudio videoSourceD trap
-- beginning of lossOfAudio12 videoSourceA trap

	faultlossOfAudio12FalsevideoSourceA TRAP-TYPE
		ENTERPRISE	trapFault
		VARIABLES	{ quattroInstance }
		DESCRIPTION
			"Audio Ch1/2 OK"
	::= 1048

	faultlossOfAudio12TruevideoSourceA TRAP-TYPE
		ENTERPRISE	trapFault
		VARIABLES	{ quattroInstance }
		DESCRIPTION
			"Audio Ch1/2 Missing"
	::= 1049

-- end of lossOfAudio12 videoSourceA trap
-- beginning of lossOfAudio12 videoSourceB trap

	faultlossOfAudio12FalsevideoSourceB TRAP-TYPE
		ENTERPRISE	trapFault
		VARIABLES	{ quattroInstance }
		DESCRIPTION
			"Audio Ch1/2 OK"
	::= 1050

	faultlossOfAudio12TruevideoSourceB TRAP-TYPE
		ENTERPRISE	trapFault
		VARIABLES	{ quattroInstance }
		DESCRIPTION
			"Audio Ch1/2 Missing"
	::= 1051

-- end of lossOfAudio12 videoSourceB trap
-- beginning of lossOfAudio12 videoSourceC trap

	faultlossOfAudio12FalsevideoSourceC TRAP-TYPE
		ENTERPRISE	trapFault
		VARIABLES	{ quattroInstance }
		DESCRIPTION
			"Audio Ch1/2 OK"
	::= 1052

	faultlossOfAudio12TruevideoSourceC TRAP-TYPE
		ENTERPRISE	trapFault
		VARIABLES	{ quattroInstance }
		DESCRIPTION
			"Audio Ch1/2 Missing"
	::= 1053

-- end of lossOfAudio12 videoSourceC trap
-- beginning of lossOfAudio12 videoSourceD trap

	faultlossOfAudio12FalsevideoSourceD TRAP-TYPE
		ENTERPRISE	trapFault
		VARIABLES	{ quattroInstance }
		DESCRIPTION
			"Audio Ch1/2 OK"
	::= 1054

	faultlossOfAudio12TruevideoSourceD TRAP-TYPE
		ENTERPRISE	trapFault
		VARIABLES	{ quattroInstance }
		DESCRIPTION
			"Audio Ch1/2 Missing"
	::= 1055

-- end of lossOfAudio12 videoSourceD trap
-- beginning of lossOfAudio34 videoSourceA trap

	faultlossOfAudio34FalsevideoSourceA TRAP-TYPE
		ENTERPRISE	trapFault
		VARIABLES	{ quattroInstance }
		DESCRIPTION
			"Audio Ch3/4 OK"
	::= 1056

	faultlossOfAudio34TruevideoSourceA TRAP-TYPE
		ENTERPRISE	trapFault
		VARIABLES	{ quattroInstance }
		DESCRIPTION
			"Audio Ch3/4 Missing"
	::= 1057

-- end of lossOfAudio34 videoSourceA trap
-- beginning of lossOfAudio34 videoSourceB trap

	faultlossOfAudio34FalsevideoSourceB TRAP-TYPE
		ENTERPRISE	trapFault
		VARIABLES	{ quattroInstance }
		DESCRIPTION
			"Audio Ch3/4 OK"
	::= 1058

	faultlossOfAudio34TruevideoSourceB TRAP-TYPE
		ENTERPRISE	trapFault
		VARIABLES	{ quattroInstance }
		DESCRIPTION
			"Audio Ch3/4 Missing"
	::= 1059

-- end of lossOfAudio34 videoSourceB trap
-- beginning of lossOfAudio34 videoSourceC trap

	faultlossOfAudio34FalsevideoSourceC TRAP-TYPE
		ENTERPRISE	trapFault
		VARIABLES	{ quattroInstance }
		DESCRIPTION
			"Audio Ch3/4 OK"
	::= 1060

	faultlossOfAudio34TruevideoSourceC TRAP-TYPE
		ENTERPRISE	trapFault
		VARIABLES	{ quattroInstance }
		DESCRIPTION
			"Audio Ch3/4 Missing"
	::= 1061

-- end of lossOfAudio34 videoSourceC trap
-- beginning of lossOfAudio34 videoSourceD trap

	faultlossOfAudio34FalsevideoSourceD TRAP-TYPE
		ENTERPRISE	trapFault
		VARIABLES	{ quattroInstance }
		DESCRIPTION
			"Audio Ch3/4 OK"
	::= 1062

	faultlossOfAudio34TruevideoSourceD TRAP-TYPE
		ENTERPRISE	trapFault
		VARIABLES	{ quattroInstance }
		DESCRIPTION
			"Audio Ch3/4 Missing"
	::= 1063

-- end of lossOfAudio34 videoSourceD trap
-- beginning of lossOfAudio56 videoSourceA trap

	faultlossOfAudio56FalsevideoSourceA TRAP-TYPE
		ENTERPRISE	trapFault
		VARIABLES	{ quattroInstance }
		DESCRIPTION
			"Audio Ch5/6 OK"
	::= 1064

	faultlossOfAudio56TruevideoSourceA TRAP-TYPE
		ENTERPRISE	trapFault
		VARIABLES	{ quattroInstance }
		DESCRIPTION
			"Audio Ch5/6 Missing"
	::= 1065

-- end of lossOfAudio56 videoSourceA trap
-- beginning of lossOfAudio56 videoSourceB trap

	faultlossOfAudio56FalsevideoSourceB TRAP-TYPE
		ENTERPRISE	trapFault
		VARIABLES	{ quattroInstance }
		DESCRIPTION
			"Audio Ch5/6 OK"
	::= 1066

	faultlossOfAudio56TruevideoSourceB TRAP-TYPE
		ENTERPRISE	trapFault
		VARIABLES	{ quattroInstance }
		DESCRIPTION
			"Audio Ch5/6 Missing"
	::= 1067

-- end of lossOfAudio56 videoSourceB trap
-- beginning of lossOfAudio56 videoSourceC trap

	faultlossOfAudio56FalsevideoSourceC TRAP-TYPE
		ENTERPRISE	trapFault
		VARIABLES	{ quattroInstance }
		DESCRIPTION
			"Audio Ch5/6 OK"
	::= 1068

	faultlossOfAudio56TruevideoSourceC TRAP-TYPE
		ENTERPRISE	trapFault
		VARIABLES	{ quattroInstance }
		DESCRIPTION
			"Audio Ch5/6 Missing"
	::= 1069

-- end of lossOfAudio56 videoSourceC trap
-- beginning of lossOfAudio56 videoSourceD trap

	faultlossOfAudio56FalsevideoSourceD TRAP-TYPE
		ENTERPRISE	trapFault
		VARIABLES	{ quattroInstance }
		DESCRIPTION
			"Audio Ch5/6 OK"
	::= 1070

	faultlossOfAudio56TruevideoSourceD TRAP-TYPE
		ENTERPRISE	trapFault
		VARIABLES	{ quattroInstance }
		DESCRIPTION
			"Audio Ch5/6 Missing"
	::= 1071

-- end of lossOfAudio56 videoSourceD trap
-- beginning of apEDHError videoSourceA trap

	faultapEDHErrorFalsevideoSourceA TRAP-TYPE
		ENTERPRISE	trapFault
		VARIABLES	{ quattroInstance }
		DESCRIPTION
			"Active Picture EDH Error Cleared"
	::= 1072

	faultapEDHErrorTruevideoSourceA TRAP-TYPE
		ENTERPRISE	trapFault
		VARIABLES	{ quattroInstance }
		DESCRIPTION
			"Active Picture EDH Error Present"
	::= 1073

-- end of apEDHError videoSourceA trap
-- beginning of apEDHError videoSourceB trap

	faultapEDHErrorFalsevideoSourceB TRAP-TYPE
		ENTERPRISE	trapFault
		VARIABLES	{ quattroInstance }
		DESCRIPTION
			"Active Picture EDH Error Cleared"
	::= 1074

	faultapEDHErrorTruevideoSourceB TRAP-TYPE
		ENTERPRISE	trapFault
		VARIABLES	{ quattroInstance }
		DESCRIPTION
			"Active Picture EDH Error Present"
	::= 1075

-- end of apEDHError videoSourceB trap
-- beginning of apEDHError videoSourceC trap

	faultapEDHErrorFalsevideoSourceC TRAP-TYPE
		ENTERPRISE	trapFault
		VARIABLES	{ quattroInstance }
		DESCRIPTION
			"Active Picture EDH Error Cleared"
	::= 1076

	faultapEDHErrorTruevideoSourceC TRAP-TYPE
		ENTERPRISE	trapFault
		VARIABLES	{ quattroInstance }
		DESCRIPTION
			"Active Picture EDH Error Present"
	::= 1077

-- end of apEDHError videoSourceC trap
-- beginning of apEDHError videoSourceD trap

	faultapEDHErrorFalsevideoSourceD TRAP-TYPE
		ENTERPRISE	trapFault
		VARIABLES	{ quattroInstance }
		DESCRIPTION
			"Active Picture EDH Error Cleared"
	::= 1078

	faultapEDHErrorTruevideoSourceD TRAP-TYPE
		ENTERPRISE	trapFault
		VARIABLES	{ quattroInstance }
		DESCRIPTION
			"Active Picture EDH Error Present"
	::= 1079

-- end of apEDHError videoSourceD trap
-- beginning of ffEDHError videoSourceA trap

	faultffEDHErrorFalsevideoSourceA TRAP-TYPE
		ENTERPRISE	trapFault
		VARIABLES	{ quattroInstance }
		DESCRIPTION
			"Full Field EDH Error Cleared"
	::= 1080

	faultffEDHErrorTruevideoSourceA TRAP-TYPE
		ENTERPRISE	trapFault
		VARIABLES	{ quattroInstance }
		DESCRIPTION
			"Full Field EDH Error Present"
	::= 1081

-- end of ffEDHError videoSourceA trap
-- beginning of ffEDHError videoSourceB trap

	faultffEDHErrorFalsevideoSourceB TRAP-TYPE
		ENTERPRISE	trapFault
		VARIABLES	{ quattroInstance }
		DESCRIPTION
			"Full Field EDH Error Cleared"
	::= 1082

	faultffEDHErrorTruevideoSourceB TRAP-TYPE
		ENTERPRISE	trapFault
		VARIABLES	{ quattroInstance }
		DESCRIPTION
			"Full Field EDH Error Present"
	::= 1083

-- end of ffEDHError videoSourceB trap
-- beginning of ffEDHError videoSourceC trap

	faultffEDHErrorFalsevideoSourceC TRAP-TYPE
		ENTERPRISE	trapFault
		VARIABLES	{ quattroInstance }
		DESCRIPTION
			"Full Field EDH Error Cleared"
	::= 1084

	faultffEDHErrorTruevideoSourceC TRAP-TYPE
		ENTERPRISE	trapFault
		VARIABLES	{ quattroInstance }
		DESCRIPTION
			"Full Field EDH Error Present"
	::= 1085

-- end of ffEDHError videoSourceC trap
-- beginning of ffEDHError videoSourceD trap

	faultffEDHErrorFalsevideoSourceD TRAP-TYPE
		ENTERPRISE	trapFault
		VARIABLES	{ quattroInstance }
		DESCRIPTION
			"Full Field EDH Error Cleared"
	::= 1086

	faultffEDHErrorTruevideoSourceD TRAP-TYPE
		ENTERPRISE	trapFault
		VARIABLES	{ quattroInstance }
		DESCRIPTION
			"Full Field EDH Error Present"
	::= 1087

-- end of ffEDHError videoSourceD trap
-- beginning of phaseReversal12 videoSourceA trap

	faultphaseReversal12FalsevideoSourceA TRAP-TYPE
		ENTERPRISE	trapFault
		VARIABLES	{ quattroInstance }
		DESCRIPTION
			"Audio Ch1/2 Phase OK"
	::= 1088

	faultphaseReversal12TruevideoSourceA TRAP-TYPE
		ENTERPRISE	trapFault
		VARIABLES	{ quattroInstance }
		DESCRIPTION
			"Audio Ch1/2 Phase Reversed"
	::= 1089

-- end of phaseReversal12 videoSourceA trap
-- beginning of phaseReversal12 videoSourceB trap

	faultphaseReversal12FalsevideoSourceB TRAP-TYPE
		ENTERPRISE	trapFault
		VARIABLES	{ quattroInstance }
		DESCRIPTION
			"Audio Ch1/2 Phase OK"
	::= 1090

	faultphaseReversal12TruevideoSourceB TRAP-TYPE
		ENTERPRISE	trapFault
		VARIABLES	{ quattroInstance }
		DESCRIPTION
			"Audio Ch1/2 Phase Reversed"
	::= 1091

-- end of phaseReversal12 videoSourceB trap
-- beginning of phaseReversal12 videoSourceC trap

	faultphaseReversal12FalsevideoSourceC TRAP-TYPE
		ENTERPRISE	trapFault
		VARIABLES	{ quattroInstance }
		DESCRIPTION
			"Audio Ch1/2 Phase OK"
	::= 1092

	faultphaseReversal12TruevideoSourceC TRAP-TYPE
		ENTERPRISE	trapFault
		VARIABLES	{ quattroInstance }
		DESCRIPTION
			"Audio Ch1/2 Phase Reversed"
	::= 1093

-- end of phaseReversal12 videoSourceC trap
-- beginning of phaseReversal12 videoSourceD trap

	faultphaseReversal12FalsevideoSourceD TRAP-TYPE
		ENTERPRISE	trapFault
		VARIABLES	{ quattroInstance }
		DESCRIPTION
			"Audio Ch1/2 Phase OK"
	::= 1094

	faultphaseReversal12TruevideoSourceD TRAP-TYPE
		ENTERPRISE	trapFault
		VARIABLES	{ quattroInstance }
		DESCRIPTION
			"Audio Ch1/2 Phase Reversed"
	::= 1095

-- end of phaseReversal12 videoSourceD trap
-- beginning of phaseReversal34 videoSourceA trap

	faultphaseReversal34FalsevideoSourceA TRAP-TYPE
		ENTERPRISE	trapFault
		VARIABLES	{ quattroInstance }
		DESCRIPTION
			"Audio Ch3/4 Phase OK"
	::= 1096

	faultphaseReversal34TruevideoSourceA TRAP-TYPE
		ENTERPRISE	trapFault
		VARIABLES	{ quattroInstance }
		DESCRIPTION
			"Audio Ch3/4 Phase Reverse "
	::= 1097

-- end of phaseReversal34 videoSourceA trap
-- beginning of phaseReversal34 videoSourceB trap

	faultphaseReversal34FalsevideoSourceB TRAP-TYPE
		ENTERPRISE	trapFault
		VARIABLES	{ quattroInstance }
		DESCRIPTION
			"Audio Ch3/4 Phase Ok"
	::= 1098

	faultphaseReversal34TruevideoSourceB TRAP-TYPE
		ENTERPRISE	trapFault
		VARIABLES	{ quattroInstance }
		DESCRIPTION
			"Audio Ch3/4 Phase Reversed"
	::= 1099

-- end of phaseReversal34 videoSourceB trap
-- beginning of phaseReversal34 videoSourceC trap

	faultphaseReversal34FalsevideoSourceC TRAP-TYPE
		ENTERPRISE	trapFault
		VARIABLES	{ quattroInstance }
		DESCRIPTION
			"Audio Ch3/4 Phase OK"
	::= 1100

	faultphaseReversal34TruevideoSourceC TRAP-TYPE
		ENTERPRISE	trapFault
		VARIABLES	{ quattroInstance }
		DESCRIPTION
			"Audio Ch3/4 Phase Reversed"
	::= 1101

-- end of phaseReversal34 videoSourceC trap
-- beginning of phaseReversal34 videoSourceD trap

	faultphaseReversal34FalsevideoSourceD TRAP-TYPE
		ENTERPRISE	trapFault
		VARIABLES	{ quattroInstance }
		DESCRIPTION
			"Audio Ch3/4 Phase OK"
	::= 1102

	faultphaseReversal34TruevideoSourceD TRAP-TYPE
		ENTERPRISE	trapFault
		VARIABLES	{ quattroInstance }
		DESCRIPTION
			"Audio Ch3/4 Phase Reversed"
	::= 1103

-- end of phaseReversal34 videoSourceD trap
-- beginning of phaseReversal56 videoSourceA trap

	faultphaseReversal56FalsevideoSourceA TRAP-TYPE
		ENTERPRISE	trapFault
		VARIABLES	{ quattroInstance }
		DESCRIPTION
			"Audio Ch5/6 Phase OK"
	::= 1104

	faultphaseReversal56TruevideoSourceA TRAP-TYPE
		ENTERPRISE	trapFault
		VARIABLES	{ quattroInstance }
		DESCRIPTION
			"Audio Ch5/6 Phase Reversed"
	::= 1105

-- end of phaseReversal56 videoSourceA trap
-- beginning of phaseReversal56 videoSourceB trap

	faultphaseReversal56FalsevideoSourceB TRAP-TYPE
		ENTERPRISE	trapFault
		VARIABLES	{ quattroInstance }
		DESCRIPTION
			"Audio Ch5/6 Phase OK"
	::= 1106

	faultphaseReversal56TruevideoSourceB TRAP-TYPE
		ENTERPRISE	trapFault
		VARIABLES	{ quattroInstance }
		DESCRIPTION
			"Audio Ch5/6 Phase Reversed"
	::= 1107

-- end of phaseReversal56 videoSourceB trap
-- beginning of phaseReversal56 videoSourceC trap

	faultphaseReversal56FalsevideoSourceC TRAP-TYPE
		ENTERPRISE	trapFault
		VARIABLES	{ quattroInstance }
		DESCRIPTION
			"Audio Ch5/6 Phase OK"
	::= 1108

	faultphaseReversal56TruevideoSourceC TRAP-TYPE
		ENTERPRISE	trapFault
		VARIABLES	{ quattroInstance }
		DESCRIPTION
			"Audio Ch5/6 Phase Reversed"
	::= 1109

-- end of phaseReversal56 videoSourceC trap
-- beginning of phaseReversal56 videoSourceD trap

	faultphaseReversal56FalsevideoSourceD TRAP-TYPE
		ENTERPRISE	trapFault
		VARIABLES	{ quattroInstance }
		DESCRIPTION
			"Audio Ch5/6 Phase OK"
	::= 1110

	faultphaseReversal56TruevideoSourceD TRAP-TYPE
		ENTERPRISE	trapFault
		VARIABLES	{ quattroInstance }
		DESCRIPTION
			"Audio Ch5/6 Phase Reversed"
	::= 1111

-- end of phaseReversal56 videoSourceD trap
-- beginning of audioOver12 videoSourceA trap

	faultaudioOver12FalsevideoSourceA TRAP-TYPE
		ENTERPRISE	trapFault
		VARIABLES	{ quattroInstance }
		DESCRIPTION
			"Audio Ch1/2 Level OK"
	::= 1112

	faultaudioOver12TruevideoSourceA TRAP-TYPE
		ENTERPRISE	trapFault
		VARIABLES	{ quattroInstance }
		DESCRIPTION
			"Audio Ch1/2 Level Too Loud"
	::= 1113

-- end of audioOver12 videoSourceA trap
-- beginning of audioOver12 videoSourceB trap

	faultaudioOver12FalsevideoSourceB TRAP-TYPE
		ENTERPRISE	trapFault
		VARIABLES	{ quattroInstance }
		DESCRIPTION
			"Audio Ch1/2 Level OK"
	::= 1114

	faultaudioOver12TruevideoSourceB TRAP-TYPE
		ENTERPRISE	trapFault
		VARIABLES	{ quattroInstance }
		DESCRIPTION
			"Audio Ch1/2 Level Too Loud"
	::= 1115

-- end of audioOver12 videoSourceB trap
-- beginning of audioOver12 videoSourceC trap

	faultaudioOver12FalsevideoSourceC TRAP-TYPE
		ENTERPRISE	trapFault
		VARIABLES	{ quattroInstance }
		DESCRIPTION
			"Audio Ch1/2 Level OK"
	::= 1116

	faultaudioOver12TruevideoSourceC TRAP-TYPE
		ENTERPRISE	trapFault
		VARIABLES	{ quattroInstance }
		DESCRIPTION
			"Audio Ch1/2 Level Too Loud"
	::= 1117

-- end of audioOver12 videoSourceC trap
-- beginning of audioOver12 videoSourceD trap

	faultaudioOver12FalsevideoSourceD TRAP-TYPE
		ENTERPRISE	trapFault
		VARIABLES	{ quattroInstance }
		DESCRIPTION
			"Audio Ch1/2 Level OK"
	::= 1118

	faultaudioOver12TruevideoSourceD TRAP-TYPE
		ENTERPRISE	trapFault
		VARIABLES	{ quattroInstance }
		DESCRIPTION
			"Audio Ch1/2 Level Too Loud"
	::= 1119

-- end of audioOver12 videoSourceD trap
-- beginning of audioOver34 videoSourceA trap

	faultaudioOver34FalsevideoSourceA TRAP-TYPE
		ENTERPRISE	trapFault
		VARIABLES	{ quattroInstance }
		DESCRIPTION
			"Audio Ch3/4 Level OK"
	::= 1120

	faultaudioOver34TruevideoSourceA TRAP-TYPE
		ENTERPRISE	trapFault
		VARIABLES	{ quattroInstance }
		DESCRIPTION
			"Audio Ch3/4 Level Too Loud"
	::= 1121

-- end of audioOver34 videoSourceA trap
-- beginning of audioOver34 videoSourceB trap

	faultaudioOver34FalsevideoSourceB TRAP-TYPE
		ENTERPRISE	trapFault
		VARIABLES	{ quattroInstance }
		DESCRIPTION
			"Audio Ch3/4 Level OK"
	::= 1122

	faultaudioOver34TruevideoSourceB TRAP-TYPE
		ENTERPRISE	trapFault
		VARIABLES	{ quattroInstance }
		DESCRIPTION
			"Audio Ch3/4 Level Too Loud"
	::= 1123

-- end of audioOver34 videoSourceB trap
-- beginning of audioOver34 videoSourceC trap

	faultaudioOver34FalsevideoSourceC TRAP-TYPE
		ENTERPRISE	trapFault
		VARIABLES	{ quattroInstance }
		DESCRIPTION
			"Audio Ch3/4 Level OK"
	::= 1124

	faultaudioOver34TruevideoSourceC TRAP-TYPE
		ENTERPRISE	trapFault
		VARIABLES	{ quattroInstance }
		DESCRIPTION
			"Audio Ch3/4 Level Too Loud"
	::= 1125

-- end of audioOver34 videoSourceC trap
-- beginning of audioOver34 videoSourceD trap

	faultaudioOver34FalsevideoSourceD TRAP-TYPE
		ENTERPRISE	trapFault
		VARIABLES	{ quattroInstance }
		DESCRIPTION
			"Audio Ch3/4 Level OK"
	::= 1126

	faultaudioOver34TruevideoSourceD TRAP-TYPE
		ENTERPRISE	trapFault
		VARIABLES	{ quattroInstance }
		DESCRIPTION
			"Audio Ch3/4 Level Too Loud"
	::= 1127

-- end of audioOver34 videoSourceD trap
-- beginning of audioOver56 videoSourceA trap

	faultaudioOver56FalsevideoSourceA TRAP-TYPE
		ENTERPRISE	trapFault
		VARIABLES	{ quattroInstance }
		DESCRIPTION
			"Audio Ch5/6 Level OK"
	::= 1128

	faultaudioOver56TruevideoSourceA TRAP-TYPE
		ENTERPRISE	trapFault
		VARIABLES	{ quattroInstance }
		DESCRIPTION
			"Audio Ch5/6 Level Too Loud"
	::= 1129

-- end of audioOver56 videoSourceA trap
-- beginning of audioOver56 videoSourceB trap

	faultaudioOver56FalsevideoSourceB TRAP-TYPE
		ENTERPRISE	trapFault
		VARIABLES	{ quattroInstance }
		DESCRIPTION
			"Audio Ch5/6 Level OK"
	::= 1130

	faultaudioOver56TruevideoSourceB TRAP-TYPE
		ENTERPRISE	trapFault
		VARIABLES	{ quattroInstance }
		DESCRIPTION
			"Audio Ch5/6 Level Too Loud"
	::= 1131

-- end of audioOver56 videoSourceB trap
-- beginning of audioOver56 videoSourceC trap

	faultaudioOver56FalsevideoSourceC TRAP-TYPE
		ENTERPRISE	trapFault
		VARIABLES	{ quattroInstance }
		DESCRIPTION
			"Audio Ch5/6 Level OK"
	::= 1132

	faultaudioOver56TruevideoSourceC TRAP-TYPE
		ENTERPRISE	trapFault
		VARIABLES	{ quattroInstance }
		DESCRIPTION
			"Audio Ch5/6 Level Too Loud"
	::= 1133

-- end of audioOver56 videoSourceC trap
-- beginning of audioOver56 videoSourceD trap

	faultaudioOver56FalsevideoSourceD TRAP-TYPE
		ENTERPRISE	trapFault
		VARIABLES	{ quattroInstance }
		DESCRIPTION
			"Audio Ch5/6 Level OK"
	::= 1134

	faultaudioOver56TruevideoSourceD TRAP-TYPE
		ENTERPRISE	trapFault
		VARIABLES	{ quattroInstance }
		DESCRIPTION
			"Audio Ch5/6 Level Too Loud"
	::= 1135

-- end of audioOver56 videoSourceD trap
-- beginning of audioSilence12 videoSourceA trap

	faultaudioSilence12FalsevideoSourceA TRAP-TYPE
		ENTERPRISE	trapFault
		VARIABLES	{ quattroInstance }
		DESCRIPTION
			"Audio Ch1/2 Level OK"
	::= 1136

	faultaudioSilence12TruevideoSourceA TRAP-TYPE
		ENTERPRISE	trapFault
		VARIABLES	{ quattroInstance }
		DESCRIPTION
			"Audio Ch1/2 Level Too Quiet"
	::= 1137

-- end of audioSilence12 videoSourceA trap
-- beginning of audioSilence12 videoSourceB trap

	faultaudioSilence12FalsevideoSourceB TRAP-TYPE
		ENTERPRISE	trapFault
		VARIABLES	{ quattroInstance }
		DESCRIPTION
			"Audio Ch1/2 Level OK"
	::= 1138

	faultaudioSilence12TruevideoSourceB TRAP-TYPE
		ENTERPRISE	trapFault
		VARIABLES	{ quattroInstance }
		DESCRIPTION
			"Audio Ch1/2 Level Too Quiet"
	::= 1139

-- end of audioSilence12 videoSourceB trap
-- beginning of audioSilence12 videoSourceC trap

	faultaudioSilence12FalsevideoSourceC TRAP-TYPE
		ENTERPRISE	trapFault
		VARIABLES	{ quattroInstance }
		DESCRIPTION
			"Audio Ch1/2 Level OK"
	::= 1140

	faultaudioSilence12TruevideoSourceC TRAP-TYPE
		ENTERPRISE	trapFault
		VARIABLES	{ quattroInstance }
		DESCRIPTION
			"Audio Ch1/2 Level Too Quiet"
	::= 1141

-- end of audioSilence12 videoSourceC trap
-- beginning of audioSilence12 videoSourceD trap

	faultaudioSilence12FalsevideoSourceD TRAP-TYPE
		ENTERPRISE	trapFault
		VARIABLES	{ quattroInstance }
		DESCRIPTION
			"Audio Ch1/2 Level OK"
	::= 1142

	faultaudioSilence12TruevideoSourceD TRAP-TYPE
		ENTERPRISE	trapFault
		VARIABLES	{ quattroInstance }
		DESCRIPTION
			"Audio Ch1/2 Level Too Quiet"
	::= 1143

-- end of audioSilence12 videoSourceD trap
-- beginning of audioSilence34 videoSourceA trap

	faultaudioSilence34FalsevideoSourceA TRAP-TYPE
		ENTERPRISE	trapFault
		VARIABLES	{ quattroInstance }
		DESCRIPTION
			"Audio Ch3/4 Level OK"
	::= 1144

	faultaudioSilence34TruevideoSourceA TRAP-TYPE
		ENTERPRISE	trapFault
		VARIABLES	{ quattroInstance }
		DESCRIPTION
			"Audio Ch3/4 Level Too Quiet"
	::= 1145

-- end of audioSilence34 videoSourceA trap
-- beginning of audioSilence34 videoSourceB trap

	faultaudioSilence34FalsevideoSourceB TRAP-TYPE
		ENTERPRISE	trapFault
		VARIABLES	{ quattroInstance }
		DESCRIPTION
			"Audio Ch3/4 Level OK"
	::= 1146

	faultaudioSilence34TruevideoSourceB TRAP-TYPE
		ENTERPRISE	trapFault
		VARIABLES	{ quattroInstance }
		DESCRIPTION
			"Audio Ch3/4 Level Too Quiet"
	::= 1147

-- end of audioSilence34 videoSourceB trap
-- beginning of audioSilence34 videoSourceC trap

	faultaudioSilence34FalsevideoSourceC TRAP-TYPE
		ENTERPRISE	trapFault
		VARIABLES	{ quattroInstance }
		DESCRIPTION
			"Audio Ch3/4 Level OK"
	::= 1148

	faultaudioSilence34TruevideoSourceC TRAP-TYPE
		ENTERPRISE	trapFault
		VARIABLES	{ quattroInstance }
		DESCRIPTION
			"Audio Ch3/4 Level Too Quiet"
	::= 1149

-- end of audioSilence34 videoSourceC trap
-- beginning of audioSilence34 videoSourceD trap

	faultaudioSilence34FalsevideoSourceD TRAP-TYPE
		ENTERPRISE	trapFault
		VARIABLES	{ quattroInstance }
		DESCRIPTION
			"Audio Ch3/4 Level OK"
	::= 1150

	faultaudioSilence34TruevideoSourceD TRAP-TYPE
		ENTERPRISE	trapFault
		VARIABLES	{ quattroInstance }
		DESCRIPTION
			"Audio Ch3/4 Level Too Quiet"
	::= 1151

-- end of audioSilence34 videoSourceD trap
-- beginning of audioSilence56 videoSourceA trap

	faultaudioSilence56FalsevideoSourceA TRAP-TYPE
		ENTERPRISE	trapFault
		VARIABLES	{ quattroInstance }
		DESCRIPTION
			"Audio Ch5/6 Level OK"
	::= 1152

	faultaudioSilence56TruevideoSourceA TRAP-TYPE
		ENTERPRISE	trapFault
		VARIABLES	{ quattroInstance }
		DESCRIPTION
			"Audio Ch5/6 Level Too Quiet"
	::= 1153

-- end of audioSilence56 videoSourceA trap
-- beginning of audioSilence56 videoSourceB trap

	faultaudioSilence56FalsevideoSourceB TRAP-TYPE
		ENTERPRISE	trapFault
		VARIABLES	{ quattroInstance }
		DESCRIPTION
			"Audio Ch5/6 Level OK"
	::= 1154

	faultaudioSilence56TruevideoSourceB TRAP-TYPE
		ENTERPRISE	trapFault
		VARIABLES	{ quattroInstance }
		DESCRIPTION
			"Audio Ch5/6 Level Too Quiet"
	::= 1155

-- end of audioSilence56 videoSourceB trap
-- beginning of audioSilence56 videoSourceC trap

	faultaudioSilence56FalsevideoSourceC TRAP-TYPE
		ENTERPRISE	trapFault
		VARIABLES	{ quattroInstance }
		DESCRIPTION
			"Audio Ch5/6 Level OK"
	::= 1156

	faultaudioSilence56TruevideoSourceC TRAP-TYPE
		ENTERPRISE	trapFault
		VARIABLES	{ quattroInstance }
		DESCRIPTION
			"Audio Ch5/6 Level Too Quiet"
	::= 1157

-- end of audioSilence56 videoSourceC trap
-- beginning of audioSilence56 videoSourceD trap

	faultaudioSilence56FalsevideoSourceD TRAP-TYPE
		ENTERPRISE	trapFault
		VARIABLES	{ quattroInstance }
		DESCRIPTION
			"Audio Ch5/6 Level OK"
	::= 1158

	faultaudioSilence56TruevideoSourceD TRAP-TYPE
		ENTERPRISE	trapFault
		VARIABLES	{ quattroInstance }
		DESCRIPTION
			"Audio Ch5/6 Level Too Quiet"
	::= 1159

-- end of audioSilence56 videoSourceD trap
-- beginning of audioMono12 videoSourceA trap

	faultaudioMono12FalsevideoSourceA TRAP-TYPE
		ENTERPRISE	trapFault
		VARIABLES	{ quattroInstance }
		DESCRIPTION
			"Audio Ch1/2 Stereo"
	::= 1160

	faultaudioMono12TruevideoSourceA TRAP-TYPE
		ENTERPRISE	trapFault
		VARIABLES	{ quattroInstance }
		DESCRIPTION
			"Audio Ch1/2 Mono"
	::= 1161

-- end of audioMono12 videoSourceA trap
-- beginning of audioMono12 videoSourceB trap

	faultaudioMono12FalsevideoSourceB TRAP-TYPE
		ENTERPRISE	trapFault
		VARIABLES	{ quattroInstance }
		DESCRIPTION
			"Audio Ch1/2 Stereo"
	::= 1162

	faultaudioMono12TruevideoSourceB TRAP-TYPE
		ENTERPRISE	trapFault
		VARIABLES	{ quattroInstance }
		DESCRIPTION
			"Audio Ch1/2 Mono"
	::= 1163

-- end of audioMono12 videoSourceB trap
-- beginning of audioMono12 videoSourceC trap

	faultaudioMono12FalsevideoSourceC TRAP-TYPE
		ENTERPRISE	trapFault
		VARIABLES	{ quattroInstance }
		DESCRIPTION
			"Audio Ch1/2 Stereo"
	::= 1164

	faultaudioMono12TruevideoSourceC TRAP-TYPE
		ENTERPRISE	trapFault
		VARIABLES	{ quattroInstance }
		DESCRIPTION
			"Audio Ch1/2 Mono"
	::= 1165

-- end of audioMono12 videoSourceC trap
-- beginning of audioMono12 videoSourceD trap

	faultaudioMono12FalsevideoSourceD TRAP-TYPE
		ENTERPRISE	trapFault
		VARIABLES	{ quattroInstance }
		DESCRIPTION
			"Audio Ch1/2 Stereo"
	::= 1166

	faultaudioMono12TruevideoSourceD TRAP-TYPE
		ENTERPRISE	trapFault
		VARIABLES	{ quattroInstance }
		DESCRIPTION
			"Audio Ch1/2 Mono"
	::= 1167

-- end of audioMono12 videoSourceD trap
-- beginning of audioMono34 videoSourceA trap

	faultaudioMono34FalsevideoSourceA TRAP-TYPE
		ENTERPRISE	trapFault
		VARIABLES	{ quattroInstance }
		DESCRIPTION
			"Audio Ch3/4 Stereo"
	::= 1168

	faultaudioMono34TruevideoSourceA TRAP-TYPE
		ENTERPRISE	trapFault
		VARIABLES	{ quattroInstance }
		DESCRIPTION
			"Audio Ch3/4 Mono"
	::= 1169

-- end of audioMono34 videoSourceA trap
-- beginning of audioMono34 videoSourceB trap

	faultaudioMono34FalsevideoSourceB TRAP-TYPE
		ENTERPRISE	trapFault
		VARIABLES	{ quattroInstance }
		DESCRIPTION
			"Audio Ch3/4 Stereo"
	::= 1170

	faultaudioMono34TruevideoSourceB TRAP-TYPE
		ENTERPRISE	trapFault
		VARIABLES	{ quattroInstance }
		DESCRIPTION
			"Audio Ch3/4 Mono"
	::= 1171

-- end of audioMono34 videoSourceB trap
-- beginning of audioMono34 videoSourceC trap

	faultaudioMono34FalsevideoSourceC TRAP-TYPE
		ENTERPRISE	trapFault
		VARIABLES	{ quattroInstance }
		DESCRIPTION
			"Audio Ch3/4 Stereo"
	::= 1172

	faultaudioMono34TruevideoSourceC TRAP-TYPE
		ENTERPRISE	trapFault
		VARIABLES	{ quattroInstance }
		DESCRIPTION
			"Audio Ch3/4 Mono"
	::= 1173

-- end of audioMono34 videoSourceC trap
-- beginning of audioMono34 videoSourceD trap

	faultaudioMono34FalsevideoSourceD TRAP-TYPE
		ENTERPRISE	trapFault
		VARIABLES	{ quattroInstance }
		DESCRIPTION
			"Audio Ch3/4 Stereo"
	::= 1174

	faultaudioMono34TruevideoSourceD TRAP-TYPE
		ENTERPRISE	trapFault
		VARIABLES	{ quattroInstance }
		DESCRIPTION
			"Audio Ch3/4 Mono"
	::= 1175

-- end of audioMono34 videoSourceD trap
-- beginning of audioMono56 videoSourceA trap

	faultaudioMono56FalsevideoSourceA TRAP-TYPE
		ENTERPRISE	trapFault
		VARIABLES	{ quattroInstance }
		DESCRIPTION
			"Audio Ch5/6 Stereo"
	::= 1176

	faultaudioMono56TruevideoSourceA TRAP-TYPE
		ENTERPRISE	trapFault
		VARIABLES	{ quattroInstance }
		DESCRIPTION
			"Audio Ch5/6 Mono"
	::= 1177

-- end of audioMono56 videoSourceA trap
-- beginning of audioMono56 videoSourceB trap

	faultaudioMono56FalsevideoSourceB TRAP-TYPE
		ENTERPRISE	trapFault
		VARIABLES	{ quattroInstance }
		DESCRIPTION
			"Audio Ch5/6 Stereo"
	::= 1178

	faultaudioMono56TruevideoSourceB TRAP-TYPE
		ENTERPRISE	trapFault
		VARIABLES	{ quattroInstance }
		DESCRIPTION
			"Audio Ch5/6 Mono"
	::= 1179

-- end of audioMono56 videoSourceB trap
-- beginning of audioMono56 videoSourceC trap

	faultaudioMono56FalsevideoSourceC TRAP-TYPE
		ENTERPRISE	trapFault
		VARIABLES	{ quattroInstance }
		DESCRIPTION
			"Audio Ch5/6 Stereo"
	::= 1180

	faultaudioMono56TruevideoSourceC TRAP-TYPE
		ENTERPRISE	trapFault
		VARIABLES	{ quattroInstance }
		DESCRIPTION
			"Audio Ch5/6 Mono"
	::= 1181

-- end of audioMono56 videoSourceC trap
-- beginning of audioMono56 videoSourceD trap

	faultaudioMono56FalsevideoSourceD TRAP-TYPE
		ENTERPRISE	trapFault
		VARIABLES	{ quattroInstance }
		DESCRIPTION
			"Audio Ch5/6 Stereo"
	::= 1182

	faultaudioMono56TruevideoSourceD TRAP-TYPE
		ENTERPRISE	trapFault
		VARIABLES	{ quattroInstance }
		DESCRIPTION
			"Audio Ch5/6 Mono"
	::= 1183

-- end of audioMono56 videoSourceD trap
-- beginning of lossOfVITC videoSourceA trap

	faultlossOfVITCFalsevideoSourceA TRAP-TYPE
		ENTERPRISE	trapFault
		VARIABLES	{ quattroInstance }
		DESCRIPTION
			"VITC OK"
	::= 1184

	faultlossOfVITCTruevideoSourceA TRAP-TYPE
		ENTERPRISE	trapFault
		VARIABLES	{ quattroInstance }
		DESCRIPTION
			"No VITC"
	::= 1185

-- end of lossOfVITC videoSourceA trap
-- beginning of lossOfVITC videoSourceB trap

	faultlossOfVITCFalsevideoSourceB TRAP-TYPE
		ENTERPRISE	trapFault
		VARIABLES	{ quattroInstance }
		DESCRIPTION
			"VITC OK"
	::= 1186

	faultlossOfVITCTruevideoSourceB TRAP-TYPE
		ENTERPRISE	trapFault
		VARIABLES	{ quattroInstance }
		DESCRIPTION
			"No VITC"
	::= 1187

-- end of lossOfVITC videoSourceB trap
-- beginning of lossOfVITC videoSourceC trap

	faultlossOfVITCFalsevideoSourceC TRAP-TYPE
		ENTERPRISE	trapFault
		VARIABLES	{ quattroInstance }
		DESCRIPTION
			"VITC OK"
	::= 1188

	faultlossOfVITCTruevideoSourceC TRAP-TYPE
		ENTERPRISE	trapFault
		VARIABLES	{ quattroInstance }
		DESCRIPTION
			"No VITC"
	::= 1189

-- end of lossOfVITC videoSourceC trap
-- beginning of lossOfVITC videoSourceD trap

	faultlossOfVITCFalsevideoSourceD TRAP-TYPE
		ENTERPRISE	trapFault
		VARIABLES	{ quattroInstance }
		DESCRIPTION
			"VITC OK"
	::= 1190

	faultlossOfVITCTruevideoSourceD TRAP-TYPE
		ENTERPRISE	trapFault
		VARIABLES	{ quattroInstance }
		DESCRIPTION
			"No VITC"
	::= 1191

-- end of lossOfVITC videoSourceD trap
-- beginning of lossOfSID videoSourceA trap

	faultlossOfSIDFalsevideoSourceA TRAP-TYPE
		ENTERPRISE	trapFault
		VARIABLES	{ quattroInstance }
		DESCRIPTION
			"SID OK"
	::= 1192

	faultlossOfSIDTruevideoSourceA TRAP-TYPE
		ENTERPRISE	trapFault
		VARIABLES	{ quattroInstance }
		DESCRIPTION
			"No SID"
	::= 1193

-- end of lossOfSID videoSourceA trap
-- beginning of lossOfSID videoSourceB trap

	faultlossOfSIDFalsevideoSourceB TRAP-TYPE
		ENTERPRISE	trapFault
		VARIABLES	{ quattroInstance }
		DESCRIPTION
			"SID OK"
	::= 1194

	faultlossOfSIDTruevideoSourceB TRAP-TYPE
		ENTERPRISE	trapFault
		VARIABLES	{ quattroInstance }
		DESCRIPTION
			"No SID"
	::= 1195

-- end of lossOfSID videoSourceB trap
-- beginning of lossOfSID videoSourceC trap

	faultlossOfSIDFalsevideoSourceC TRAP-TYPE
		ENTERPRISE	trapFault
		VARIABLES	{ quattroInstance }
		DESCRIPTION
			"SID OK"
	::= 1196

	faultlossOfSIDTruevideoSourceC TRAP-TYPE
		ENTERPRISE	trapFault
		VARIABLES	{ quattroInstance }
		DESCRIPTION
			"No SID"
	::= 1197

-- end of lossOfSID videoSourceC trap
-- beginning of lossOfSID videoSourceD trap

	faultlossOfSIDFalsevideoSourceD TRAP-TYPE
		ENTERPRISE	trapFault
		VARIABLES	{ quattroInstance }
		DESCRIPTION
			"SID OK"
	::= 1198

	faultlossOfSIDTruevideoSourceD TRAP-TYPE
		ENTERPRISE	trapFault
		VARIABLES	{ quattroInstance }
		DESCRIPTION
			"No SID"
	::= 1199

-- end of lossOfSID videoSourceD trap
-- beginning of lossOfProgramRating videoSourceA trap

	faultlossOfProgramRatingFalsevideoSourceA TRAP-TYPE
		ENTERPRISE	trapFault
		VARIABLES	{ quattroInstance }
		DESCRIPTION
			"Program Rating OK"
	::= 1200

	faultlossOfProgramRatingTruevideoSourceA TRAP-TYPE
		ENTERPRISE	trapFault
		VARIABLES	{ quattroInstance }
		DESCRIPTION
			"No Program Rating"
	::= 1201

-- end of lossOfProgramRating videoSourceA trap
-- beginning of lossOfProgramRating videoSourceB trap

	faultlossOfProgramRatingFalsevideoSourceB TRAP-TYPE
		ENTERPRISE	trapFault
		VARIABLES	{ quattroInstance }
		DESCRIPTION
			"Program Rating OK"
	::= 1202

	faultlossOfProgramRatingTruevideoSourceB TRAP-TYPE
		ENTERPRISE	trapFault
		VARIABLES	{ quattroInstance }
		DESCRIPTION
			"No Program Rating"
	::= 1203

-- end of lossOfProgramRating videoSourceB trap
-- beginning of lossOfProgramRating videoSourceC trap

	faultlossOfProgramRatingFalsevideoSourceC TRAP-TYPE
		ENTERPRISE	trapFault
		VARIABLES	{ quattroInstance }
		DESCRIPTION
			"Program Rating OK"
	::= 1204

	faultlossOfProgramRatingTruevideoSourceC TRAP-TYPE
		ENTERPRISE	trapFault
		VARIABLES	{ quattroInstance }
		DESCRIPTION
			"No Program Rating"
	::= 1205

-- end of lossOfProgramRating videoSourceC trap
-- beginning of lossOfProgramRating videoSourceD trap

	faultlossOfProgramRatingFalsevideoSourceD TRAP-TYPE
		ENTERPRISE	trapFault
		VARIABLES	{ quattroInstance }
		DESCRIPTION
			"Program Rating OK"
	::= 1206

	faultlossOfProgramRatingTruevideoSourceD TRAP-TYPE
		ENTERPRISE	trapFault
		VARIABLES	{ quattroInstance }
		DESCRIPTION
			"No Program Rating"
	::= 1207

-- end of lossOfProgramRating videoSourceD trap
-- beginning of lossOfCC videoSourceA trap

	faultlossOfCCFalsevideoSourceA TRAP-TYPE
		ENTERPRISE	trapFault
		VARIABLES	{ quattroInstance }
		DESCRIPTION
			"Closed Captioning OK"
	::= 1208

	faultlossOfCCTruevideoSourceA TRAP-TYPE
		ENTERPRISE	trapFault
		VARIABLES	{ quattroInstance }
		DESCRIPTION
			"No Closed Captioning"
	::= 1209

-- end of lossOfCC videoSourceA trap
-- beginning of lossOfCC videoSourceB trap

	faultlossOfCCFalsevideoSourceB TRAP-TYPE
		ENTERPRISE	trapFault
		VARIABLES	{ quattroInstance }
		DESCRIPTION
			"Closed Captioning OK"
	::= 1210

	faultlossOfCCTruevideoSourceB TRAP-TYPE
		ENTERPRISE	trapFault
		VARIABLES	{ quattroInstance }
		DESCRIPTION
			"No Closed Captioning"
	::= 1211

-- end of lossOfCC videoSourceB trap
-- beginning of lossOfCC videoSourceC trap

	faultlossOfCCFalsevideoSourceC TRAP-TYPE
		ENTERPRISE	trapFault
		VARIABLES	{ quattroInstance }
		DESCRIPTION
			"Closed Captioning OK"
	::= 1212

	faultlossOfCCTruevideoSourceC TRAP-TYPE
		ENTERPRISE	trapFault
		VARIABLES	{ quattroInstance }
		DESCRIPTION
			"No Closed Captioning"
	::= 1213

-- end of lossOfCC videoSourceC trap
-- beginning of lossOfCC videoSourceD trap

	faultlossOfCCFalsevideoSourceD TRAP-TYPE
		ENTERPRISE	trapFault
		VARIABLES	{ quattroInstance }
		DESCRIPTION
			"Closed Captioning OK"
	::= 1214

	faultlossOfCCTruevideoSourceD TRAP-TYPE
		ENTERPRISE	trapFault
		VARIABLES	{ quattroInstance }
		DESCRIPTION
			"No Closed Captioning"
	::= 1215

-- end of lossOfCC videoSourceD trap
-- beginning of pictureFreeze videoSourceA trap

	faultpictureFreezeFalsevideoSourceA TRAP-TYPE
		ENTERPRISE	trapFault
		VARIABLES	{ quattroInstance }
		DESCRIPTION
			"Video Not Frozen"
	::= 1216

	faultpictureFreezeTruevideoSourceA TRAP-TYPE
		ENTERPRISE	trapFault
		VARIABLES	{ quattroInstance }
		DESCRIPTION
			"Video Frozen"
	::= 1217

-- end of pictureFreeze videoSourceA trap
-- beginning of pictureFreeze videoSourceB trap

	faultpictureFreezeFalsevideoSourceB TRAP-TYPE
		ENTERPRISE	trapFault
		VARIABLES	{ quattroInstance }
		DESCRIPTION
			"Video Not Frozen"
	::= 1218

	faultpictureFreezeTruevideoSourceB TRAP-TYPE
		ENTERPRISE	trapFault
		VARIABLES	{ quattroInstance }
		DESCRIPTION
			"Video Frozen"
	::= 1219

-- end of pictureFreeze videoSourceB trap
-- beginning of pictureFreeze videoSourceC trap

	faultpictureFreezeFalsevideoSourceC TRAP-TYPE
		ENTERPRISE	trapFault
		VARIABLES	{ quattroInstance }
		DESCRIPTION
			"Video Not Frozen"
	::= 1220

	faultpictureFreezeTruevideoSourceC TRAP-TYPE
		ENTERPRISE	trapFault
		VARIABLES	{ quattroInstance }
		DESCRIPTION
			"Video Frozen"
	::= 1221

-- end of pictureFreeze videoSourceC trap
-- beginning of pictureFreeze videoSourceD trap

	faultpictureFreezeFalsevideoSourceD TRAP-TYPE
		ENTERPRISE	trapFault
		VARIABLES	{ quattroInstance }
		DESCRIPTION
			"Video Not Frozen"
	::= 1222

	faultpictureFreezeTruevideoSourceD TRAP-TYPE
		ENTERPRISE	trapFault
		VARIABLES	{ quattroInstance }
		DESCRIPTION
			"Video Frozen"
	::= 1223

-- end of pictureFreeze videoSourceD trap
-- beginning of pictureBlack videoSourceA trap

	faultpictureBlackFalsevideoSourceA TRAP-TYPE
		ENTERPRISE	trapFault
		VARIABLES	{ quattroInstance }
		DESCRIPTION
			"Video Not Black"
	::= 1224

	faultpictureBlackTruevideoSourceA TRAP-TYPE
		ENTERPRISE	trapFault
		VARIABLES	{ quattroInstance }
		DESCRIPTION
			"Video Black"
	::= 1225

-- end of pictureBlack videoSourceA trap
-- beginning of pictureBlack videoSourceB trap

	faultpictureBlackFalsevideoSourceB TRAP-TYPE
		ENTERPRISE	trapFault
		VARIABLES	{ quattroInstance }
		DESCRIPTION
			"Video Not Black"
	::= 1226

	faultpictureBlackTruevideoSourceB TRAP-TYPE
		ENTERPRISE	trapFault
		VARIABLES	{ quattroInstance }
		DESCRIPTION
			"Video Black"
	::= 1227

-- end of pictureBlack videoSourceB trap
-- beginning of pictureBlack videoSourceC trap

	faultpictureBlackFalsevideoSourceC TRAP-TYPE
		ENTERPRISE	trapFault
		VARIABLES	{ quattroInstance }
		DESCRIPTION
			"Video Not Black"
	::= 1228

	faultpictureBlackTruevideoSourceC TRAP-TYPE
		ENTERPRISE	trapFault
		VARIABLES	{ quattroInstance }
		DESCRIPTION
			"Video Black"
	::= 1229

-- end of pictureBlack videoSourceC trap
-- beginning of pictureBlack videoSourceD trap

	faultpictureBlackFalsevideoSourceD TRAP-TYPE
		ENTERPRISE	trapFault
		VARIABLES	{ quattroInstance }
		DESCRIPTION
			"Video Not Black"
	::= 1230

	faultpictureBlackTruevideoSourceD TRAP-TYPE
		ENTERPRISE	trapFault
		VARIABLES	{ quattroInstance }
		DESCRIPTION
			"Video Black"
	::= 1231

-- end of pictureBlack videoSourceD trap
-- beginning of gpi1  trap

	faultgpi1False TRAP-TYPE
		ENTERPRISE	trapFault
		VARIABLES	{ quattroInstance }
		DESCRIPTION
			"GPI1 Inactive"
	::= 1232

	faultgpi1True TRAP-TYPE
		ENTERPRISE	trapFault
		VARIABLES	{ quattroInstance }
		DESCRIPTION
			"GPI1 Active"
	::= 1233

-- end of gpi1  trap
-- beginning of gpi2  trap

	faultgpi2False TRAP-TYPE
		ENTERPRISE	trapFault
		VARIABLES	{ quattroInstance }
		DESCRIPTION
			"GPI2 Inactive"
	::= 1234

	faultgpi2True TRAP-TYPE
		ENTERPRISE	trapFault
		VARIABLES	{ quattroInstance }
		DESCRIPTION
			"GPI2 Active"
	::= 1235

-- end of gpi2  trap
-- beginning of gpi3  trap

	faultgpi3False TRAP-TYPE
		ENTERPRISE	trapFault
		VARIABLES	{ quattroInstance }
		DESCRIPTION
			"GPI3 Inactive"
	::= 1236

	faultgpi3True TRAP-TYPE
		ENTERPRISE	trapFault
		VARIABLES	{ quattroInstance }
		DESCRIPTION
			"GPI3 Active"
	::= 1237

-- end of gpi3  trap
-- beginning of gpi4  trap

	faultgpi4False TRAP-TYPE
		ENTERPRISE	trapFault
		VARIABLES	{ quattroInstance }
		DESCRIPTION
			"GPI4 Inactive"
	::= 1238

	faultgpi4True TRAP-TYPE
		ENTERPRISE	trapFault
		VARIABLES	{ quattroInstance }
		DESCRIPTION
			"GPI4 Active"
	::= 1239

-- end of gpi4  trap
-- beginning of gpi5  trap

	faultgpi5False TRAP-TYPE
		ENTERPRISE	trapFault
		VARIABLES	{ quattroInstance }
		DESCRIPTION
			"GPI5 Inactive"
	::= 1240

	faultgpi5True TRAP-TYPE
		ENTERPRISE	trapFault
		VARIABLES	{ quattroInstance }
		DESCRIPTION
			"GPI5 Active"
	::= 1241

-- end of gpi5  trap
-- beginning of gpi6  trap

	faultgpi6False TRAP-TYPE
		ENTERPRISE	trapFault
		VARIABLES	{ quattroInstance }
		DESCRIPTION
			"GPI6 Inactive"
	::= 1242

	faultgpi6True TRAP-TYPE
		ENTERPRISE	trapFault
		VARIABLES	{ quattroInstance }
		DESCRIPTION
			"GPI6 Active"
	::= 1243

-- end of gpi6  trap
-- beginning of gpi7  trap

	faultgpi7False TRAP-TYPE
		ENTERPRISE	trapFault
		VARIABLES	{ quattroInstance }
		DESCRIPTION
			"GPI7 Inactive"
	::= 1244

	faultgpi7True TRAP-TYPE
		ENTERPRISE	trapFault
		VARIABLES	{ quattroInstance }
		DESCRIPTION
			"GPI7 Active"
	::= 1245

-- end of gpi7  trap
-- beginning of gpi8  trap

	faultgpi8False TRAP-TYPE
		ENTERPRISE	trapFault
		VARIABLES	{ quattroInstance }
		DESCRIPTION
			"GPI8 Inactive"
	::= 1246

	faultgpi8True TRAP-TYPE
		ENTERPRISE	trapFault
		VARIABLES	{ quattroInstance }
		DESCRIPTION
			"GPI8 Active" 
	::= 1247

-- end of gpi8  trap
-- beginning of gpi9  trap

	faultgpi9False TRAP-TYPE
		ENTERPRISE	trapFault
		VARIABLES	{ quattroInstance }
		DESCRIPTION
			"GPI9 Inactive"
	::= 1248

	faultgpi9True TRAP-TYPE
		ENTERPRISE	trapFault
		VARIABLES	{ quattroInstance }
		DESCRIPTION
			"GPI9 Active"
	::= 1249

-- end of gpi9  trap
-- beginning of gpi10  trap

	faultgpi10False TRAP-TYPE
		ENTERPRISE	trapFault
		VARIABLES	{ quattroInstance }
		DESCRIPTION
			"GPI10 Inactive"
	::= 1250

	faultgpi10True TRAP-TYPE
		ENTERPRISE	trapFault
		VARIABLES	{ quattroInstance }
		DESCRIPTION
			"GPI10 Active"
	::= 1251

-- end of gpi10  trap
-- beginning of gpi11  trap

	faultgpi11False TRAP-TYPE
		ENTERPRISE	trapFault
		VARIABLES	{ quattroInstance }
		DESCRIPTION
			"GPI11 Inactive"
	::= 1252

	faultgpi11True TRAP-TYPE
		ENTERPRISE	trapFault
		VARIABLES	{ quattroInstance }
		DESCRIPTION
			"GPI11 Active"
	::= 1253

-- end of gpi11  trap
-- beginning of gpi12  trap

	faultgpi12False TRAP-TYPE
		ENTERPRISE	trapFault
		VARIABLES	{ quattroInstance }
		DESCRIPTION
			"GPI12 Inactive"
	::= 1254

	faultgpi12True TRAP-TYPE
		ENTERPRISE	trapFault
		VARIABLES	{ quattroInstance }
		DESCRIPTION
			"GPI12 Active" 
	::= 1255

-- end of gpi12  trap


END
