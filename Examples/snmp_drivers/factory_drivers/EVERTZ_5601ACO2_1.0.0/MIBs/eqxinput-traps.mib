-- Copyright 2007 Evertz Microsystems Ltd.
-- Fri Nov 09 11:38:06 2007
-- Confidential

EQXINPUT-TRAPS DEFINITIONS ::= BEGIN

IMPORTS
    eqxInputTraps
        FROM EQXINPUT-MIB
    TRAP-TYPE
        FROM RFC-1215;

    trapFault OBJECT IDENTIFIER ::= { eqxInputTraps 1 }


-- beginning of signalLoss VideoInput1 trap

    faultsignalLossVideoInput1False TRAP-TYPE
        ENTERPRISE  trapFault
        DESCRIPTION
            "Video Present on VideoInput1"
    ::= 1000
    
    faultsignalLossVideoInput1True TRAP-TYPE
        ENTERPRISE  trapFault
        DESCRIPTION
            "Video Missing on VideoInput1"
    ::= 1001

-- end of signalLoss VideoInput1 trap

-- beginning of signalLoss VideoInput2 trap

    faultsignalLossVideoInput2False TRAP-TYPE
        ENTERPRISE  trapFault
        DESCRIPTION
            "Video Present on VideoInput2"
    ::= 1002
    
    faultsignalLossVideoInput2True TRAP-TYPE
        ENTERPRISE  trapFault
        DESCRIPTION
            "Video Missing on VideoInput2"
    ::= 1003

-- end of signalLoss VideoInput2 trap

-- beginning of signalLoss VideoInput3 trap

    faultsignalLossVideoInput3False TRAP-TYPE
        ENTERPRISE  trapFault
        DESCRIPTION
            "Video Present on VideoInput3"
    ::= 1004
    
    faultsignalLossVideoInput3True TRAP-TYPE
        ENTERPRISE  trapFault
        DESCRIPTION
            "Video Missing on VideoInput3"
    ::= 1005

-- end of signalLoss VideoInput3 trap

-- beginning of signalLoss VideoInput4 trap

    faultsignalLossVideoInput4False TRAP-TYPE
        ENTERPRISE  trapFault
        DESCRIPTION
            "Video Present on VideoInput4"
    ::= 1006
    
    faultsignalLossVideoInput4True TRAP-TYPE
        ENTERPRISE  trapFault
        DESCRIPTION
            "Video Missing on VideoInput4"
    ::= 1007

-- end of signalLoss VideoInput4 trap

-- beginning of signalLoss VideoInput5 trap

    faultsignalLossVideoInput5False TRAP-TYPE
        ENTERPRISE  trapFault
        DESCRIPTION
            "Video Present on VideoInput5"
    ::= 1008
    
    faultsignalLossVideoInput5True TRAP-TYPE
        ENTERPRISE  trapFault
        DESCRIPTION
            "Video Missing on VideoInput5"
    ::= 1009

-- end of signalLoss VideoInput5 trap

-- beginning of signalLoss VideoInput6 trap

    faultsignalLossVideoInput6False TRAP-TYPE
        ENTERPRISE  trapFault
        DESCRIPTION
            "Video Present on VideoInput6"
    ::= 1010
    
    faultsignalLossVideoInput6True TRAP-TYPE
        ENTERPRISE  trapFault
        DESCRIPTION
            "Video Missing on VideoInput6"
    ::= 1011

-- end of signalLoss VideoInput6 trap

-- beginning of signalLoss VideoInput7 trap

    faultsignalLossVideoInput7False TRAP-TYPE
        ENTERPRISE  trapFault
        DESCRIPTION
            "Video Present on VideoInput7"
    ::= 1012
    
    faultsignalLossVideoInput7True TRAP-TYPE
        ENTERPRISE  trapFault
        DESCRIPTION
            "Video Missing on VideoInput7"
    ::= 1013

-- end of signalLoss VideoInput7 trap

-- beginning of signalLoss VideoInput8 trap

    faultsignalLossVideoInput8False TRAP-TYPE
        ENTERPRISE  trapFault
        DESCRIPTION
            "Video Present on VideoInput8"
    ::= 1014
    
    faultsignalLossVideoInput8True TRAP-TYPE
        ENTERPRISE  trapFault
        DESCRIPTION
            "Video Missing on VideoInput8"
    ::= 1015

-- end of signalLoss VideoInput8 trap

-- beginning of signalLoss VideoInput9 trap

    faultsignalLossVideoInput9False TRAP-TYPE
        ENTERPRISE  trapFault
        DESCRIPTION
            "Video Present on VideoInput9"
    ::= 1016
    
    faultsignalLossVideoInput9True TRAP-TYPE
        ENTERPRISE  trapFault
        DESCRIPTION
            "Video Missing on VideoInput9"
    ::= 1017

-- end of signalLoss VideoInput9 trap

-- beginning of signalLoss VideoInput10 trap

    faultsignalLossVideoInput10False TRAP-TYPE
        ENTERPRISE  trapFault
        DESCRIPTION
            "Video Present on VideoInput10"
    ::= 1018
    
    faultsignalLossVideoInput10True TRAP-TYPE
        ENTERPRISE  trapFault
        DESCRIPTION
            "Video Missing on VideoInput10"
    ::= 1019

-- end of signalLoss VideoInput10 trap

-- beginning of signalLoss VideoInput11 trap

    faultsignalLossVideoInput11False TRAP-TYPE
        ENTERPRISE  trapFault
        DESCRIPTION
            "Video Present on VideoInput11"
    ::= 1020
    
    faultsignalLossVideoInput11True TRAP-TYPE
        ENTERPRISE  trapFault
        DESCRIPTION
            "Video Missing on VideoInput11"
    ::= 1021

-- end of signalLoss VideoInput11 trap

-- beginning of signalLoss VideoInput12 trap

    faultsignalLossVideoInput12False TRAP-TYPE
        ENTERPRISE  trapFault
        DESCRIPTION
            "Video Present on VideoInput12"
    ::= 1022
    
    faultsignalLossVideoInput12True TRAP-TYPE
        ENTERPRISE  trapFault
        DESCRIPTION
            "Video Missing on VideoInput12"
    ::= 1023

-- end of signalLoss VideoInput12 trap

-- beginning of signalLoss VideoInput13 trap

    faultsignalLossVideoInput13False TRAP-TYPE
        ENTERPRISE  trapFault
        DESCRIPTION
            "Video Present on VideoInput13"
    ::= 1024
    
    faultsignalLossVideoInput13True TRAP-TYPE
        ENTERPRISE  trapFault
        DESCRIPTION
            "Video Missing on VideoInput13"
    ::= 1025

-- end of signalLoss VideoInput13 trap

-- beginning of signalLoss VideoInput14 trap

    faultsignalLossVideoInput14False TRAP-TYPE
        ENTERPRISE  trapFault
        DESCRIPTION
            "Video Present on VideoInput14"
    ::= 1026
    
    faultsignalLossVideoInput14True TRAP-TYPE
        ENTERPRISE  trapFault
        DESCRIPTION
            "Video Missing on VideoInput14"
    ::= 1027

-- end of signalLoss VideoInput14 trap

-- beginning of signalLoss VideoInput15 trap

    faultsignalLossVideoInput15False TRAP-TYPE
        ENTERPRISE  trapFault
        DESCRIPTION
            "Video Present on VideoInput15"
    ::= 1028
    
    faultsignalLossVideoInput15True TRAP-TYPE
        ENTERPRISE  trapFault
        DESCRIPTION
            "Video Missing on VideoInput15"
    ::= 1029

-- end of signalLoss VideoInput15 trap

-- beginning of signalLoss VideoInput16 trap

    faultsignalLossVideoInput16False TRAP-TYPE
        ENTERPRISE  trapFault
        DESCRIPTION
            "Video Present on VideoInput16"
    ::= 1030
    
    faultsignalLossVideoInput16True TRAP-TYPE
        ENTERPRISE  trapFault
        DESCRIPTION
            "Video Missing on VideoInput16"
    ::= 1031

-- end of signalLoss VideoInput16 trap

-- beginning of signalLoss VideoInput17 trap

    faultsignalLossVideoInput17False TRAP-TYPE
        ENTERPRISE  trapFault
        DESCRIPTION
            "Video Present on VideoInput17"
    ::= 1032
    
    faultsignalLossVideoInput17True TRAP-TYPE
        ENTERPRISE  trapFault
        DESCRIPTION
            "Video Missing on VideoInput17"
    ::= 1033

-- end of signalLoss VideoInput17 trap

-- beginning of signalLoss VideoInput18 trap

    faultsignalLossVideoInput18False TRAP-TYPE
        ENTERPRISE  trapFault
        DESCRIPTION
            "Video Present on VideoInput18"
    ::= 1034
    
    faultsignalLossVideoInput18True TRAP-TYPE
        ENTERPRISE  trapFault
        DESCRIPTION
            "Video Missing on VideoInput18"
    ::= 1035

-- end of signalLoss VideoInput18 trap

-- beginning of cardOverTemperature trap

    faultcardOverTemperatureFalse TRAP-TYPE
        ENTERPRISE  trapFault
        DESCRIPTION
            "Card Over Temperature Error Cleared"
    ::= 1036
    
    faultcardOverTemperatureTrue TRAP-TYPE
        ENTERPRISE  trapFault
        DESCRIPTION
            "Card Over Temperature Error Alert"
    ::= 1037

-- end of cardOverTemperature trap

-- beginning of rxErrorFlinkControlBus trap

    faultrxErrorFlinkControlBusFalse TRAP-TYPE
        ENTERPRISE  trapFault
        DESCRIPTION
            "F-Link Control Bus Receive Error Cleared"
    ::= 1038
    
    faultrxErrorFlinkControlBusTrue TRAP-TYPE
        ENTERPRISE  trapFault
        DESCRIPTION
            "F-Link Control Bus Receive Error Alert"
    ::= 1039

-- end of rxErrorFlinkControlBus trap

-- beginning of rxOverrunFlinkControlBus trap

    faultrxOverrunFlinkControlBusFalse TRAP-TYPE
        ENTERPRISE  trapFault
        DESCRIPTION
            "F-Link Control Bus Rx FIFO Overrun Error Cleared"
    ::= 1040
    
    faultrxOverrunFlinkControlBusTrue TRAP-TYPE
        ENTERPRISE  trapFault
        DESCRIPTION
            "F-Link Control Bus Rx FIFO Overrun Error Alert"
    ::= 1041

-- end of rxOverrunFlinkControlBus trap

-- beginning of txOverrunFlinkControlBus trap

    faulttxOverrunFlinkControlBusFalse TRAP-TYPE
        ENTERPRISE  trapFault
        DESCRIPTION
            "F-Link Control Bus Tx FIFO Overrun Error Cleared"
    ::= 1042
    
    faulttxOverrunFlinkControlBusTrue TRAP-TYPE
        ENTERPRISE  trapFault
        DESCRIPTION
            "F-Link Control Bus Tx FIFO Overrun Error Alert"
    ::= 1043

-- end of txOverrunFlinkControlBus trap

-- beginning of commsQuietFlinkControlBus trap

    faultcommsQuietFlinkControlBusFalse TRAP-TYPE
        ENTERPRISE  trapFault
        DESCRIPTION
            "F-Link Control Bus Receive Comms Quiet Error Cleared"
    ::= 1044
    
    faultcommsQuietFlinkControlBusTrue TRAP-TYPE
        ENTERPRISE  trapFault
        DESCRIPTION
            "F-Link Control Bus Receive Comms Quiet Error Alert"
    ::= 1045

-- end of commsQuietFlinkControlBus trap

-- beginning of rxErrorFlinkStatusBus trap

    faultrxErrorFlinkStatusBusFalse TRAP-TYPE
        ENTERPRISE  trapFault
        DESCRIPTION
            "F-Link Status Bus Receive Error Cleared"
    ::= 1046
    
    faultrxErrorFlinkStatusBusTrue TRAP-TYPE
        ENTERPRISE  trapFault
        DESCRIPTION
            "F-Link Status Bus Receive Error Alert"
    ::= 1047

-- end of rxErrorFlinkStatusBus trap

-- beginning of rxOverrunFlinkStatusBus trap

    faultrxOverrunFlinkStatusBusFalse TRAP-TYPE
        ENTERPRISE  trapFault
        DESCRIPTION
            "F-Link Status Bus Rx FIFO Overrun Error Cleared"
    ::= 1048
    
    faultrxOverrunFlinkStatusBusTrue TRAP-TYPE
        ENTERPRISE  trapFault
        DESCRIPTION
            "F-Link Status Bus Rx FIFO Overrun Error Alert"
    ::= 1049

-- end of rxOverrunFlinkStatusBus trap

-- beginning of txOverrunFlinkStatusBus trap

    faulttxOverrunFlinkStatusBusFalse TRAP-TYPE
        ENTERPRISE  trapFault
        DESCRIPTION
            "F-Link Status Bus Tx FIFO Overrun Error Cleared"
    ::= 1050
    
    faulttxOverrunFlinkStatusBusTrue TRAP-TYPE
        ENTERPRISE  trapFault
        DESCRIPTION
            "F-Link Status Bus Tx FIFO Overrun Error Alert"
    ::= 1051

-- end of txOverrunFlinkStatusBus trap

-- beginning of commsQuietFlinkStatusBus trap

    faultcommsQuietFlinkStatusBusFalse TRAP-TYPE
        ENTERPRISE  trapFault
        DESCRIPTION
            "F-Link Status Bus Receive Comms Quiet Error Cleared"
    ::= 1052
    
    faultcommsQuietFlinkStatusBusTrue TRAP-TYPE
        ENTERPRISE  trapFault
        DESCRIPTION
            "F-Link Status Bus Receive Comms Quiet Error Alert"
    ::= 1053

-- end of commsQuietFlinkStatusBus trap

-- beginning of primaryEthernetLinkDown trap

    faultprimaryEthernetLinkDownFalse TRAP-TYPE
        ENTERPRISE  trapFault
        DESCRIPTION
            "Primary Ethernet Link Down Error Cleared"
    ::= 1054
    
    faultprimaryEthernetLinkDownTrue TRAP-TYPE
        ENTERPRISE  trapFault
        DESCRIPTION
            "Primary Ethernet Link Down Error Alert"
    ::= 1055

-- end of primaryEthernetLinkDown trap

-- beginning of secondaryEthernetLinkDown trap

    faultsecondaryEthernetLinkDownFalse TRAP-TYPE
        ENTERPRISE  trapFault
        DESCRIPTION
            "Secondary Ethernet Link Down Error Cleared"
    ::= 1056
    
    faultsecondaryEthernetLinkDownTrue TRAP-TYPE
        ENTERPRISE  trapFault
        DESCRIPTION
            "Secondary Ethernet Link Down Error Alert"
    ::= 1057

-- end of secondaryEthernetLinkDown trap

-- beginning of fvh50Missing trap

    faultfvh50MissingFalse TRAP-TYPE
        ENTERPRISE  trapFault
        DESCRIPTION
            "FVH 50Hz Reference Missing Cleared"
    ::= 1058
    
    faultfvh50MissingTrue TRAP-TYPE
        ENTERPRISE  trapFault
        DESCRIPTION
            "FVH 50Hz Reference Missing Alert"
    ::= 1059

-- end of fvh50Missing trap

-- beginning of fvh60Missing trap

    faultfvh60MissingFalse TRAP-TYPE
        ENTERPRISE  trapFault
        DESCRIPTION
            "FVH 60Hz Reference Missing Cleared"
    ::= 1060
    
    faultfvh60MissingTrue TRAP-TYPE
        ENTERPRISE  trapFault
        DESCRIPTION
            "FVH 60Hz Reference Missing Alert"
    ::= 1061

-- end of fvh60Missing trap




END
