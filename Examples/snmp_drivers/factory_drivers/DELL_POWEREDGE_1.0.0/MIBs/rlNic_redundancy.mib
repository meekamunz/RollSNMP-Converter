RADLAN-rlNicRedundancy DEFINITIONS ::= BEGIN

-- Title:      RADLAN Management Private Extension
-- Version:    7.37.00.01
-- Date:       16 Jun 2005

IMPORTS
    rnd                                                     FROM RADLAN-MIB
    MODULE-IDENTITY, OBJECT-TYPE                            FROM SNMPv2-SMI
    TruthValue                                              FROM SNMPv2-TC;


rlNicRedundancy MODULE-IDENTITY
        LAST-UPDATED "200506160000Z"
        ORGANIZATION "Radlan, A Marvell Company"
        CONTACT-INFO
             "marvell.com"
        DESCRIPTION
             "The private MIB module definition for RND NIC redundancy MIB."
        REVISION "200506160000Z"
        DESCRIPTION
             "Initial version of this MIB."
        ::= { rnd 105 }


rlNicRedundancyEnable OBJECT-TYPE
    SYNTAX  TruthValue
    MAX-ACCESS  read-write
    STATUS      current
    DESCRIPTION
      "Enable / Disable NIC redundancy."
    REFERENCE
        ""
    DEFVAL { false }
    ::= { rlNicRedundancy 1 }

END
