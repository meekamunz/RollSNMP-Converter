DELL-RAC-MIB

       --FORCE-INCLUDE <bsp.h>
       --FORCE-INCLUDE <pna.h>
       --FORCE-INCLUDE <pna_mib.h>
       --FORCE-INCLUDE <envoy/h/asn1.h>
       --FORCE-INCLUDE <envoy/h/mib.h>
       --FORCE-INCLUDE <envoy/h/snmp.h>
       --FORCE-INCLUDE <envoy/h/snmpstat.h>
       --FORCE-INCLUDE "sm_types.h"
       --FORCE-INCLUDE "snmpvars.h"
       --FORCE-INCLUDE "pnamib.h"

 DEFINITIONS ::= BEGIN

 IMPORTS
    enterprises
       FROM RFC1155-SMI
    OBJECT-TYPE
       FROM RFC-1212
    TRAP-TYPE
       FROM RFC-1215;


   -- text convention ------------------------------------------------------------------------

        DisplayString ::=
            OCTET STRING
         -- This data type is used to model textual information taken
         -- from the NVT ASCII character set.  By convention, objects
         -- with this syntax are declared as having
         --
         --      SIZE (0..255)

        DellString                  ::= DisplayString (SIZE (0..64))

        DellStatus                  ::= INTEGER {
            other(1),               -- the status of the object is not one of the following:
            unknown(2),             -- the status of the object is unknown
                                    --  (not known or monitored)
            ok(3),                  -- the status of the object is ok
            nonCritical(4),         -- the status of the object is warning, non-critical
            critical(5),            -- the status of the object is critical (failure)
            nonRecoverable(6)       -- the status of the object is non-recoverable (dead)
        }

    -- MIB Objects ----------------------------------------------------------------------------

       dell                          OBJECT IDENTIFIER ::= { enterprises    674   }
       server3                       OBJECT IDENTIFIER ::= { dell           10892 }
       drsOutofBandGroup             OBJECT IDENTIFIER ::= { server3        2     }

       drsInformationGroup           OBJECT IDENTIFIER ::= { drsOutofBandGroup 1}
       drsProductInfoGroup           OBJECT IDENTIFIER ::= { drsInformationGroup 1}
       drsFirmwareGroup              OBJECT IDENTIFIER ::= { drsInformationGroup 2}
       drsStatusGroup                OBJECT IDENTIFIER ::= { drsOutofBandGroup 2 }

       -- drsProductInfoGroup ------------------------------------------------------------------------

           drsProductName OBJECT-TYPE
               SYNTAX          DellString
               ACCESS          read-only
               STATUS          mandatory
               DESCRIPTION     "0001.0001.0001 This attribute defines the product name of a remote access card. "
               --DEFAULT get-function-async    get_from_config_db
               --DEFAULT next-function-async   std_next_async
               --DEFAULT cookie                "ID_PROD_INFO"
              ::= { drsProductInfoGroup 1 }

           drsProductShortName OBJECT-TYPE
               SYNTAX          DellString
               ACCESS          read-only
               STATUS          mandatory
               DESCRIPTION     "0001.0001.0002 This attribute defines the short product name of a remote access card. "
               --DEFAULT get-function-async    get_from_config_db
               --DEFAULT next-function-async   std_next_async
               --DEFAULT cookie                "CARD_NAME"
              ::= { drsProductInfoGroup 2 }

           drsProductDescription OBJECT-TYPE
               SYNTAX          DellString
               ACCESS          read-only
               STATUS          mandatory
               DESCRIPTION     "0001.0001.0003 This attribute defines the product description of a remote access card. "
               --DEFAULT get-function-async    get_from_config_db
               --DEFAULT next-function-async   std_next_async
               --DEFAULT cookie                "ID_DESC_INFO"
              ::= { drsProductInfoGroup 3 }

           drsProductManufacturer OBJECT-TYPE
               SYNTAX          DellString
               ACCESS          read-only
               STATUS          mandatory
               DESCRIPTION     "0001.0001.0004 This attribute defines the product manufacturer of a remote access card. "
               --DEFAULT get-function-async    get_from_config_db
               --DEFAULT next-function-async   std_next_async
               --DEFAULT cookie                "BOARD_MANUFACTURER"
              ::= { drsProductInfoGroup 4 }

           drsProductVersion OBJECT-TYPE
               SYNTAX          DellString
               ACCESS          read-only
               STATUS          mandatory
               DESCRIPTION     "0001.0001.0005 This attribute defines the product version of a remote access card. "
               --DEFAULT get-function-async    get_from_config_db
               --DEFAULT next-function-async   std_next_async
               --DEFAULT cookie                "ID_VERS_INFO"
              ::= { drsProductInfoGroup 5 }

           drsChassisServiceTag OBJECT-TYPE
               SYNTAX          DellString
               ACCESS          read-only
               STATUS          mandatory
               DESCRIPTION     "0001.0001.0006 This attribute defines the service tag of the DELL chassis. "
               --DEFAULT get-function-async    get_from_config_db
               --DEFAULT next-function-async   std_next_async
               --DEFAULT cookie                "D_SYSINFO_CHASSIS_SERVICETAG"
              ::= { drsProductInfoGroup 6 }

           drsProductURL       OBJECT-TYPE
               SYNTAX          DellString
               ACCESS          read-only
               STATUS          mandatory
               DESCRIPTION
                   "0001.0001.0007 This attribute defines the out-of-band UI URL of a remote access card. "
               --DEFAULT get-function-async    get_%n_async
               --DEFAULT next-function-async   std_next_async
               --DEFAULT cookie                (char *) 0
               ::= { drsProductInfoGroup 7 }

           drsProductChassisAssetTag  OBJECT-TYPE
               SYNTAX          DellString
               ACCESS          read-only
               STATUS          mandatory
               DESCRIPTION
                   "0001.0001.0008 This attribute defines the Asset Tag of the DELL chassis. "
               --DEFAULT get-function-async    get_from_config_db
               --DEFAULT next-function-async   std_next_async
               --DEFAULT cookie                "D_SYSINFO_CHASSIS_ASSETTAG"
               ::= { drsProductInfoGroup 8 }

           drsProductChassisLocation  OBJECT-TYPE
               SYNTAX          DellString
               ACCESS          read-only
               STATUS          mandatory
               DESCRIPTION
                   "0001.0001.0009 This attribute defines the location of the DELL chassis. "
               --DEFAULT get-function-async    get_from_config_db
               --DEFAULT next-function-async   std_next_async
               --DEFAULT cookie                "LOCATION"
               ::= { drsProductInfoGroup 9 }

           drsProductChassisName  OBJECT-TYPE
               SYNTAX          DellString
               ACCESS          read-only
               STATUS          mandatory
               DESCRIPTION
                   "0001.0001.0010 This attribute defines the name of the DELL chassis. "
               --DEFAULT get-function-async    get_from_config_db
               --DEFAULT next-function-async   std_next_async
               --DEFAULT cookie                "CHASSIS_NAME"
               ::= { drsProductInfoGroup 10 }

           drsSystemServiceTag  OBJECT-TYPE
               SYNTAX          DellString
               ACCESS          read-only
               STATUS          mandatory
               DESCRIPTION
                   "0001.0001.0011 This attribute defines the service tag of a DELL system. "
               --DEFAULT get-function-async    get_from_config_db
               --DEFAULT next-function-async   std_next_async
               --DEFAULT cookie                "D_SYSINFO_SERVICETAG"
               ::= { drsProductInfoGroup 11 }

           drsProductSystemAssetTag  OBJECT-TYPE
               SYNTAX          DellString
               ACCESS          read-only
               STATUS          mandatory
               DESCRIPTION
                   "0001.0001.0012 This attribute defines the asset tag of a DELL system. "
               --DEFAULT get-function-async    get_from_config_db
               --DEFAULT next-function-async   std_next_async
               --DEFAULT cookie                "D_SYSINFO_ASSETTAG"
               ::= { drsProductInfoGroup 12 }

           drsProductSystemSlot  OBJECT-TYPE
               SYNTAX          DellString
               ACCESS          read-only
               STATUS          mandatory
               DESCRIPTION
                   "0001.0001.0013 This attribute defines the slot number of a DELL system. "
               --DEFAULT get-function-async    get_%n_async
               --DEFAULT next-function-async   std_next_async
               --DEFAULT cookie                (char *) 0
               ::= { drsProductInfoGroup 13 }


       -- drsFirmwareInfoGroup ------------------------------------------------------------------------

           drsFirmwareVersion OBJECT-TYPE
               SYNTAX          DellString
               ACCESS          read-only
               STATUS          mandatory
               DESCRIPTION     "0001.0002.0001 This attribute defines the firmware version of a remote access card. "
               --DEFAULT get-function-async    get_from_config_db
               --DEFAULT next-function-async   std_next_async
               --DEFAULT cookie                "FIRMWARE_REVISION"
              ::= { drsFirmwareGroup 1 }

       -- drsStatusGroup ------------------------------------------------------------------------

           drsGlobalSystemStatus OBJECT-TYPE
               SYNTAX          DellStatus
               ACCESS          read-only
               STATUS          mandatory
               DESCRIPTION     "0002.0001 This attribute defines the overall DELL chassis status
                               being monitored by the remote access card."
               --DEFAULT get-function-async    get_%n_async
               --DEFAULT next-function-async   std_next_async
               --DEFAULT         cookie  (char *)0
               ::= { drsStatusGroup 1 }

   -------------------------------------------------------------------------------
   --
   -- Alert Group
   --
   -------------------------------------------------------------------------------

   --
   -- Alert Variables
   --

       drsAlertGroup          OBJECT IDENTIFIER ::= { drsOutofBandGroup 5000  }
       drsAlertVariables      OBJECT IDENTIFIER ::= { drsAlertGroup     10    }

       drsAlertSystem         OBJECT-TYPE
           SYNTAX             OCTET STRING (SIZE (0..255))
           ACCESS             read-only
           STATUS             mandatory
           DESCRIPTION
           "5000.0010.0001 Name of the system generating the alert."
           --DEFAULT get-function-async    get_%n_async
           --DEFAULT next-function-async   std_next_async
           ::= { drsAlertVariables 1 }

       drsAlertTableIndexOID  OBJECT-TYPE
           SYNTAX             OBJECT IDENTIFIER
           ACCESS             read-only
           STATUS             mandatory
           DESCRIPTION
           "5000.0010.0002 0.0"
           --DEFAULT get-function-async    get_OID_null_async
           --DEFAULT next-function-async   std_next_async
           ::= { drsAlertVariables 2 }

       drsAlertMessage        OBJECT-TYPE
           SYNTAX             OCTET STRING (SIZE (0..1024))
           ACCESS             read-only
           STATUS             mandatory
           DESCRIPTION
           "5000.0010.0003 Message describing the alert."
           --DEFAULT get-function-async    get_string_null_async
           --DEFAULT next-function-async   std_next_async
           ::= { drsAlertVariables 3 }

       drsAlertCurrentStatus  OBJECT-TYPE
           SYNTAX             DellStatus
           ACCESS             read-only
           STATUS             mandatory
           DESCRIPTION
           "5000.0010.0004 Current status of object causing the alert."
           --DEFAULT get-function-async    get_dellstatus_unknow_async
           --DEFAULT next-function-async   std_next_async
           ::= { drsAlertVariables 4 }

       drsAlertPreviousStatus OBJECT-TYPE
           SYNTAX             DellStatus
           ACCESS             read-only
           STATUS             mandatory
           DESCRIPTION
           "5000.0010.0005 Previous status of object causing the alert."
           --DEFAULT get-function-async    get_dellstatus_unknow_async
           --DEFAULT next-function-async   std_next_async
           ::= { drsAlertVariables 5 }

       drsAlertData           OBJECT-TYPE
           SYNTAX             OCTET STRING (SIZE (0..1024))
           ACCESS             read-only
           STATUS             mandatory
           DESCRIPTION
           "5000.0010.0006 Alert data."
           --DEFAULT get-function-async    get_string_null_async
           --DEFAULT next-function-async   std_next_async
           ::= { drsAlertVariables 6 }


   --
   -- Alerts
   --

       alertDrscTestTrapEvent      TRAP-TYPE
       ENTERPRISE  drsOutofBandGroup
       VARIABLES { drsAlertSystem,
                   drsAlertTableIndexOID,
                   drsAlertMessage,
                   drsAlertCurrentStatus,
                   drsAlertPreviousStatus,
                   drsAlertData }
       DESCRIPTION
       "The RAC generated a test trap event in response to a user request."
       --#TYPE "Dell RAC Test TRAP Event"
       --#SUMMARY "%s"
       --#ARGUMENTS {2}
       --#SEVERITY INFORMATIONAL
       --#CATEGORY Status Events
       ::= 1001

       alertDrscAuthError          TRAP-TYPE
       ENTERPRISE  drsOutofBandGroup
       VARIABLES { drsAlertSystem,
                   drsAlertTableIndexOID,
                   drsAlertMessage,
                   drsAlertCurrentStatus,
                   drsAlertPreviousStatus,
                   drsAlertData }
       DESCRIPTION
       "The RAC Authentication Failures during a time period have Exceeded a Threshold."
       --#TYPE "Dell RAC Authentication Error"
       --#SUMMARY "%s"
       --#ARGUMENTS {2}
       --#SEVERITY MINOR
       --#CATEGORY Error Events
       ::= 1002

       alertDrscLostESM          TRAP-TYPE
       ENTERPRISE  drsOutofBandGroup
       VARIABLES { drsAlertSystem,
                   drsAlertTableIndexOID,
                   drsAlertMessage,
                   drsAlertCurrentStatus,
                   drsAlertPreviousStatus,
                   drsAlertData }
       DESCRIPTION
       "The RAC cannot communicate with the baseboard management controller (ESM)."
       --#TYPE "Dell RAC Lost Communication with ESM"
       --#SUMMARY "%s"
       --#ARGUMENTS {2}
       --#SEVERITY MINOR
       --#CATEGORY Error Events
       ::= 1003

       alertDrscFoundESM          TRAP-TYPE
       ENTERPRISE  drsOutofBandGroup
       VARIABLES { drsAlertSystem,
                   drsAlertTableIndexOID,
                   drsAlertMessage,
                   drsAlertCurrentStatus,
                   drsAlertPreviousStatus,
                   drsAlertData }
       DESCRIPTION
       "The RAC is communicating normally with the baseboard management controller (ESM)."
       --#TYPE "Dell RAC Communication with ESM is OK"
       --#SUMMARY "%s"
       --#ARGUMENTS {2}
       --#SEVERITY INFORMATIONAL
       --#CATEGORY Error Events
       ::= 1004

       alertDrscPowerOff          TRAP-TYPE
       ENTERPRISE  drsOutofBandGroup
       VARIABLES { drsAlertSystem,
                   drsAlertTableIndexOID,
                   drsAlertMessage,
                   drsAlertCurrentStatus,
                   drsAlertPreviousStatus,
                   drsAlertData }
       DESCRIPTION
       "The RAC has detected a System power state change to powered-off."
       --#TYPE "Dell RAC Detected System Powered-Off"
       --#SUMMARY "%s"
       --#ARGUMENTS {2}
       --#SEVERITY CRITICAL
       --#CATEGORY Error Events
       ::= 1005

       alertDrscPowerOn          TRAP-TYPE
       ENTERPRISE  drsOutofBandGroup
       VARIABLES { drsAlertSystem,
                   drsAlertTableIndexOID,
                   drsAlertMessage,
                   drsAlertCurrentStatus,
                   drsAlertPreviousStatus,
                   drsAlertData }
       DESCRIPTION
       "The RAC has detected a system power state change to powered-on."
       --#TYPE "Dell RAC Detected System Powered-On"
       --#SUMMARY "%s"
       --#ARGUMENTS {2}
       --#SEVERITY INFORMATIONAL
       --#CATEGORY Error Events
       ::= 1006

       alertDrscWatchdogExpired          TRAP-TYPE
       ENTERPRISE  drsOutofBandGroup
       VARIABLES { drsAlertSystem,
                   drsAlertTableIndexOID,
                   drsAlertMessage,
                   drsAlertCurrentStatus,
                   drsAlertPreviousStatus,
                   drsAlertData }
       DESCRIPTION
       "The RAC has detected that the system watchdog has expired indicating a system hang."
       --#TYPE "Dell RAC Detected Watchdog Expired"
       --#SUMMARY "%s"
       --#ARGUMENTS {2}
       --#SEVERITY CRITICAL
       --#CATEGORY Error Events
       ::= 1007

       alertDrscBattLow          TRAP-TYPE
       ENTERPRISE  drsOutofBandGroup
       VARIABLES { drsAlertSystem,
                   drsAlertTableIndexOID,
                   drsAlertMessage,
                   drsAlertCurrentStatus,
                   drsAlertPreviousStatus,
                   drsAlertData }
       DESCRIPTION
       "The RAC Battery charge is below 25% indicating that the battery may only be able to power the DRSC for 8-10 minutes."
       --#TYPE "Dell RAC Battery Charge Low"
       --#SUMMARY "%s"
       --#ARGUMENTS {2}
       --#SEVERITY MINOR
       --#CATEGORY Error Events
       ::= 1008

       alertDrscTempNormal          TRAP-TYPE
       ENTERPRISE  drsOutofBandGroup
       VARIABLES { drsAlertSystem,
                   drsAlertTableIndexOID,
                   drsAlertMessage,
                   drsAlertCurrentStatus,
                   drsAlertPreviousStatus,
                   drsAlertData }
       DESCRIPTION
       "The RAC Temperature probe has retured to a normal value."
       --#TYPE "Dell RAC Temperature Normal"
       --#SUMMARY "%s"
       --#ARGUMENTS {2}
       --#SEVERITY INFORMATIONAL
       --#CATEGORY Error Events
       ::= 1009

       alertDrscTempWarning          TRAP-TYPE
       ENTERPRISE  drsOutofBandGroup
       VARIABLES { drsAlertSystem,
                   drsAlertTableIndexOID,
                   drsAlertMessage,
                   drsAlertCurrentStatus,
                   drsAlertPreviousStatus,
                   drsAlertData }
       DESCRIPTION
       "The RAC Temperature probe has detected a Warning value."
       --#TYPE "Dell RAC Temperature Warning"
       --#SUMMARY "%s"
       --#ARGUMENTS {2}
       --#SEVERITY MINOR
       --#CATEGORY Error Events
       ::= 1010

       alertDrscTempCritical          TRAP-TYPE
       ENTERPRISE  drsOutofBandGroup
       VARIABLES { drsAlertSystem,
                   drsAlertTableIndexOID,
                   drsAlertMessage,
                   drsAlertCurrentStatus,
                   drsAlertPreviousStatus,
                   drsAlertData }
       DESCRIPTION
       "The RAC Temperature probe has detected a failure (or critical) value."
       --#TYPE "Dell RAC Temperature Failure"
       --#SUMMARY "%s"
       --#ARGUMENTS {2}
       --#SEVERITY CRITICAL
       --#CATEGORY Error Events
       ::= 1011

       alertDrscVoltNormal          TRAP-TYPE
       ENTERPRISE  drsOutofBandGroup
       VARIABLES { drsAlertSystem,
                   drsAlertTableIndexOID,
                   drsAlertMessage,
                   drsAlertCurrentStatus,
                   drsAlertPreviousStatus,
                   drsAlertData }
       DESCRIPTION
       "The RAC voltage has returned to a normal value."
       --#TYPE "Dell RAC Voltage Normal"
       --#SUMMARY "%s"
       --#ARGUMENTS {2}
       --#SEVERITY INFORMATIONAL
       --#CATEGORY Error Events
       ::= 1012

       alertDrscVoltWarning          TRAP-TYPE
       ENTERPRISE  drsOutofBandGroup
       VARIABLES { drsAlertSystem,
                   drsAlertTableIndexOID,
                   drsAlertMessage,
                   drsAlertCurrentStatus,
                   drsAlertPreviousStatus,
                   drsAlertData }
       DESCRIPTION
       "The RAC voltage probe has detected a warning value."
       --#TYPE "Dell RAC Battery Warning"
       --#SUMMARY "%s"
       --#ARGUMENTS {2}
       --#SEVERITY MINOR
       --#CATEGORY Error Events
       ::= 1013

       alertDrscVoltCritical          TRAP-TYPE
       ENTERPRISE  drsOutofBandGroup
       VARIABLES { drsAlertSystem,
                   drsAlertTableIndexOID,
                   drsAlertMessage,
                   drsAlertCurrentStatus,
                   drsAlertPreviousStatus,
                   drsAlertData }
       DESCRIPTION
       "The RAC voltage probe has detected a failure (or critical) value."
       --#TYPE "Dell RAC Voltage Failure"
       --#SUMMARY "%s"
       --#ARGUMENTS {2}
       --#SEVERITY CRITICAL
       --#CATEGORY Error Events
       ::= 1014

       alertDrscSELWarning          TRAP-TYPE
       ENTERPRISE  drsOutofBandGroup
       VARIABLES { drsAlertSystem,
                   drsAlertTableIndexOID,
                   drsAlertMessage,
                   drsAlertCurrentStatus,
                   drsAlertPreviousStatus,
                   drsAlertData }
       DESCRIPTION
       "The RAC has detected a new event in the System Event Log with Severity: Warning."
       --#TYPE "Dell RAC System Event Log Warning"
       --#SUMMARY "%s"
       --#ARGUMENTS {2}
       --#SEVERITY MAJOR
       --#CATEGORY Error Events
       ::= 1015

       alertDrscSELCritical          TRAP-TYPE
       ENTERPRISE  drsOutofBandGroup
       VARIABLES { drsAlertSystem,
                   drsAlertTableIndexOID,
                   drsAlertMessage,
                   drsAlertCurrentStatus,
                   drsAlertPreviousStatus,
                   drsAlertData }
       DESCRIPTION
       "The RAC has detected a new event in the System Event Log with Severity: Critical."
       --#TYPE "Dell RAC System Event Log Critical"
       --#SUMMARY "%s"
       --#ARGUMENTS {2}
       --#SEVERITY CRITICAL
       --#CATEGORY Error Events
       ::= 1016

       alertDrscSEL80percentFull          TRAP-TYPE
       ENTERPRISE  drsOutofBandGroup
       VARIABLES { drsAlertSystem,
                   drsAlertTableIndexOID,
                   drsAlertMessage,
                   drsAlertCurrentStatus,
                   drsAlertPreviousStatus,
                   drsAlertData }
       DESCRIPTION
       "The RAC has detected that the System Event Log is 80% full."
       --#TYPE "Dell System Event Log 80% Full Warning"
       --#SUMMARY "%s"
       --#ARGUMENTS {2}
       --#SEVERITY MAJOR
       --#CATEGORY Status Events
       ::= 1017

       alertDrscSEL90percentFull          TRAP-TYPE
       ENTERPRISE  drsOutofBandGroup
       VARIABLES { drsAlertSystem,
                   drsAlertTableIndexOID,
                   drsAlertMessage,
                   drsAlertCurrentStatus,
                   drsAlertPreviousStatus,
                   drsAlertData }
       DESCRIPTION
       "The RAC has detected that the System Event Log is 90% full."
       --#TYPE " Dell System Event Log 90% Full Warning "
       --#SUMMARY "%s"
       --#ARGUMENTS {2}
       --#SEVERITY MAJOR
       --#CATEGORY Status Events
       ::= 1018

       alertDrscSEL100percentFull          TRAP-TYPE
       ENTERPRISE  drsOutofBandGroup
       VARIABLES { drsAlertSystem,
                   drsAlertTableIndexOID,
                   drsAlertMessage,
                   drsAlertCurrentStatus,
                   drsAlertPreviousStatus,
                   drsAlertData }
       DESCRIPTION
       "The RAC has detected that the System Event Log is 100% full."
       --#TYPE " Dell System Event Log 100% Full Warning "
       --#SUMMARY "%s"
       --#ARGUMENTS {2}
       --#SEVERITY MAJOR
       --#CATEGORY Status Events
       ::= 1019

       alertDrscSELNormal          TRAP-TYPE
       ENTERPRISE  drsOutofBandGroup
       VARIABLES { drsAlertSystem,
                   drsAlertTableIndexOID,
                   drsAlertMessage,
                   drsAlertCurrentStatus,
                   drsAlertPreviousStatus,
                   drsAlertData }
       DESCRIPTION
       "The RAC has detected a new event in the System Event Log with Severity: Normal."
       --#TYPE "Dell RAC System Event Log Normal"
       --#SUMMARY "%s"
       --#ARGUMENTS {2}
       --#SEVERITY INFORMATIONAL
       --#CATEGORY Error Events
       ::= 1020

 END
